-- **********************************************************************
-- Copyright Datang Telecom.
-- All rights reserved.

-- File Name : enb2018-06-29
-- Date      : 2018-06-29 10:42:29
-- Author    : Datang Mobile Excel - Mib Editor 6
-- -- -- -- -- -- -- -- -- -- -- -- -- -- -- -- -- -- -- -- -- -- -- -- -- -- -- -- -- -- -- -- -- -- -- -- -- -- -- -- -- -- -- -- -- -- -- -- -- -- -- -- -- -- -- -- -- -- -- -- -- -- -- -- -- -- -- -- -- -- -- -- -- -- -- -- -- -- -- -- -- -- -- -- -- -- 
-- **********************************************************************

 DTM-TD-LTE-ENODEB-ENBMIB	DEFINITIONS ::= BEGIN
 IMPORTS
  TEXTUAL-CONVENTION, DisplayString, RowStatus, MacAddress, DateAndTime, VariablePointer
   FROM SNMPv2-TC
  MODULE-IDENTITY, OBJECT-TYPE, NOTIFICATION-TYPE, IpAddress, Unsigned32, Integer32, Counter32, enterprises
   FROM SNMPv2-SMI;
 
 dtm MODULE-IDENTITY
  LAST-UPDATED "0212240000Z"
  ORGANIZATION "Datang Mobile Technology CO., LTD"
  CONTACT-INFO "        O&M Group, Software department,
 
         Postal: Datang Mobile Communicatins Equipment CO., LTD.
                 No.29 Xue Yuan Rd., Hai Dian District, Beijing, P.R.C.
 
            Zip: 100083
 
            Tel: 86 10 58832000 Ext.2415
 
         E-mail: zhangjianfeng@datangmobile.com"
  DESCRIPTION  "This mib module defines enterprise MIBs under dtt
         enterprise OID that manage LTE NodeB system."
  ::=  {  enterprises  5105  }

-- TEXTUAL-CONVENTIONS --
InetAddressType ::= TEXTUAL-CONVENTION
    STATUS      current
    DESCRIPTION
        "A value that represents a type of Internet address.

         unknown(0)  An unknown address type.  This value MUST
                     be used if the value of the corresponding
                     InetAddress object is a zero-length string.
                     It may also be used to indicate an IP address
                     that is not in one of the formats defined
                     below.

         ipv4(1)     An IPv4 address as defined by the
                     InetAddressIPv4 textual convention.

         ipv6(2)     An IPv6 address as defined by the
                     InetAddressIPv6 textual convention.

         Each definition of a concrete InetAddressType value must be
         accompanied by a definition of a textual convention for use
         with that InetAddressType.

         To support future extensions, the InetAddressType textual
         convention SHOULD NOT be sub-typed in object type definitions.
         It MAY be sub-typed in compliance statements in order to
         require only a subset of these address types for a compliant
         implementation.

         Implementations must ensure that InetAddressType objects
         and any dependent objects (e.g., InetAddress objects) are
         consistent.  An inconsistentValue error must be generated
         if an attempt to change an InetAddressType object would,
         for example, lead to an undefined InetAddress value.  In
         particular, InetAddressType/InetAddress pairs must be
         changed together if the address type changes (e.g., from
         ipv6(2) to ipv4(1))."
    SYNTAX       INTEGER {
                     unknown(0),
                     ipv4(1),
                     ipv6(2)
                 }

 
InetAddress ::= TEXTUAL-CONVENTION
    STATUS      current
    DESCRIPTION
        "Denotes a generic Internet address.

         An InetAddress value is always interpreted within the context
         of an InetAddressType value.  Every usage of the InetAddress
         textual convention is required to specify the InetAddressType
         object that provides the context.  It is suggested that the
         InetAddressType object be logically registered before the
         object(s) that use the InetAddress textual convention, if
         they appear in the same logical row.

         The value of an InetAddress object must always be
         consistent with the value of the associated InetAddressType
         object.  Attempts to set an InetAddress object to a value
         inconsistent with the associated InetAddressType
         must fail with an inconsistentValue error.

         When this textual convention is used as the syntax of an
         index object, there may be issues with the limit of 128
         sub-identifiers specified in SMIv2, STD 58.  In this case,
         the object definition MUST include a 'SIZE' clause to
         limit the number of potential instance sub-identifiers;
         otherwise the applicable constraints MUST be stated in
         the appropriate conceptual row DESCRIPTION clauses, or
         in the surrounding documentation if there is no single
         DESCRIPTION clause that is appropriate."
    SYNTAX       OCTET STRING (SIZE (4..16))
    
    
Unsigned32Array ::= TEXTUAL-CONVENTION
    DISPLAY-HINT  "{Unsigned32,Unsigned32,...,Unsigned32}"
    STATUS      current
    DESCRIPTION
        "."
    SYNTAX      OCTET STRING (SIZE (4..256))
    
Integer32Array ::= TEXTUAL-CONVENTION
    DISPLAY-HINT  "{Integer32,Integer32,...,Integer32}"
    STATUS      current
    DESCRIPTION
        "."
    SYNTAX      OCTET STRING (SIZE (4..256))
    
    
MncMccType ::= TEXTUAL-CONVENTION
    DISPLAY-HINT    "1d1d1d"
    STATUS   current
    DESCRIPTION      
   "A mnc or mcc specification for plmn.
         The mnc or mcc format must match the following:

 

         field  strings  contents                   range
         -----  ------   --------                   -----
           1      1      mnc or mcc area code1       0..9|255
           2      1      mnc or mcc area code2       0..9|255
           3      1      mnc or mcc area code3       0..9|255
                    
         For example, mnc = 086 should be input as:
                         
             mnc = 086         

 

         mnc = 86 should be input as:

             mnc = 86

        the last area should be input 0xFF by machine to be 86FF.

             
         Note that every Unsigned32 must be shown in one digit." 
    SYNTAX  OCTET STRING (SIZE(3))
    

lte	OBJECT IDENTIFIER
		::=  {  dtm  100  }


	lteCommon		 OBJECT IDENTIFIER
		::=  { lte  1 }


	faultManagement		 OBJECT IDENTIFIER
		::=  { lteCommon  1 }


	alarmGeneralManagement		 OBJECT IDENTIFIER
		::=  { faultManagement  1 }


	alarmCauseTable		 OBJECT-TYPE
		SYNTAX					 SEQUENCE  OF	 AlarmCauseEntry
		MAX-ACCESS			 not-accessible
		STATUS					 current
		DESCRIPTION			 " -- "
		::=  { alarmGeneralManagement  1 }


	alarmCauseEntry		 OBJECT-TYPE
		SYNTAX					 AlarmCauseEntry
		MAX-ACCESS			 not-accessible
		STATUS					 current
		DESCRIPTION			 " -- "
		INDEX						{ alarmCauseNo }
		::=  { alarmCauseTable  1 }


	AlarmCauseEntry		 ::=  SEQUENCE {
		alarmCauseNo					Integer32,
		alarmCauseRowStatus					RowStatus,
		alarmCauseSeverity					INTEGER,
		alarmCauseIsValid					INTEGER,
		alarmCauseType					INTEGER,
		alarmCauseClearStyle					INTEGER,
		alarmCauseToAlarmBox					INTEGER,
		alarmCauseItfNProtocolCauseNo					Integer32,
		alarmCauseIsStateful					INTEGER,
		alarmCausePrimaryAlarmCauseNo					Integer32,
		alarmCauseStatefulClearDeditheringInterval					Integer32,
		alarmCauseStatefulCreateDeditheringInterval					Integer32,
		alarmCauseStatefulDelayTime					Integer32,
		alarmCauseCompressionInterval					Integer32,
		alarmCauseCompressionRepetitions					Integer32,
		alarmCauseAutoProcessPolicy					INTEGER,
		alarmCauseProcessFlag					INTEGER
		}


	alarmCauseNo		 OBJECT-TYPE
		SYNTAX					 Integer32( 0 .. 2147483647 )
		MAX-ACCESS			 not-accessible
		STATUS					 current
		DESCRIPTION			 " -- "
		::=  { alarmCauseEntry  1 }


	alarmCauseRowStatus		 OBJECT-TYPE
		SYNTAX					 RowStatus
		MAX-ACCESS			 read-only
		STATUS					 current
		DESCRIPTION			 " -- "
		::=  { alarmCauseEntry  2 }


	alarmCauseSeverity		 OBJECT-TYPE
		SYNTAX					 INTEGER{ critical(1),major(2),minor(3),warn(4),clear(6)  }
		MAX-ACCESS			 read-write
		STATUS					 current
		DESCRIPTION			 " -- "
		::=  { alarmCauseEntry  3 }


	alarmCauseIsValid		 OBJECT-TYPE
		SYNTAX					 INTEGER{ valid(0),invalid(1)  }
		MAX-ACCESS			 read-write
		STATUS					 current
		DESCRIPTION			 " -- "
		::=  { alarmCauseEntry  4 }


	alarmCauseType		 OBJECT-TYPE
		SYNTAX					 INTEGER{ communication(1),qos(2),processing(3),equipment(4),environment(5)  }
		MAX-ACCESS			 read-only
		STATUS					 current
		DESCRIPTION			 " -- "
		::=  { alarmCauseEntry  5 }


	alarmCauseClearStyle		 OBJECT-TYPE
		SYNTAX					 INTEGER{ adac(1),admc(2)  }
		MAX-ACCESS			 read-only
		STATUS					 current
		DESCRIPTION			 " -- "
		::=  { alarmCauseEntry  6 }


	alarmCauseToAlarmBox		 OBJECT-TYPE
		SYNTAX					 INTEGER{ closed(0),open(1)  }
		MAX-ACCESS			 read-write
		STATUS					 current
		DESCRIPTION			 " -- "
		::=  { alarmCauseEntry  7 }


	alarmCauseItfNProtocolCauseNo		 OBJECT-TYPE
		SYNTAX					 Integer32( -2147483648 .. 2147483647 )
		MAX-ACCESS			 read-only
		STATUS					 current
		DESCRIPTION			 " -- "
		::=  { alarmCauseEntry  8 }


	alarmCauseIsStateful		 OBJECT-TYPE
		SYNTAX					 INTEGER{ stateful(0),stateless(1)  }
		MAX-ACCESS			 read-only
		STATUS					 current
		DESCRIPTION			 " -- "
		::=  { alarmCauseEntry  9 }


	alarmCausePrimaryAlarmCauseNo		 OBJECT-TYPE
		SYNTAX					 Integer32( 1 .. 2500|0 )
		MAX-ACCESS			 read-only
		STATUS					 current
		DESCRIPTION			 " -- "
		::=  { alarmCauseEntry  10 }


	alarmCauseStatefulClearDeditheringInterval		 OBJECT-TYPE
		SYNTAX					 Integer32( 0 .. 86400|-1 )
		MAX-ACCESS			 read-write
		STATUS					 current
		DESCRIPTION			 " -- "
		::=  { alarmCauseEntry  11 }


	alarmCauseStatefulCreateDeditheringInterval		 OBJECT-TYPE
		SYNTAX					 Integer32( 0 .. 86400 )
		MAX-ACCESS			 read-write
		STATUS					 current
		DESCRIPTION			 " -- "
		::=  { alarmCauseEntry  12 }


	alarmCauseStatefulDelayTime		 OBJECT-TYPE
		SYNTAX					 Integer32( 0 .. 86400 )
		MAX-ACCESS			 read-write
		STATUS					 current
		DESCRIPTION			 " -- "
		::=  { alarmCauseEntry  13 }


	alarmCauseCompressionInterval		 OBJECT-TYPE
		SYNTAX					 Integer32( 0 .. 86400 )
		MAX-ACCESS			 read-write
		STATUS					 current
		DESCRIPTION			 " -- "
		::=  { alarmCauseEntry  14 }


	alarmCauseCompressionRepetitions		 OBJECT-TYPE
		SYNTAX					 Integer32( 0 .. 30 )
		MAX-ACCESS			 read-write
		STATUS					 current
		DESCRIPTION			 " -- "
		::=  { alarmCauseEntry  15 }


	alarmCauseAutoProcessPolicy		 OBJECT-TYPE
		SYNTAX					 INTEGER{ closed(0),objectAutoReset(1),neAutoReset(2)  }
		MAX-ACCESS			 read-write
		STATUS					 current
		DESCRIPTION			 " -- "
		::=  { alarmCauseEntry  16 }


	alarmCauseProcessFlag		 OBJECT-TYPE
		SYNTAX					 INTEGER{ closed(0),denyAccess(1)  }
		MAX-ACCESS			 read-write
		STATUS					 current
		DESCRIPTION			 " -- "
		::=  { alarmCauseEntry  17 }


	efdTable		 OBJECT-TYPE
		SYNTAX					 SEQUENCE  OF	 EfdEntry
		MAX-ACCESS			 not-accessible
		STATUS					 current
		DESCRIPTION			 " -- "
		::=  { alarmGeneralManagement  2 }


	efdEntry		 OBJECT-TYPE
		SYNTAX					 EfdEntry
		MAX-ACCESS			 not-accessible
		STATUS					 current
		DESCRIPTION			 " -- "
		INDEX						{ efdIndex }
		::=  { efdTable  1 }


	EfdEntry		 ::=  SEQUENCE {
		efdIndex					Integer32,
		efdRowStatus					RowStatus,
		efdAdministrativeState					INTEGER,
		efdStartTime					DateAndTime,
		efdEndTime					DateAndTime,
		efdAlarmType					BITS,
		efdAlarmSeverity					BITS,
		efdAlarmSourceObject					VariablePointer,
		efdAlarmNo					Integer32
		}


	efdIndex		 OBJECT-TYPE
		SYNTAX					 Integer32( 0 .. 30 )
		MAX-ACCESS			 not-accessible
		STATUS					 current
		DESCRIPTION			 " -- "
		::=  { efdEntry  1 }


	efdRowStatus		 OBJECT-TYPE
		SYNTAX					 RowStatus
		MAX-ACCESS			 read-create
		STATUS					 current
		DESCRIPTION			 " -- "
		::=  { efdEntry  2 }


	efdAdministrativeState		 OBJECT-TYPE
		SYNTAX					 INTEGER{ unlocked(0),locked(1)  }
		MAX-ACCESS			 read-create
		STATUS					 current
		DESCRIPTION			 " -- "
		::=  { efdEntry  3 }


	efdStartTime		 OBJECT-TYPE
		SYNTAX					 DateAndTime
		MAX-ACCESS			 read-create
		STATUS					 current
		DESCRIPTION			 " -- "
		::=  { efdEntry  4 }


	efdEndTime		 OBJECT-TYPE
		SYNTAX					 DateAndTime
		MAX-ACCESS			 read-create
		STATUS					 current
		DESCRIPTION			 " -- "
		::=  { efdEntry  5 }


	efdAlarmType		 OBJECT-TYPE
		SYNTAX					 BITS{ communication(0),qos(1),processing(2),equipment(3),environment(4)  }
		MAX-ACCESS			 read-create
		STATUS					 current
		DESCRIPTION			 " -- "
		::=  { efdEntry  6 }


	efdAlarmSeverity		 OBJECT-TYPE
		SYNTAX					 BITS{ critical(0),major(1),minor(2),warn(3)  }
		MAX-ACCESS			 read-create
		STATUS					 current
		DESCRIPTION			 " -- "
		::=  { efdEntry  7 }


	efdAlarmSourceObject		 OBJECT-TYPE
		SYNTAX					 VariablePointer
		MAX-ACCESS			 read-create
		STATUS					 current
		DESCRIPTION			 " -- "
		::=  { efdEntry  8 }


	efdAlarmNo		 OBJECT-TYPE
		SYNTAX					 Integer32( -2147483648 .. 2147483647 )
		MAX-ACCESS			 read-create
		STATUS					 current
		DESCRIPTION			 " -- "
		::=  { efdEntry  9 }


	alarmNotificationNode		 OBJECT IDENTIFIER
		::=  { faultManagement  2 }


	alarmNotifications		 OBJECT IDENTIFIER
		::=  { alarmNotificationNode  1 }


	alarmNotify		 NOTIFICATION-TYPE
		OBJECTS					 { alarmNotiNEType,alarmNotiNEID,alarmNotiNEVer,alarmNotiRequestID,alarmNotiCauseNo,alarmNotiSubCauseNo,alarmNotiSeverity,alarmNotiType,alarmNotiReportType,alarmNotiTime,alarmNotiItfNCauseNo,alarmNotiProblemSourceObject,alarmNotiReportSourceObject,alarmNotiThreshHold,alarmNotiCurrentValue,alarmNotiAddition,alarmNotiMaintenanceStatus,alarmAssociatedRequestId,alarmNotiRepeatTimes,alarmAffectNetworkMode }
		STATUS					 current
		DESCRIPTION			 " -- "
		::=  { alarmNotifications  1 }


	alarmNotificationObjects		 OBJECT IDENTIFIER
		::=  { alarmNotificationNode  2 }


	alarmNotiNEType		 OBJECT-TYPE
		SYNTAX					 INTEGER{ unknown(0),tlb60a(2),emb5116tdlte(3),emb5132tdlte(4),emb5116(5),mme(21),pgw(22),sgw(23),pcrf(24),pcscf(41),icscf(42),scscf(43),sbc(44),bgcf(45),as(46)  }
		MAX-ACCESS			 accessible-for-notify
		STATUS					 current
		DESCRIPTION			 " -- "
		::=  { alarmNotificationObjects  1 }


	alarmNotiNEID		 OBJECT-TYPE
		SYNTAX					 Unsigned32( 0 .. 4294967295 )
		MAX-ACCESS			 accessible-for-notify
		STATUS					 current
		DESCRIPTION			 " -- "
		::=  { alarmNotificationObjects  2 }


	alarmNotiNEVer		 OBJECT-TYPE
		SYNTAX					 DisplayString( SIZE ( 1 .. 255 ) )
		MAX-ACCESS			 accessible-for-notify
		STATUS					 current
		DESCRIPTION			 " -- "
		::=  { alarmNotificationObjects  3 }


	alarmNotiRequestID		 OBJECT-TYPE
		SYNTAX					 Integer32( -2147483648 .. 2147483647 )
		MAX-ACCESS			 accessible-for-notify
		STATUS					 current
		DESCRIPTION			 " -- "
		::=  { alarmNotificationObjects  4 }


	alarmNotiCauseNo		 OBJECT-TYPE
		SYNTAX					 Integer32( 1 .. 2500|0 )
		MAX-ACCESS			 accessible-for-notify
		STATUS					 current
		DESCRIPTION			 " -- "
		::=  { alarmNotificationObjects  5 }


	alarmNotiSubCauseNo		 OBJECT-TYPE
		SYNTAX					 Integer32( 1 .. 255|0 )
		MAX-ACCESS			 accessible-for-notify
		STATUS					 current
		DESCRIPTION			 " -- "
		::=  { alarmNotificationObjects  6 }


	alarmNotiSeverity		 OBJECT-TYPE
		SYNTAX					 INTEGER{ critical(1),major(2),minor(3),warn(4),clear(6)  }
		MAX-ACCESS			 accessible-for-notify
		STATUS					 current
		DESCRIPTION			 " -- "
		::=  { alarmNotificationObjects  7 }


	alarmNotiType		 OBJECT-TYPE
		SYNTAX					 INTEGER{ communication(1),qos(2),processing(3),equipment(4),environment(5)  }
		MAX-ACCESS			 accessible-for-notify
		STATUS					 current
		DESCRIPTION			 " -- "
		::=  { alarmNotificationObjects  8 }


	alarmNotiReportType		 OBJECT-TYPE
		SYNTAX					 INTEGER{ statelessAlarmCreate(0),alarmCreate(1),alarmAutoClear(2),alarmProblemSourceResetClear(3),alarmProblemSourceConfigDeletClear(4),alarmReportSourceResetClear(5),alarmReportSourceConfigDeleteClear(6),alarmManualClear(7)  }
		MAX-ACCESS			 accessible-for-notify
		STATUS					 current
		DESCRIPTION			 " -- "
		::=  { alarmNotificationObjects  9 }


	alarmNotiTime		 OBJECT-TYPE
		SYNTAX					 DateAndTime
		MAX-ACCESS			 accessible-for-notify
		STATUS					 current
		DESCRIPTION			 " -- "
		::=  { alarmNotificationObjects  10 }


	alarmNotiItfNCauseNo		 OBJECT-TYPE
		SYNTAX					 Integer32( 0 .. 1000 )
		MAX-ACCESS			 accessible-for-notify
		STATUS					 current
		DESCRIPTION			 " -- "
		::=  { alarmNotificationObjects  11 }


	alarmNotiProblemSourceObject		 OBJECT-TYPE
		SYNTAX					 VariablePointer
		MAX-ACCESS			 accessible-for-notify
		STATUS					 current
		DESCRIPTION			 " -- "
		::=  { alarmNotificationObjects  12 }


	alarmNotiReportSourceObject		 OBJECT-TYPE
		SYNTAX					 VariablePointer
		MAX-ACCESS			 accessible-for-notify
		STATUS					 current
		DESCRIPTION			 " -- "
		::=  { alarmNotificationObjects  13 }


	alarmNotiThreshHold		 OBJECT-TYPE
		SYNTAX					 Integer32( -2147483648 .. 2147483647 )
		MAX-ACCESS			 accessible-for-notify
		STATUS					 current
		DESCRIPTION			 " -- "
		::=  { alarmNotificationObjects  14 }


	alarmNotiCurrentValue		 OBJECT-TYPE
		SYNTAX					 Integer32( -2147483648 .. 2147483647 )
		MAX-ACCESS			 accessible-for-notify
		STATUS					 current
		DESCRIPTION			 " -- "
		::=  { alarmNotificationObjects  15 }


	alarmNotiAddition		 OBJECT-TYPE
		SYNTAX					 DisplayString( SIZE ( 1 .. 255 ) )
		MAX-ACCESS			 accessible-for-notify
		STATUS					 current
		DESCRIPTION			 " -- "
		::=  { alarmNotificationObjects  16 }


	alarmNotiMaintenanceStatus		 OBJECT-TYPE
		SYNTAX					 INTEGER{ waitingToSetup(0),settingup(1),inMaintenance(2),inService(3)  }
		MAX-ACCESS			 accessible-for-notify
		STATUS					 current
		DESCRIPTION			 " -- "
		::=  { alarmNotificationObjects  17 }


	alarmAssociatedRequestId		 OBJECT-TYPE
		SYNTAX					 Unsigned32Array
		MAX-ACCESS			 accessible-for-notify
		STATUS					 current
		DESCRIPTION			 " -- "
		::=  { alarmNotificationObjects  18 }


	alarmNotiRepeatTimes		 OBJECT-TYPE
		SYNTAX					 Integer32( -2147483648 .. 2147483647 )
		MAX-ACCESS			 accessible-for-notify
		STATUS					 current
		DESCRIPTION			 " -- "
		::=  { alarmNotificationObjects  19 }


	alarmAffectNetworkMode		 OBJECT-TYPE
		SYNTAX					 INTEGER{ invalid(0),tds(1),tdl(2),all(3)  }
		MAX-ACCESS			 accessible-for-notify
		STATUS					 current
		DESCRIPTION			 " -- "
		::=  { alarmNotificationObjects  20 }


	activeAlarmManagement		 OBJECT IDENTIFIER
		::=  { faultManagement  3 }


	activeAlarmTable		 OBJECT-TYPE
		SYNTAX					 SEQUENCE  OF	 ActiveAlarmEntry
		MAX-ACCESS			 not-accessible
		STATUS					 current
		DESCRIPTION			 " -- "
		::=  { activeAlarmManagement  1 }


	activeAlarmEntry		 OBJECT-TYPE
		SYNTAX					 ActiveAlarmEntry
		MAX-ACCESS			 not-accessible
		STATUS					 current
		DESCRIPTION			 " -- "
		INDEX						{ activeAlarmRequestID }
		::=  { activeAlarmTable  1 }


	ActiveAlarmEntry		 ::=  SEQUENCE {
		activeAlarmRequestID					Integer32,
		activeAlarmRowStatus					RowStatus,
		activeAlarmCauseNo					Integer32,
		activeAlarmSubCauseNo					Integer32,
		activeAlarmSeverity					INTEGER,
		activeAlarmType					INTEGER,
		activeAlarmReportType					INTEGER,
		activeAlarmTime					DateAndTime,
		activeAlarmItfNCauseNo					Integer32,
		activeAlarmProblemSourceObject					VariablePointer,
		activeAlarmReportSourceObject					VariablePointer,
		activeAlarmThreshHold					Integer32,
		activeAlarmCurrentValue					Integer32,
		activeAlarmAddition					DisplayString,
		activeAlarmMaintenanceStatus					INTEGER,
		activeAlarmAssociatedRequestId					Unsigned32Array,
		activeAlarmRepeatTimes					Integer32,
		activeAlarmAffectNetworkMode					INTEGER
		}


	activeAlarmRequestID		 OBJECT-TYPE
		SYNTAX					 Integer32( 1 .. 2147483647 )
		MAX-ACCESS			 not-accessible
		STATUS					 current
		DESCRIPTION			 " -- "
		::=  { activeAlarmEntry  1 }


	activeAlarmRowStatus		 OBJECT-TYPE
		SYNTAX					 RowStatus
		MAX-ACCESS			 read-write
		STATUS					 current
		DESCRIPTION			 " -- "
		::=  { activeAlarmEntry  2 }


	activeAlarmCauseNo		 OBJECT-TYPE
		SYNTAX					 Integer32( 1 .. 2500 )
		MAX-ACCESS			 read-only
		STATUS					 current
		DESCRIPTION			 " -- "
		::=  { activeAlarmEntry  3 }


	activeAlarmSubCauseNo		 OBJECT-TYPE
		SYNTAX					 Integer32( 1 .. 255|0 )
		MAX-ACCESS			 read-only
		STATUS					 current
		DESCRIPTION			 " -- "
		::=  { activeAlarmEntry  4 }


	activeAlarmSeverity		 OBJECT-TYPE
		SYNTAX					 INTEGER{ critical(1),major(2),minor(3),warn(4),clear(6)  }
		MAX-ACCESS			 read-only
		STATUS					 current
		DESCRIPTION			 " -- "
		::=  { activeAlarmEntry  5 }


	activeAlarmType		 OBJECT-TYPE
		SYNTAX					 INTEGER{ communication(1),qos(2),processing(3),equipment(4),environment(5)  }
		MAX-ACCESS			 read-only
		STATUS					 current
		DESCRIPTION			 " -- "
		::=  { activeAlarmEntry  6 }


	activeAlarmReportType		 OBJECT-TYPE
		SYNTAX					 INTEGER{ statelessAlarmCreate(0),alarmCreate(1),alarmAutoClear(2),alarmProblemSourceResetClear(3),alarmProblemSourceConfigDeletClear(4),alarmReportSourceResetClear(5),alarmReportSourceConfigDeleteClear(6),alarmManualClear(7)  }
		MAX-ACCESS			 read-only
		STATUS					 current
		DESCRIPTION			 " -- "
		::=  { activeAlarmEntry  7 }


	activeAlarmTime		 OBJECT-TYPE
		SYNTAX					 DateAndTime
		MAX-ACCESS			 read-only
		STATUS					 current
		DESCRIPTION			 " -- "
		::=  { activeAlarmEntry  8 }


	activeAlarmItfNCauseNo		 OBJECT-TYPE
		SYNTAX					 Integer32( 0 .. 1000 )
		MAX-ACCESS			 read-only
		STATUS					 current
		DESCRIPTION			 " -- "
		::=  { activeAlarmEntry  9 }


	activeAlarmProblemSourceObject		 OBJECT-TYPE
		SYNTAX					 VariablePointer
		MAX-ACCESS			 read-only
		STATUS					 current
		DESCRIPTION			 " -- "
		::=  { activeAlarmEntry  10 }


	activeAlarmReportSourceObject		 OBJECT-TYPE
		SYNTAX					 VariablePointer
		MAX-ACCESS			 read-only
		STATUS					 current
		DESCRIPTION			 " -- "
		::=  { activeAlarmEntry  11 }


	activeAlarmThreshHold		 OBJECT-TYPE
		SYNTAX					 Integer32( -2147483648 .. 2147483647 )
		MAX-ACCESS			 read-only
		STATUS					 current
		DESCRIPTION			 " -- "
		::=  { activeAlarmEntry  12 }


	activeAlarmCurrentValue		 OBJECT-TYPE
		SYNTAX					 Integer32( -2147483648 .. 2147483647 )
		MAX-ACCESS			 read-only
		STATUS					 current
		DESCRIPTION			 " -- "
		::=  { activeAlarmEntry  13 }


	activeAlarmAddition		 OBJECT-TYPE
		SYNTAX					 DisplayString( SIZE ( 1 .. 255 ) )
		MAX-ACCESS			 read-only
		STATUS					 current
		DESCRIPTION			 " -- "
		::=  { activeAlarmEntry  14 }


	activeAlarmMaintenanceStatus		 OBJECT-TYPE
		SYNTAX					 INTEGER{ waitingToSetup(0),settingup(1),inMaintenance(2),inService(3)  }
		MAX-ACCESS			 read-only
		STATUS					 current
		DESCRIPTION			 " -- "
		::=  { activeAlarmEntry  15 }


	activeAlarmAssociatedRequestId		 OBJECT-TYPE
		SYNTAX					 Unsigned32Array
		MAX-ACCESS			 read-only
		STATUS					 current
		DESCRIPTION			 " -- "
		::=  { activeAlarmEntry  16 }


	activeAlarmRepeatTimes		 OBJECT-TYPE
		SYNTAX					 Integer32( -2147483648 .. 2147483647 )
		MAX-ACCESS			 read-only
		STATUS					 current
		DESCRIPTION			 " -- "
		::=  { activeAlarmEntry  17 }


	activeAlarmAffectNetworkMode		 OBJECT-TYPE
		SYNTAX					 INTEGER{ invalid(0),tds(1),tdl(2),all(3)  }
		MAX-ACCESS			 read-only
		STATUS					 current
		DESCRIPTION			 " -- "
		::=  { activeAlarmEntry  18 }


	alarmInfo		 OBJECT IDENTIFIER
		::=  { faultManagement  6 }


	alarmCauseVersion		 OBJECT-TYPE
		SYNTAX					 DisplayString( SIZE ( 1 .. 150 ) )
		MAX-ACCESS			 read-only
		STATUS					 current
		DESCRIPTION			 " -- "
		::=  { alarmInfo  1 }


	alarmStatelessAlarmCompressionInterval		 OBJECT-TYPE
		SYNTAX					 Integer32( 1 .. 1800 )
		MAX-ACCESS			 read-write
		STATUS					 current
		DESCRIPTION			 " -- "
		::=  { alarmInfo  2 }


	alarmStatefulAlarmSends		 OBJECT-TYPE
		SYNTAX					 Integer32( -2147483648 .. 2147483647 )
		MAX-ACCESS			 read-only
		STATUS					 current
		DESCRIPTION			 " -- "
		::=  { alarmInfo  3 }


	alarmStatelessSends		 OBJECT-TYPE
		SYNTAX					 Integer32( -2147483648 .. 2147483647 )
		MAX-ACCESS			 read-only
		STATUS					 current
		DESCRIPTION			 " -- "
		::=  { alarmInfo  4 }


	alarmBox		 OBJECT IDENTIFIER
		::=  { faultManagement  7 }


	alarmBoxTable		 OBJECT-TYPE
		SYNTAX					 SEQUENCE  OF	 AlarmBoxEntry
		MAX-ACCESS			 not-accessible
		STATUS					 current
		DESCRIPTION			 " -- "
		::=  { alarmBox  1 }


	alarmBoxEntry		 OBJECT-TYPE
		SYNTAX					 AlarmBoxEntry
		MAX-ACCESS			 not-accessible
		STATUS					 current
		DESCRIPTION			 " -- "
		INDEX						{ alarmBoxIndex }
		::=  { alarmBoxTable  1 }


	AlarmBoxEntry		 ::=  SEQUENCE {
		alarmBoxIndex					Integer32,
		alarmBoxRowStatus					RowStatus,
		alarmBoxMute					INTEGER,
		alarmBoxVersion					DisplayString,
		alarmBoxManufacturer					DisplayString,
		alarmBoxStatus					INTEGER,
		alarmBoxMStatus					INTEGER,
		alarmBoxAttr					Unsigned32,
		alarmBoxOption					Unsigned32,
		alarmBoxCmd					INTEGER
		}


	alarmBoxIndex		 OBJECT-TYPE
		SYNTAX					 Integer32( 1 .. 1 )
		MAX-ACCESS			 not-accessible
		STATUS					 current
		DESCRIPTION			 " -- "
		::=  { alarmBoxEntry  1 }


	alarmBoxRowStatus		 OBJECT-TYPE
		SYNTAX					 RowStatus
		MAX-ACCESS			 read-create
		STATUS					 current
		DESCRIPTION			 " -- "
		::=  { alarmBoxEntry  2 }


	alarmBoxMute		 OBJECT-TYPE
		SYNTAX					 INTEGER{ no(0),yes(1)  }
		MAX-ACCESS			 read-create
		STATUS					 current
		DESCRIPTION			 " -- "
		::=  { alarmBoxEntry  3 }


	alarmBoxVersion		 OBJECT-TYPE
		SYNTAX					 DisplayString( SIZE ( 1 .. 255 ) )
		MAX-ACCESS			 read-only
		STATUS					 current
		DESCRIPTION			 " -- "
		::=  { alarmBoxEntry  4 }


	alarmBoxManufacturer		 OBJECT-TYPE
		SYNTAX					 DisplayString( SIZE ( 1 .. 255 ) )
		MAX-ACCESS			 read-only
		STATUS					 current
		DESCRIPTION			 " -- "
		::=  { alarmBoxEntry  5 }


	alarmBoxStatus		 OBJECT-TYPE
		SYNTAX					 INTEGER{ normal(0),abnormal(1)  }
		MAX-ACCESS			 read-only
		STATUS					 current
		DESCRIPTION			 " -- "
		::=  { alarmBoxEntry  6 }


	alarmBoxMStatus		 OBJECT-TYPE
		SYNTAX					 INTEGER{ enable(0),disable(1)  }
		MAX-ACCESS			 read-only
		STATUS					 current
		DESCRIPTION			 " -- "
		::=  { alarmBoxEntry  7 }


	alarmBoxAttr		 OBJECT-TYPE
		SYNTAX					 Unsigned32( 0 .. 4294967295 )
		MAX-ACCESS			 read-create
		STATUS					 current
		DESCRIPTION			 " -- "
		::=  { alarmBoxEntry  8 }


	alarmBoxOption		 OBJECT-TYPE
		SYNTAX					 Unsigned32( 0 .. 4294967295 )
		MAX-ACCESS			 read-create
		STATUS					 current
		DESCRIPTION			 " -- "
		::=  { alarmBoxEntry  9 }


	alarmBoxCmd		 OBJECT-TYPE
		SYNTAX					 INTEGER{ reboot(1),enable(2),disable(3),selftest(4)  }
		MAX-ACCESS			 read-write
		STATUS					 current
		DESCRIPTION			 " -- "
		::=  { alarmBoxEntry  10 }


	fileManagement		 OBJECT IDENTIFIER
		::=  { lteCommon  2 }


	fileServer		 OBJECT IDENTIFIER
		::=  { fileManagement  1 }


	ftpServerTable		 OBJECT-TYPE
		SYNTAX					 SEQUENCE  OF	 FtpServerEntry
		MAX-ACCESS			 not-accessible
		STATUS					 current
		DESCRIPTION			 " -- "
		::=  { fileServer  1 }


	ftpServerEntry		 OBJECT-TYPE
		SYNTAX					 FtpServerEntry
		MAX-ACCESS			 not-accessible
		STATUS					 current
		DESCRIPTION			 " -- "
		INDEX						{ ftpServerManangerIndex }
		::=  { ftpServerTable  1 }


	FtpServerEntry		 ::=  SEQUENCE {
		ftpServerManangerIndex					Integer32,
		ftpServerRowStatus					RowStatus,
		ftpServerManagerType					INTEGER,
		ftpServerInetAddrType					InetAddressType,
		ftpServerInetAddr					InetAddress,
		ftpServerPerformanceDirectory					DisplayString,
		ftpServerAlarmDirectory					DisplayString,
		ftpServerSoftwareDirectory					DisplayString,
		ftpServerConfigurationDirectory					DisplayString,
		ftpServerLogDirectory					DisplayString,
		ftpServerLoginName					DisplayString,
		ftpServerPassword					DisplayString
		}


	ftpServerManangerIndex		 OBJECT-TYPE
		SYNTAX					 Integer32( 0 .. 16 )
		MAX-ACCESS			 not-accessible
		STATUS					 current
		DESCRIPTION			 " -- "
		::=  { ftpServerEntry  1 }


	ftpServerRowStatus		 OBJECT-TYPE
		SYNTAX					 RowStatus
		MAX-ACCESS			 read-create
		STATUS					 current
		DESCRIPTION			 " -- "
		::=  { ftpServerEntry  2 }


	ftpServerManagerType		 OBJECT-TYPE
		SYNTAX					 INTEGER{ omc(1),dci(2),lmt(4),rnc(8)  }
		MAX-ACCESS			 read-create
		STATUS					 current
		DESCRIPTION			 " -- "
		::=  { ftpServerEntry  3 }


	ftpServerInetAddrType		 OBJECT-TYPE
		SYNTAX					 InetAddressType
		MAX-ACCESS			 read-create
		STATUS					 current
		DESCRIPTION			 " -- "
		::=  { ftpServerEntry  4 }


	ftpServerInetAddr		 OBJECT-TYPE
		SYNTAX					 InetAddress
		MAX-ACCESS			 read-create
		STATUS					 current
		DESCRIPTION			 " -- "
		::=  { ftpServerEntry  5 }


	ftpServerPerformanceDirectory		 OBJECT-TYPE
		SYNTAX					 DisplayString( SIZE ( 1 .. 199 ) )
		MAX-ACCESS			 read-create
		STATUS					 current
		DESCRIPTION			 " -- "
		::=  { ftpServerEntry  6 }


	ftpServerAlarmDirectory		 OBJECT-TYPE
		SYNTAX					 DisplayString( SIZE ( 1 .. 199 ) )
		MAX-ACCESS			 read-create
		STATUS					 current
		DESCRIPTION			 " -- "
		::=  { ftpServerEntry  7 }


	ftpServerSoftwareDirectory		 OBJECT-TYPE
		SYNTAX					 DisplayString( SIZE ( 1 .. 199 ) )
		MAX-ACCESS			 read-create
		STATUS					 current
		DESCRIPTION			 " -- "
		::=  { ftpServerEntry  8 }


	ftpServerConfigurationDirectory		 OBJECT-TYPE
		SYNTAX					 DisplayString( SIZE ( 1 .. 199 ) )
		MAX-ACCESS			 read-create
		STATUS					 current
		DESCRIPTION			 " -- "
		::=  { ftpServerEntry  9 }


	ftpServerLogDirectory		 OBJECT-TYPE
		SYNTAX					 DisplayString( SIZE ( 1 .. 199 ) )
		MAX-ACCESS			 read-create
		STATUS					 current
		DESCRIPTION			 " -- "
		::=  { ftpServerEntry  10 }


	ftpServerLoginName		 OBJECT-TYPE
		SYNTAX					 DisplayString( SIZE ( 1 .. 255 ) )
		MAX-ACCESS			 read-create
		STATUS					 current
		DESCRIPTION			 " -- "
		::=  { ftpServerEntry  11 }


	ftpServerPassword		 OBJECT-TYPE
		SYNTAX					 DisplayString( SIZE ( 1 .. 255 ) )
		MAX-ACCESS			 read-create
		STATUS					 current
		DESCRIPTION			 " -- "
		::=  { ftpServerEntry  12 }


	fileTransferControl		 OBJECT IDENTIFIER
		::=  { fileManagement  2 }


	fileTransIDInfo		 OBJECT IDENTIFIER
		::=  { fileTransferControl  1 }


	fileTransNextAvailableIDForOMC		 OBJECT-TYPE
		SYNTAX					 Integer32( 1 .. 20 )
		MAX-ACCESS			 read-only
		STATUS					 current
		DESCRIPTION			 " -- "
		::=  { fileTransIDInfo  1 }


	fileTransNextAvailableIDForOthers		 OBJECT-TYPE
		SYNTAX					 Integer32( 1 .. 20 )
		MAX-ACCESS			 read-only
		STATUS					 current
		DESCRIPTION			 " -- "
		::=  { fileTransIDInfo  2 }


	fileTransTable		 OBJECT-TYPE
		SYNTAX					 SEQUENCE  OF	 FileTransEntry
		MAX-ACCESS			 not-accessible
		STATUS					 current
		DESCRIPTION			 " -- "
		::=  { fileTransferControl  2 }


	fileTransEntry		 OBJECT-TYPE
		SYNTAX					 FileTransEntry
		MAX-ACCESS			 not-accessible
		STATUS					 current
		DESCRIPTION			 " -- "
		INDEX						{ fileTransID }
		::=  { fileTransTable  1 }


	FileTransEntry		 ::=  SEQUENCE {
		fileTransID					Integer32,
		fileTransRowStatus					RowStatus,
		fileTransType					INTEGER,
		fileTransIndicator					INTEGER,
		fileTransNEDirectory					DisplayString,
		fileTransFTPDirectory					DisplayString,
		fileTransFileName					DisplayString,
		fileTransState					INTEGER,
		fileTransPercent					Unsigned32
		}


	fileTransID		 OBJECT-TYPE
		SYNTAX					 Integer32( 1 .. 20 )
		MAX-ACCESS			 not-accessible
		STATUS					 current
		DESCRIPTION			 " -- "
		::=  { fileTransEntry  1 }


	fileTransRowStatus		 OBJECT-TYPE
		SYNTAX					 RowStatus
		MAX-ACCESS			 read-create
		STATUS					 current
		DESCRIPTION			 " -- "
		::=  { fileTransEntry  2 }


	fileTransType		 OBJECT-TYPE
		SYNTAX					 INTEGER{ operationLog(1),alterLog(2),omSecurityLog(3),alarmLog(4),omKeyLog(5),updateLog(6),debugLog(7),statelessAlarmLog(8),eventLog(9),userLog(10),cfgDataConsistency(11),stateDataConsistency(12),dataConsistency(13),curConfig(14),planConfig(15),equipSoftwarePack(16),coldPatchPack(17),hotPatchPack(18),rruEquipSoftwarePack(19),relantEquipSoftwarePack(20),enviromentEquipSoftwarePackPack(21),gpsEquipSoftwarePack(22),equip1588SoftwarePack(23),cnssEquipSoftwarePackPack(24),generalFile(25),lmtMDBFile(26),activeAlarmFile(27),performanceFile(28),cfgPatchFile(29),snapshotFile(30),cdlFile(31),sctpLogFile(32),dumpLogFile(33),ocuEquipSoftwarePack(34),servicecdlFile(35),mroFile(36),mrsFile(37),mreFile(38),mmlOpLog(39),mmlPmFile(40),gtsaLog(41),iotLog(42),traceUserLog(43),pcapLog(44),immediatMdt(45),loggedMdt(46),rlf(47),ripLog(48),rncDisa(49),raeFile(50),riaLog(51),slotRipFile(52),symbolRipFile(53),secStatelessAlarmLog(54)  }
		MAX-ACCESS			 read-create
		STATUS					 current
		DESCRIPTION			 " -- "
		::=  { fileTransEntry  3 }


	fileTransIndicator		 OBJECT-TYPE
		SYNTAX					 INTEGER{ upload(1),download(2)  }
		MAX-ACCESS			 read-create
		STATUS					 current
		DESCRIPTION			 " -- "
		::=  { fileTransEntry  4 }


	fileTransNEDirectory		 OBJECT-TYPE
		SYNTAX					 DisplayString( SIZE ( 1 .. 199 ) )
		MAX-ACCESS			 read-create
		STATUS					 current
		DESCRIPTION			 " -- "
		::=  { fileTransEntry  5 }


	fileTransFTPDirectory		 OBJECT-TYPE
		SYNTAX					 DisplayString( SIZE ( 1 .. 199 ) )
		MAX-ACCESS			 read-create
		STATUS					 current
		DESCRIPTION			 " -- "
		::=  { fileTransEntry  6 }


	fileTransFileName		 OBJECT-TYPE
		SYNTAX					 DisplayString( SIZE ( 1 .. 69 ) )
		MAX-ACCESS			 read-create
		STATUS					 current
		DESCRIPTION			 " -- "
		::=  { fileTransEntry  7 }


	fileTransState		 OBJECT-TYPE
		SYNTAX					 INTEGER{ transfering(1),unzipping(2)  }
		MAX-ACCESS			 read-only
		STATUS					 current
		DESCRIPTION			 " -- "
		::=  { fileTransEntry  8 }


	fileTransPercent		 OBJECT-TYPE
		SYNTAX					 Unsigned32( 0 .. 4294967295 )
		MAX-ACCESS			 read-only
		STATUS					 current
		DESCRIPTION			 " -- "
		::=  { fileTransEntry  9 }


	fileTransNotificationNode		 OBJECT IDENTIFIER
		::=  { fileTransferControl  3 }


	fileTransResultNotifications		 OBJECT IDENTIFIER
		::=  { fileTransNotificationNode  1 }


	fileTransNotification		 NOTIFICATION-TYPE
		OBJECTS					 { fileTransNotiNEType,fileTransNotiNEID,fileTransNotiFileTaskId,fileTransNotiFileType,fileTransNotiFileName,fileTransNotiIndicator,fileTransNotiResult,fileTransNotiErrorCode,fileTransNotiTime }
		STATUS					 current
		DESCRIPTION			 " -- "
		::=  { fileTransResultNotifications  1 }


	fileTransObjects		 OBJECT IDENTIFIER
		::=  { fileTransNotificationNode  2 }


	fileTransNotiNEType		 OBJECT-TYPE
		SYNTAX					 INTEGER{ unknown(0),tlb60a(2),emb5116tdlte(3),emb5132tdlte(4),emb5116(5),epc(21),ims(41)  }
		MAX-ACCESS			 accessible-for-notify
		STATUS					 current
		DESCRIPTION			 " -- "
		::=  { fileTransObjects  1 }


	fileTransNotiNEID		 OBJECT-TYPE
		SYNTAX					 Unsigned32( 0 .. 4294967295 )
		MAX-ACCESS			 accessible-for-notify
		STATUS					 current
		DESCRIPTION			 " -- "
		::=  { fileTransObjects  2 }


	fileTransNotiFileTaskId		 OBJECT-TYPE
		SYNTAX					 Integer32( 1 .. 30 )
		MAX-ACCESS			 accessible-for-notify
		STATUS					 current
		DESCRIPTION			 " -- "
		::=  { fileTransObjects  3 }


	fileTransNotiFileType		 OBJECT-TYPE
		SYNTAX					 INTEGER{ operationLog(1),alterLog(2),omSecurityLog(3),alarmLog(4),omKeyLog(5),updateLog(6),debugLog(7),statelessAlarmLog(8),eventLog(9),userLog(10),cfgDataConsistency(11),stateDataConsistency(12),dataConsistency(13),curConfig(14),planConfig(15),equipSoftwarePack(16),coldPatchPack(17),hotPatchPack(18),rruEquipSoftwarePack(19),relantEquipSoftwarePack(20),enviromentEquipSoftwarePackPack(21),gpsEquipSoftwarePack(22),equip1588SoftwarePack(23),cnssEquipSoftwarePackPack(24),generalFile(25),lmtMDBFile(26),activeAlarmFile(27),performanceFile(28),cfgPatchFile(29),snapshotFile(30),cdlFile(31),sctpLogFile(32),dumpLogFile(33),ocuEquipSoftwarePack(34),servicecdlFile(35),mroFile(36),mrsFile(37),mreFile(38),mmlOpLog(39),mmlPmFile(40),iotLog(42),traceUserLog(43),immediatMdt(45),loggedMdt(46),rlf(47),ripLog(48),rncDisa(49),raeFile(50),riaLog(51),slotRipFile(52),symbolRipFile(53),secStatelessAlarmLog(54)  }
		MAX-ACCESS			 accessible-for-notify
		STATUS					 current
		DESCRIPTION			 " -- "
		::=  { fileTransObjects  4 }


	fileTransNotiFileName		 OBJECT-TYPE
		SYNTAX					 DisplayString( SIZE ( 1 .. 255 ) )
		MAX-ACCESS			 accessible-for-notify
		STATUS					 current
		DESCRIPTION			 " -- "
		::=  { fileTransObjects  5 }


	fileTransNotiIndicator		 OBJECT-TYPE
		SYNTAX					 INTEGER{ upload(1),download(2)  }
		MAX-ACCESS			 accessible-for-notify
		STATUS					 current
		DESCRIPTION			 " -- "
		::=  { fileTransObjects  6 }


	fileTransNotiResult		 OBJECT-TYPE
		SYNTAX					 INTEGER{ success(0),failure(3)  }
		MAX-ACCESS			 accessible-for-notify
		STATUS					 current
		DESCRIPTION			 " -- "
		::=  { fileTransObjects  7 }


	fileTransNotiErrorCode		 OBJECT-TYPE
		SYNTAX					 INTEGER{ success(0),busy(1),typeError(2),filenameError(3),ftpServerConnectError(4),userNameOrPasswordError(5),ftpPathError(6),fileNotExistOrCreatError(7),timeout(8),downloadForbidden(9),unzipError(10),verError(11),other(100)  }
		MAX-ACCESS			 accessible-for-notify
		STATUS					 current
		DESCRIPTION			 " -- "
		::=  { fileTransObjects  8 }


	fileTransNotiTime		 OBJECT-TYPE
		SYNTAX					 DateAndTime
		MAX-ACCESS			 accessible-for-notify
		STATUS					 current
		DESCRIPTION			 " -- "
		::=  { fileTransObjects  9 }


	fileControl		 OBJECT IDENTIFIER
		::=  { fileManagement  5 }


	fileTypeLimitTable		 OBJECT-TYPE
		SYNTAX					 SEQUENCE  OF	 FileTypeLimitEntry
		MAX-ACCESS			 not-accessible
		STATUS					 current
		DESCRIPTION			 " -- "
		::=  { fileControl  1 }


	fileTypeLimitEntry		 OBJECT-TYPE
		SYNTAX					 FileTypeLimitEntry
		MAX-ACCESS			 not-accessible
		STATUS					 current
		DESCRIPTION			 " -- "
		INDEX						{ fileTypeLimitIndex }
		::=  { fileTypeLimitTable  1 }


	FileTypeLimitEntry		 ::=  SEQUENCE {
		fileTypeLimitIndex					INTEGER,
		fileTypeLimitRowStatus					RowStatus,
		fileTypeLimitFileMaxPreservingDay					Integer32,
		fileTypeLimitSingleFileMaxBytes					Integer32,
		fileTypeLimitFileMaxNumber					Integer32
		}


	fileTypeLimitIndex		 OBJECT-TYPE
		SYNTAX					 INTEGER{ performanceFile(28)  }
		MAX-ACCESS			 not-accessible
		STATUS					 current
		DESCRIPTION			 " -- "
		::=  { fileTypeLimitEntry  1 }


	fileTypeLimitRowStatus		 OBJECT-TYPE
		SYNTAX					 RowStatus
		MAX-ACCESS			 read-create
		STATUS					 current
		DESCRIPTION			 " -- "
		::=  { fileTypeLimitEntry  2 }


	fileTypeLimitFileMaxPreservingDay		 OBJECT-TYPE
		SYNTAX					 Integer32( 1 .. 7 )
		MAX-ACCESS			 read-create
		STATUS					 current
		DESCRIPTION			 " -- "
		::=  { fileTypeLimitEntry  3 }


	fileTypeLimitSingleFileMaxBytes		 OBJECT-TYPE
		SYNTAX					 Integer32( 1 .. 5120 )
		MAX-ACCESS			 read-create
		STATUS					 current
		DESCRIPTION			 " -- "
		::=  { fileTypeLimitEntry  4 }


	fileTypeLimitFileMaxNumber		 OBJECT-TYPE
		SYNTAX					 Integer32( 1 .. 10 )
		MAX-ACCESS			 read-create
		STATUS					 current
		DESCRIPTION			 " -- "
		::=  { fileTypeLimitEntry  5 }


	fileDeleteControl		 OBJECT IDENTIFIER
		::=  { fileControl  2 }


	fileDeleteFileTrigger		 OBJECT-TYPE
		SYNTAX					 INTEGER{ off(0),on(1)  }
		MAX-ACCESS			 read-write
		STATUS					 current
		DESCRIPTION			 " -- "
		::=  { fileDeleteControl  1 }


	fileDeleteConfigFileName		 OBJECT-TYPE
		SYNTAX					 DisplayString( SIZE ( 1 .. 200 ) )
		MAX-ACCESS			 read-write
		STATUS					 current
		DESCRIPTION			 " -- "
		::=  { fileDeleteControl  2 }


	fileClearFolderTrigger		 OBJECT-TYPE
		SYNTAX					 INTEGER{ off(0),on(1)  }
		MAX-ACCESS			 read-write
		STATUS					 current
		DESCRIPTION			 " -- "
		::=  { fileDeleteControl  3 }


	fileClearFolderName		 OBJECT-TYPE
		SYNTAX					 DisplayString( SIZE ( 1 .. 200 ) )
		MAX-ACCESS			 read-write
		STATUS					 current
		DESCRIPTION			 " -- "
		::=  { fileDeleteControl  4 }


	fileUploadTable		 OBJECT-TYPE
		SYNTAX					 SEQUENCE  OF	 FileUploadEntry
		MAX-ACCESS			 not-accessible
		STATUS					 current
		DESCRIPTION			 " -- "
		::=  { fileManagement  6 }


	fileUploadEntry		 OBJECT-TYPE
		SYNTAX					 FileUploadEntry
		MAX-ACCESS			 not-accessible
		STATUS					 current
		DESCRIPTION			 " -- "
		INDEX						{ fileUpIndex }
		::=  { fileUploadTable  1 }


	FileUploadEntry		 ::=  SEQUENCE {
		fileUpIndex					Integer32,
		fileUpRowStatus					RowStatus,
		fileUpTransType					INTEGER,
		fileUpStartTime					DateAndTime,
		fileUpEndTime					DateAndTime,
		fileUpFTPDirectory					DisplayString,
		fileUpState					INTEGER
		}


	fileUpIndex		 OBJECT-TYPE
		SYNTAX					 Integer32( 1 .. 10 )
		MAX-ACCESS			 not-accessible
		STATUS					 current
		DESCRIPTION			 " -- "
		::=  { fileUploadEntry  1 }


	fileUpRowStatus		 OBJECT-TYPE
		SYNTAX					 RowStatus
		MAX-ACCESS			 read-create
		STATUS					 current
		DESCRIPTION			 " -- "
		::=  { fileUploadEntry  2 }


	fileUpTransType		 OBJECT-TYPE
		SYNTAX					 INTEGER{ operationLog(1),alterLog(2),omSecurityLog(3),alarmLog(4),omKeyLog(5),updateLog(6),debugLog(7),statelessAlarmLog(8),eventLog(9),userLog(10),cfgDataConsistency(11),stateDataConsistency(12),dataConsistency(13),curConfig(14),planConfig(15),equipSoftwarePack(16),coldPatchPack(17),hotPatchPack(18),rruEquipSoftwarePack(19),relantEquipSoftwarePack(20),enviromentEquipSoftwarePackPack(21),gpsEquipSoftwarePack(22),equip1588SoftwarePack(23),cnssEquipSoftwarePackPack(24),generalFile(25),lmtMDBFile(26),activeAlarmFile(27),performanceFile(28),cfgPatchFile(29),snapshotFile(30),cdlFile(31),sctpLogFile(32),dumpLogFile(33),ocuEquipSoftwarePack(34),servicecdlFile(35),mroFile(36),mrsFile(37),mreFile(38),mmlOpLog(39),mmlPmFile(40),raeFile(50),secStatelessAlarmLog(54)  }
		MAX-ACCESS			 read-create
		STATUS					 current
		DESCRIPTION			 " -- "
		::=  { fileUploadEntry  3 }


	fileUpStartTime		 OBJECT-TYPE
		SYNTAX					 DateAndTime
		MAX-ACCESS			 read-create
		STATUS					 current
		DESCRIPTION			 " -- "
		::=  { fileUploadEntry  4 }


	fileUpEndTime		 OBJECT-TYPE
		SYNTAX					 DateAndTime
		MAX-ACCESS			 read-create
		STATUS					 current
		DESCRIPTION			 " -- "
		::=  { fileUploadEntry  5 }


	fileUpFTPDirectory		 OBJECT-TYPE
		SYNTAX					 DisplayString( SIZE ( 1 .. 199 ) )
		MAX-ACCESS			 read-create
		STATUS					 current
		DESCRIPTION			 " -- "
		::=  { fileUploadEntry  6 }


	fileUpState		 OBJECT-TYPE
		SYNTAX					 INTEGER{ unProcess(1),processing(2),processed(3)  }
		MAX-ACCESS			 read-only
		STATUS					 current
		DESCRIPTION			 " -- "
		::=  { fileUploadEntry  7 }


	fileAutoUploadInfo		 OBJECT IDENTIFIER
		::=  { fileManagement  7 }


	fileAutoUpInetAddrType		 OBJECT-TYPE
		SYNTAX					 InetAddressType
		MAX-ACCESS			 read-write
		STATUS					 current
		DESCRIPTION			 " -- "
		::=  { fileAutoUploadInfo  1 }


	fileAutoUpInetAddr		 OBJECT-TYPE
		SYNTAX					 InetAddress
		MAX-ACCESS			 read-write
		STATUS					 current
		DESCRIPTION			 " -- "
		::=  { fileAutoUploadInfo  2 }


	fileAutoUpftpServerLoginName		 OBJECT-TYPE
		SYNTAX					 DisplayString( SIZE ( 1 .. 255 ) )
		MAX-ACCESS			 read-write
		STATUS					 current
		DESCRIPTION			 " -- "
		::=  { fileAutoUploadInfo  3 }


	fileAutoUpftpServerPassword		 OBJECT-TYPE
		SYNTAX					 DisplayString( SIZE ( 1 .. 255 ) )
		MAX-ACCESS			 read-write
		STATUS					 current
		DESCRIPTION			 " -- "
		::=  { fileAutoUploadInfo  4 }


	fileAutoUpFTPDirectory		 OBJECT-TYPE
		SYNTAX					 DisplayString( SIZE ( 1 .. 199 ) )
		MAX-ACCESS			 read-write
		STATUS					 current
		DESCRIPTION			 " -- "
		::=  { fileAutoUploadInfo  5 }


	fileAutoUpInterval		 OBJECT-TYPE
		SYNTAX					 INTEGER{ min0(0),min15(15),min30(30),min60(60),min720(720),min1440(1440)  }
		MAX-ACCESS			 read-write
		STATUS					 current
		DESCRIPTION			 " -- "
		::=  { fileAutoUploadInfo  6 }


	programManagement		 OBJECT IDENTIFIER
		::=  { lteCommon  3 }


	softwareNB		 OBJECT IDENTIFIER
		::=  { programManagement  1 }


	softwarePackPlanTable		 OBJECT-TYPE
		SYNTAX					 SEQUENCE  OF	 SoftwarePackPlanEntry
		MAX-ACCESS			 not-accessible
		STATUS					 current
		DESCRIPTION			 " -- "
		::=  { softwareNB  1 }


	softwarePackPlanEntry		 OBJECT-TYPE
		SYNTAX					 SoftwarePackPlanEntry
		MAX-ACCESS			 not-accessible
		STATUS					 current
		DESCRIPTION			 " -- "
		INDEX						{ swPackPlanTypeIndex }
		::=  { softwarePackPlanTable  1 }


	SoftwarePackPlanEntry		 ::=  SEQUENCE {
		swPackPlanTypeIndex					INTEGER,
		swPackPlanRowStatus					RowStatus,
		swPackPlanPackName					DisplayString,
		swPackPlanVendor					DisplayString,
		swPackPlanVersion					DisplayString,
		swPackPlanDownloadIndicator					INTEGER,
		swPackPlanScheduleDownloadTime					DateAndTime,
		swPackPlanDownloadDirectory					DisplayString,
		swPackPlanActivateIndicator					INTEGER,
		swPackPlanScheduleActivateTime					DateAndTime,
		swPackPlanRelyVesion					DisplayString,
		swPackPlanFwActiveIndicator					INTEGER,
		swPackPlanUpgradeState					INTEGER,
		swPackPlanUpgradePercent					Unsigned32,
		swPackPlanUpgradeResult					BITS,
		swPackPlanOpEndingIndicator					INTEGER,
		swPackPlanSubPackNumber					Unsigned32,
		swPackPlanRstOpEndingIndTrg					INTEGER,
		swPackPlanFwUpgEndingIndicator					INTEGER
		}


	swPackPlanTypeIndex		 OBJECT-TYPE
		SYNTAX					 INTEGER{ equip(1),coldPatch(2),hotPatch(3)  }
		MAX-ACCESS			 not-accessible
		STATUS					 current
		DESCRIPTION			 " -- "
		::=  { softwarePackPlanEntry  1 }


	swPackPlanRowStatus		 OBJECT-TYPE
		SYNTAX					 RowStatus
		MAX-ACCESS			 read-create
		STATUS					 current
		DESCRIPTION			 " -- "
		::=  { softwarePackPlanEntry  2 }


	swPackPlanPackName		 OBJECT-TYPE
		SYNTAX					 DisplayString( SIZE ( 1 .. 60 ) )
		MAX-ACCESS			 read-create
		STATUS					 current
		DESCRIPTION			 " -- "
		::=  { softwarePackPlanEntry  3 }


	swPackPlanVendor		 OBJECT-TYPE
		SYNTAX					 DisplayString( SIZE ( 1 .. 60 ) )
		MAX-ACCESS			 read-create
		STATUS					 current
		DESCRIPTION			 " -- "
		::=  { softwarePackPlanEntry  4 }


	swPackPlanVersion		 OBJECT-TYPE
		SYNTAX					 DisplayString( SIZE ( 1 .. 60 ) )
		MAX-ACCESS			 read-create
		STATUS					 current
		DESCRIPTION			 " -- "
		::=  { softwarePackPlanEntry  5 }


	swPackPlanDownloadIndicator		 OBJECT-TYPE
		SYNTAX					 INTEGER{ doNothing(0),instantDownload(1),scheduleDownload(2),forcedDownload(3)  }
		MAX-ACCESS			 read-create
		STATUS					 current
		DESCRIPTION			 " -- "
		::=  { softwarePackPlanEntry  6 }


	swPackPlanScheduleDownloadTime		 OBJECT-TYPE
		SYNTAX					 DateAndTime
		MAX-ACCESS			 read-create
		STATUS					 current
		DESCRIPTION			 " -- "
		::=  { softwarePackPlanEntry  7 }


	swPackPlanDownloadDirectory		 OBJECT-TYPE
		SYNTAX					 DisplayString( SIZE ( 1 .. 200 ) )
		MAX-ACCESS			 read-create
		STATUS					 current
		DESCRIPTION			 " -- "
		::=  { softwarePackPlanEntry  8 }


	swPackPlanActivateIndicator		 OBJECT-TYPE
		SYNTAX					 INTEGER{ doNothing(0),instantActivate(1),scheduleActivate(2),instantDeactivate(3),scheduleDeactivate(4),forceActive(5),manualActivate(6)  }
		MAX-ACCESS			 read-create
		STATUS					 current
		DESCRIPTION			 " -- "
		::=  { softwarePackPlanEntry  9 }


	swPackPlanScheduleActivateTime		 OBJECT-TYPE
		SYNTAX					 DateAndTime
		MAX-ACCESS			 read-create
		STATUS					 current
		DESCRIPTION			 " -- "
		::=  { softwarePackPlanEntry  10 }


	swPackPlanRelyVesion		 OBJECT-TYPE
		SYNTAX					 DisplayString( SIZE ( 1 .. 60 ) )
		MAX-ACCESS			 read-create
		STATUS					 current
		DESCRIPTION			 " -- "
		::=  { softwarePackPlanEntry  11 }


	swPackPlanFwActiveIndicator		 OBJECT-TYPE
		SYNTAX					 INTEGER{ notactive(0),active(1)  }
		MAX-ACCESS			 read-create
		STATUS					 current
		DESCRIPTION			 " -- "
		::=  { softwarePackPlanEntry  12 }


	swPackPlanUpgradeState		 OBJECT-TYPE
		SYNTAX					 INTEGER{ doNothing(0),downloading(1),unzipping(2),activating(3),synchronization(4)  }
		MAX-ACCESS			 read-only
		STATUS					 current
		DESCRIPTION			 " -- "
		::=  { softwarePackPlanEntry  13 }


	swPackPlanUpgradePercent		 OBJECT-TYPE
		SYNTAX					 Unsigned32( 0 .. 4294967295 )
		MAX-ACCESS			 read-only
		STATUS					 current
		DESCRIPTION			 " -- "
		::=  { softwarePackPlanEntry  14 }


	swPackPlanUpgradeResult		 OBJECT-TYPE
		SYNTAX					 BITS{ slot0(0),slot1(1),slot2(2),slot3(3),slot4(4),slot5(5),slot6(6),slot7(7),slot8(8),slot9(9),slot10(10),slot11(11),slot12(12),slot13(13),slot14(14),slot15(15),slot16(16)  }
		MAX-ACCESS			 read-only
		STATUS					 current
		DESCRIPTION			 " -- "
		::=  { softwarePackPlanEntry  15 }


	swPackPlanOpEndingIndicator		 OBJECT-TYPE
		SYNTAX					 INTEGER{ false(0),true(1)  }
		MAX-ACCESS			 read-only
		STATUS					 current
		DESCRIPTION			 " -- "
		::=  { softwarePackPlanEntry  16 }


	swPackPlanSubPackNumber		 OBJECT-TYPE
		SYNTAX					 Unsigned32( 0 .. 4294967295 )
		MAX-ACCESS			 read-create
		STATUS					 current
		DESCRIPTION			 " -- "
		::=  { softwarePackPlanEntry  17 }


	swPackPlanRstOpEndingIndTrg		 OBJECT-TYPE
		SYNTAX					 INTEGER{ false(0),true(1)  }
		MAX-ACCESS			 read-write
		STATUS					 current
		DESCRIPTION			 " -- "
		::=  { softwarePackPlanEntry  18 }


	swPackPlanFwUpgEndingIndicator		 OBJECT-TYPE
		SYNTAX					 INTEGER{ false(0),true(1)  }
		MAX-ACCESS			 read-only
		STATUS					 current
		DESCRIPTION			 " -- "
		::=  { softwarePackPlanEntry  22 }


	peripheralPackPlanTable		 OBJECT-TYPE
		SYNTAX					 SEQUENCE  OF	 PeripheralPackPlanEntry
		MAX-ACCESS			 not-accessible
		STATUS					 current
		DESCRIPTION			 " -- "
		::=  { softwareNB  2 }


	peripheralPackPlanEntry		 OBJECT-TYPE
		SYNTAX					 PeripheralPackPlanEntry
		MAX-ACCESS			 not-accessible
		STATUS					 current
		DESCRIPTION			 " -- "
		INDEX						{ peripheralPackPlanTypeIndex,peripheralPackPlanVendorIndex }
		::=  { peripheralPackPlanTable  1 }


	PeripheralPackPlanEntry		 ::=  SEQUENCE {
		peripheralPackPlanTypeIndex					INTEGER,
		peripheralPackPlanVendorIndex					Integer32,
		peripheralPackPlanRowStatus					RowStatus,
		peripheralPackPlanPackName					DisplayString,
		peripheralPackPlanVendor					DisplayString,
		peripheralPackPlanVersion					DisplayString,
		peripheralPackPlanDownloadIndicator					INTEGER,
		peripheralPackPlanScheduleDownloadTime					DateAndTime,
		peripheralPackPlanDownloadDirectory					DisplayString,
		peripheralPackPlanActivateIndicator					INTEGER,
		peripheralPackPlanScheduleActivateTime					DateAndTime,
		peripheralPackPlanRelyVesion					DisplayString,
		peripheralPackPlanUpgradeState					INTEGER,
		peripheralPackPlanUpgradePercent					Unsigned32,
		peripheralPackPlanUpgradeResult1					BITS,
		peripheralPackPlanUpgradeResult2					BITS,
		peripheralPackPlanOpEndingIndicator					INTEGER,
		peripheralPackPlanSubPackNumber					Unsigned32,
		peripheralPackPlanRstOpEndingIndTrg					INTEGER,
		peripheralPackPlanPackType					INTEGER,
		peripheralPackPlanUpgradeResult3					BITS,
		peripheralPackPlanUpgradeResult4					BITS,
		peripheralPackPlanUpgradeResult5					BITS,
		peripheralPackPlanUpgradeResult6					BITS,
		peripheralPackPlanUpgradeResult7					BITS,
		peripheralPackPlanUpgradeResult8					BITS
		}


	peripheralPackPlanTypeIndex		 OBJECT-TYPE
		SYNTAX					 INTEGER{ rruEquip(1),relantEquip(2),enviromentEuip(3),gpsEuip(4),pt1588Equip(5),cnssEquip(6),ocuEquip(7),rruColdPatch(8)  }
		MAX-ACCESS			 not-accessible
		STATUS					 current
		DESCRIPTION			 " -- "
		::=  { peripheralPackPlanEntry  1 }


	peripheralPackPlanVendorIndex		 OBJECT-TYPE
		SYNTAX					 Integer32( 1 .. 1 )
		MAX-ACCESS			 not-accessible
		STATUS					 current
		DESCRIPTION			 " -- "
		::=  { peripheralPackPlanEntry  2 }


	peripheralPackPlanRowStatus		 OBJECT-TYPE
		SYNTAX					 RowStatus
		MAX-ACCESS			 read-create
		STATUS					 current
		DESCRIPTION			 " -- "
		::=  { peripheralPackPlanEntry  3 }


	peripheralPackPlanPackName		 OBJECT-TYPE
		SYNTAX					 DisplayString( SIZE ( 1 .. 60 ) )
		MAX-ACCESS			 read-create
		STATUS					 current
		DESCRIPTION			 " -- "
		::=  { peripheralPackPlanEntry  4 }


	peripheralPackPlanVendor		 OBJECT-TYPE
		SYNTAX					 DisplayString( SIZE ( 1 .. 60 ) )
		MAX-ACCESS			 read-create
		STATUS					 current
		DESCRIPTION			 " -- "
		::=  { peripheralPackPlanEntry  5 }


	peripheralPackPlanVersion		 OBJECT-TYPE
		SYNTAX					 DisplayString( SIZE ( 1 .. 60 ) )
		MAX-ACCESS			 read-create
		STATUS					 current
		DESCRIPTION			 " -- "
		::=  { peripheralPackPlanEntry  6 }


	peripheralPackPlanDownloadIndicator		 OBJECT-TYPE
		SYNTAX					 INTEGER{ doNothing(0),instantDownload(1),scheduleDownload(2),forcedDownload(3)  }
		MAX-ACCESS			 read-create
		STATUS					 current
		DESCRIPTION			 " -- "
		::=  { peripheralPackPlanEntry  7 }


	peripheralPackPlanScheduleDownloadTime		 OBJECT-TYPE
		SYNTAX					 DateAndTime
		MAX-ACCESS			 read-create
		STATUS					 current
		DESCRIPTION			 " -- "
		::=  { peripheralPackPlanEntry  8 }


	peripheralPackPlanDownloadDirectory		 OBJECT-TYPE
		SYNTAX					 DisplayString( SIZE ( 1 .. 200 ) )
		MAX-ACCESS			 read-create
		STATUS					 current
		DESCRIPTION			 " -- "
		::=  { peripheralPackPlanEntry  9 }


	peripheralPackPlanActivateIndicator		 OBJECT-TYPE
		SYNTAX					 INTEGER{ doNothing(0),instantActivate(1),scheduleActivate(2),manualActivate(3)  }
		MAX-ACCESS			 read-create
		STATUS					 current
		DESCRIPTION			 " -- "
		::=  { peripheralPackPlanEntry  10 }


	peripheralPackPlanScheduleActivateTime		 OBJECT-TYPE
		SYNTAX					 DateAndTime
		MAX-ACCESS			 read-create
		STATUS					 current
		DESCRIPTION			 " -- "
		::=  { peripheralPackPlanEntry  11 }


	peripheralPackPlanRelyVesion		 OBJECT-TYPE
		SYNTAX					 DisplayString( SIZE ( 1 .. 59 ) )
		MAX-ACCESS			 read-create
		STATUS					 current
		DESCRIPTION			 " -- "
		::=  { peripheralPackPlanEntry  12 }


	peripheralPackPlanUpgradeState		 OBJECT-TYPE
		SYNTAX					 INTEGER{ doNothing(0),downloading(1),unzipping(2),activating(3),synchronization(4)  }
		MAX-ACCESS			 read-only
		STATUS					 current
		DESCRIPTION			 " -- "
		::=  { peripheralPackPlanEntry  13 }


	peripheralPackPlanUpgradePercent		 OBJECT-TYPE
		SYNTAX					 Unsigned32( 0 .. 4294967295 )
		MAX-ACCESS			 read-only
		STATUS					 current
		DESCRIPTION			 " -- "
		::=  { peripheralPackPlanEntry  14 }


	peripheralPackPlanUpgradeResult1		 OBJECT-TYPE
		SYNTAX					 BITS{ entity0(0),entity1(1),entity2(2),entity3(3),entity4(4),entity5(5),entity6(6),entity7(7),entity8(8),entity9(9),entity10(10),entity11(11),entity12(12),entity13(13),entity14(14),entity15(15),entity16(16),entity17(17),entity18(18),entity19(19),entity20(20),entity21(21),entity22(22),entity23(23),entity24(24),entity25(25),entity26(26),entity27(27),entity28(28),entity29(29),entity30(30),entity31(31)  }
		MAX-ACCESS			 read-only
		STATUS					 current
		DESCRIPTION			 " -- "
		::=  { peripheralPackPlanEntry  15 }


	peripheralPackPlanUpgradeResult2		 OBJECT-TYPE
		SYNTAX					 BITS{ entity32(0),entity33(1),entity34(2),entity35(3),entity36(4),entity37(5),entity38(6),entity39(7),entity40(8),entity41(9),entity42(10),entity43(11),entity44(12),entity45(13),entity46(14),entity47(15),entity48(16),entity49(17),entity50(18),entity51(19),entity52(20),entity53(21),entity54(22),entity55(23),entity56(24),entity57(25),entity58(26),entity59(27),entity60(28),entity61(29),entity62(30),entity63(31)  }
		MAX-ACCESS			 read-only
		STATUS					 current
		DESCRIPTION			 " -- "
		::=  { peripheralPackPlanEntry  16 }


	peripheralPackPlanOpEndingIndicator		 OBJECT-TYPE
		SYNTAX					 INTEGER{ false(0),true(1)  }
		MAX-ACCESS			 read-only
		STATUS					 current
		DESCRIPTION			 " -- "
		::=  { peripheralPackPlanEntry  17 }


	peripheralPackPlanSubPackNumber		 OBJECT-TYPE
		SYNTAX					 Unsigned32( 0 .. 4294967295 )
		MAX-ACCESS			 read-create
		STATUS					 current
		DESCRIPTION			 " -- "
		::=  { peripheralPackPlanEntry  18 }


	peripheralPackPlanRstOpEndingIndTrg		 OBJECT-TYPE
		SYNTAX					 INTEGER{ false(0),true(1)  }
		MAX-ACCESS			 read-write
		STATUS					 current
		DESCRIPTION			 " -- "
		::=  { peripheralPackPlanEntry  19 }


	peripheralPackPlanPackType		 OBJECT-TYPE
		SYNTAX					 INTEGER{ ret(1),rae(2)  }
		MAX-ACCESS			 read-create
		STATUS					 current
		DESCRIPTION			 " -- "
		::=  { peripheralPackPlanEntry  20 }


	peripheralPackPlanUpgradeResult3		 OBJECT-TYPE
		SYNTAX					 BITS{ entity64(0),entity65(1),entity66(2),entity67(3),entity68(4),entity69(5),entity70(6),entity71(7),entity72(8),entity73(9),entity74(10),entity75(11),entity76(12),entity77(13),entity78(14),entity79(15),entity80(16),entity81(17),entity82(18),entity83(19),entity84(20),entity85(21),entity86(22),entity87(23),entity88(24),entity89(25),entity90(26),entity91(27),entity92(28),entity93(29),entity94(30),entity95(31)  }
		MAX-ACCESS			 read-only
		STATUS					 current
		DESCRIPTION			 " -- "
		::=  { peripheralPackPlanEntry  24 }


	peripheralPackPlanUpgradeResult4		 OBJECT-TYPE
		SYNTAX					 BITS{ entity96(0),entity97(1),entity98(2),entity99(3),entity100(4),entity101(5),entity102(6),entity103(7),entity104(8),entity105(9),entity106(10),entity107(11),entity108(12),entity109(13),entity110(14),entity111(15),entity112(16),entity113(17),entity114(18),entity115(19),entity116(20),entity117(21),entity118(22),entity119(23),entity120(24),entity121(25),entity122(26),entity123(27),entity124(28),entity125(29),entity126(30),entity127(31)  }
		MAX-ACCESS			 read-only
		STATUS					 current
		DESCRIPTION			 " -- "
		::=  { peripheralPackPlanEntry  25 }


	peripheralPackPlanUpgradeResult5		 OBJECT-TYPE
		SYNTAX					 BITS{ entity128(0),entity129(1),entity130(2),entity131(3),entity132(4),entity133(5),entity134(6),entity135(7),entity136(8),entity137(9),entity138(10),entity139(11),entity140(12),entity141(13),entity142(14),entity143(15),entity144(16),entity145(17),entity146(18),entity147(19),entity148(20),entity149(21),entity150(22),entity151(23),entity152(24),entity153(25),entity154(26),entity155(27),entity156(28),entity157(29),entity158(30),entity159(31)  }
		MAX-ACCESS			 read-only
		STATUS					 current
		DESCRIPTION			 " -- "
		::=  { peripheralPackPlanEntry  26 }


	peripheralPackPlanUpgradeResult6		 OBJECT-TYPE
		SYNTAX					 BITS{ entity160(0),entity161(1),entity162(2),entity163(3),entity164(4),entity165(5),entity166(6),entity167(7),entity168(8),entity169(9),entity170(10),entity171(11),entity172(12),entity173(13),entity174(14),entity175(15),entity176(16),entity177(17),entity178(18),entity179(19),entity180(20),entity181(21),entity182(22),entity183(23),entity184(24),entity185(25),entity186(26),entity187(27),entity188(28),entity189(29),entity190(30),entity191(31)  }
		MAX-ACCESS			 read-only
		STATUS					 current
		DESCRIPTION			 " -- "
		::=  { peripheralPackPlanEntry  27 }


	peripheralPackPlanUpgradeResult7		 OBJECT-TYPE
		SYNTAX					 BITS{ entity192(0),entity193(1),entity194(2),entity195(3),entity196(4),entity197(5),entity198(6),entity199(7),entity200(8),entity201(9),entity202(10),entity203(11),entity204(12),entity205(13),entity206(14),entity207(15),entity208(16),entity209(17),entity210(18),entity211(19),entity212(20),entity213(21),entity214(22),entity215(23),entity216(24),entity217(25),entity218(26),entity219(27),entity220(28),entity221(29),entity222(30),entity223(31)  }
		MAX-ACCESS			 read-only
		STATUS					 current
		DESCRIPTION			 " -- "
		::=  { peripheralPackPlanEntry  28 }


	peripheralPackPlanUpgradeResult8		 OBJECT-TYPE
		SYNTAX					 BITS{ entity224(0),entity225(1),entity226(2),entity227(3),entity228(4),entity229(5),entity230(6),entity231(7),entity232(8),entity233(9),entity234(10),entity235(11),entity236(12),entity237(13),entity238(14),entity239(15),entity240(16),entity241(17),entity242(18),entity243(19),entity244(20),entity245(21),entity246(22),entity247(23),entity248(24),entity249(25),entity250(26),entity251(27),entity252(28),entity253(29),entity254(30),entity255(31)  }
		MAX-ACCESS			 read-only
		STATUS					 current
		DESCRIPTION			 " -- "
		::=  { peripheralPackPlanEntry  29 }


	softwarePackRunningTable		 OBJECT-TYPE
		SYNTAX					 SEQUENCE  OF	 SoftwarePackRunningEntry
		MAX-ACCESS			 not-accessible
		STATUS					 current
		DESCRIPTION			 " -- "
		::=  { softwareNB  3 }


	softwarePackRunningEntry		 OBJECT-TYPE
		SYNTAX					 SoftwarePackRunningEntry
		MAX-ACCESS			 not-accessible
		STATUS					 current
		DESCRIPTION			 " -- "
		INDEX						{ swPackRunningTypeIndex }
		::=  { softwarePackRunningTable  1 }


	SoftwarePackRunningEntry		 ::=  SEQUENCE {
		swPackRunningTypeIndex					INTEGER,
		swPackRunningRowStatus					RowStatus,
		swPackRunningVersion					DisplayString,
		swPackRunningDownloadTime					DateAndTime,
		swPackRunningDownloadDirectory					DisplayString,
		swPackRunningRelyVesion					DisplayString,
		swPackRunningZipType					DisplayString,
		swPackRunningDetailVersion					DisplayString
		}


	swPackRunningTypeIndex		 OBJECT-TYPE
		SYNTAX					 INTEGER{ equip(1),coldPatch(2),hotPatch(3)  }
		MAX-ACCESS			 not-accessible
		STATUS					 current
		DESCRIPTION			 " -- "
		::=  { softwarePackRunningEntry  1 }


	swPackRunningRowStatus		 OBJECT-TYPE
		SYNTAX					 RowStatus
		MAX-ACCESS			 read-only
		STATUS					 current
		DESCRIPTION			 " -- "
		::=  { softwarePackRunningEntry  2 }


	swPackRunningVersion		 OBJECT-TYPE
		SYNTAX					 DisplayString( SIZE ( 1 .. 59 ) )
		MAX-ACCESS			 read-only
		STATUS					 current
		DESCRIPTION			 " -- "
		::=  { softwarePackRunningEntry  3 }


	swPackRunningDownloadTime		 OBJECT-TYPE
		SYNTAX					 DateAndTime
		MAX-ACCESS			 read-only
		STATUS					 current
		DESCRIPTION			 " -- "
		::=  { softwarePackRunningEntry  4 }


	swPackRunningDownloadDirectory		 OBJECT-TYPE
		SYNTAX					 DisplayString( SIZE ( 1 .. 199 ) )
		MAX-ACCESS			 read-only
		STATUS					 current
		DESCRIPTION			 " -- "
		::=  { softwarePackRunningEntry  5 }


	swPackRunningRelyVesion		 OBJECT-TYPE
		SYNTAX					 DisplayString( SIZE ( 1 .. 59 ) )
		MAX-ACCESS			 read-only
		STATUS					 current
		DESCRIPTION			 " -- "
		::=  { softwarePackRunningEntry  6 }


	swPackRunningZipType		 OBJECT-TYPE
		SYNTAX					 DisplayString( SIZE ( 1 .. 59 ) )
		MAX-ACCESS			 read-only
		STATUS					 current
		DESCRIPTION			 " -- "
		::=  { softwarePackRunningEntry  7 }


	swPackRunningDetailVersion		 OBJECT-TYPE
		SYNTAX					 DisplayString( SIZE ( 1 .. 59 ) )
		MAX-ACCESS			 read-only
		STATUS					 current
		DESCRIPTION			 " -- "
		::=  { softwarePackRunningEntry  8 }


	peripheralPackRunningTable		 OBJECT-TYPE
		SYNTAX					 SEQUENCE  OF	 PeripheralPackRunningEntry
		MAX-ACCESS			 not-accessible
		STATUS					 current
		DESCRIPTION			 " -- "
		::=  { softwareNB  4 }


	peripheralPackRunningEntry		 OBJECT-TYPE
		SYNTAX					 PeripheralPackRunningEntry
		MAX-ACCESS			 not-accessible
		STATUS					 current
		DESCRIPTION			 " -- "
		INDEX						{ peripheralPackRunningTypeIndex,peripheralPackRunningVendorIndex }
		::=  { peripheralPackRunningTable  1 }


	PeripheralPackRunningEntry		 ::=  SEQUENCE {
		peripheralPackRunningTypeIndex					INTEGER,
		peripheralPackRunningVendorIndex					Integer32,
		peripheralPackRunningRowStatus					RowStatus,
		peripheralPackRunningVersion					DisplayString,
		peripheralPackRunningDownloadTime					DateAndTime,
		peripheralPackRunningDownloadDirectory					DisplayString,
		peripheralPackRunningZipType					DisplayString,
		peripheralPackRunningDetailVersion					DisplayString
		}


	peripheralPackRunningTypeIndex		 OBJECT-TYPE
		SYNTAX					 INTEGER{ rruEquip(1),relantEquip(2),enviromentEuip(3),gpsEuip(4),pt1588Equip(5),cnssEquip(6),ocuEquip(7),rruColdPatch(8)  }
		MAX-ACCESS			 not-accessible
		STATUS					 current
		DESCRIPTION			 " -- "
		::=  { peripheralPackRunningEntry  1 }


	peripheralPackRunningVendorIndex		 OBJECT-TYPE
		SYNTAX					 Integer32( 1 .. 1 )
		MAX-ACCESS			 not-accessible
		STATUS					 current
		DESCRIPTION			 " -- "
		::=  { peripheralPackRunningEntry  2 }


	peripheralPackRunningRowStatus		 OBJECT-TYPE
		SYNTAX					 RowStatus
		MAX-ACCESS			 read-only
		STATUS					 current
		DESCRIPTION			 " -- "
		::=  { peripheralPackRunningEntry  3 }


	peripheralPackRunningVersion		 OBJECT-TYPE
		SYNTAX					 DisplayString( SIZE ( 1 .. 59 ) )
		MAX-ACCESS			 read-only
		STATUS					 current
		DESCRIPTION			 " -- "
		::=  { peripheralPackRunningEntry  4 }


	peripheralPackRunningDownloadTime		 OBJECT-TYPE
		SYNTAX					 DateAndTime
		MAX-ACCESS			 read-only
		STATUS					 current
		DESCRIPTION			 " -- "
		::=  { peripheralPackRunningEntry  5 }


	peripheralPackRunningDownloadDirectory		 OBJECT-TYPE
		SYNTAX					 DisplayString( SIZE ( 1 .. 199 ) )
		MAX-ACCESS			 read-only
		STATUS					 current
		DESCRIPTION			 " -- "
		::=  { peripheralPackRunningEntry  6 }


	peripheralPackRunningZipType		 OBJECT-TYPE
		SYNTAX					 DisplayString( SIZE ( 1 .. 59 ) )
		MAX-ACCESS			 read-only
		STATUS					 current
		DESCRIPTION			 " -- "
		::=  { peripheralPackRunningEntry  7 }


	peripheralPackRunningDetailVersion		 OBJECT-TYPE
		SYNTAX					 DisplayString( SIZE ( 1 .. 59 ) )
		MAX-ACCESS			 read-only
		STATUS					 current
		DESCRIPTION			 " -- "
		::=  { peripheralPackRunningEntry  8 }


	softwarePackTable		 OBJECT-TYPE
		SYNTAX					 SEQUENCE  OF	 SoftwarePackEntry
		MAX-ACCESS			 not-accessible
		STATUS					 current
		DESCRIPTION			 " -- "
		::=  { softwareNB  5 }


	softwarePackEntry		 OBJECT-TYPE
		SYNTAX					 SoftwarePackEntry
		MAX-ACCESS			 not-accessible
		STATUS					 current
		DESCRIPTION			 " -- "
		INDEX						{ swPackTypeIndex,swPackVersionIndex }
		::=  { softwarePackTable  1 }


	SoftwarePackEntry		 ::=  SEQUENCE {
		swPackTypeIndex					INTEGER,
		swPackVersionIndex					Integer32,
		swPackRowStatus					RowStatus,
		swPackVersion					DisplayString,
		swPackDownloadTime					DateAndTime,
		swPackDirectory					DisplayString,
		swPackRelyVesion					DisplayString,
		swPackZipType					DisplayString,
		swPackDetailVersion					DisplayString
		}


	swPackTypeIndex		 OBJECT-TYPE
		SYNTAX					 INTEGER{ equip(1),coldPatch(2),hotPatch(3)  }
		MAX-ACCESS			 not-accessible
		STATUS					 current
		DESCRIPTION			 " -- "
		::=  { softwarePackEntry  1 }


	swPackVersionIndex		 OBJECT-TYPE
		SYNTAX					 Integer32( 1 .. 4 )
		MAX-ACCESS			 not-accessible
		STATUS					 current
		DESCRIPTION			 " -- "
		::=  { softwarePackEntry  2 }


	swPackRowStatus		 OBJECT-TYPE
		SYNTAX					 RowStatus
		MAX-ACCESS			 read-only
		STATUS					 current
		DESCRIPTION			 " -- "
		::=  { softwarePackEntry  3 }


	swPackVersion		 OBJECT-TYPE
		SYNTAX					 DisplayString( SIZE ( 1 .. 59 ) )
		MAX-ACCESS			 read-only
		STATUS					 current
		DESCRIPTION			 " -- "
		::=  { softwarePackEntry  4 }


	swPackDownloadTime		 OBJECT-TYPE
		SYNTAX					 DateAndTime
		MAX-ACCESS			 read-only
		STATUS					 current
		DESCRIPTION			 " -- "
		::=  { softwarePackEntry  5 }


	swPackDirectory		 OBJECT-TYPE
		SYNTAX					 DisplayString( SIZE ( 1 .. 199 ) )
		MAX-ACCESS			 read-only
		STATUS					 current
		DESCRIPTION			 " -- "
		::=  { softwarePackEntry  6 }


	swPackRelyVesion		 OBJECT-TYPE
		SYNTAX					 DisplayString( SIZE ( 1 .. 59 ) )
		MAX-ACCESS			 read-only
		STATUS					 current
		DESCRIPTION			 " -- "
		::=  { softwarePackEntry  7 }


	swPackZipType		 OBJECT-TYPE
		SYNTAX					 DisplayString( SIZE ( 1 .. 59 ) )
		MAX-ACCESS			 read-only
		STATUS					 current
		DESCRIPTION			 " -- "
		::=  { softwarePackEntry  8 }


	swPackDetailVersion		 OBJECT-TYPE
		SYNTAX					 DisplayString( SIZE ( 1 .. 59 ) )
		MAX-ACCESS			 read-only
		STATUS					 current
		DESCRIPTION			 " -- "
		::=  { softwarePackEntry  9 }


	peripheralPackTable		 OBJECT-TYPE
		SYNTAX					 SEQUENCE  OF	 PeripheralPackEntry
		MAX-ACCESS			 not-accessible
		STATUS					 current
		DESCRIPTION			 " -- "
		::=  { softwareNB  6 }


	peripheralPackEntry		 OBJECT-TYPE
		SYNTAX					 PeripheralPackEntry
		MAX-ACCESS			 not-accessible
		STATUS					 current
		DESCRIPTION			 " -- "
		INDEX						{ peripheralPackTypeIndex,peripheralPackVendorIndex,peripheralPackVersionIndex }
		::=  { peripheralPackTable  1 }


	PeripheralPackEntry		 ::=  SEQUENCE {
		peripheralPackTypeIndex					INTEGER,
		peripheralPackVendorIndex					Integer32,
		peripheralPackVersionIndex					Integer32,
		peripheralPackRowStatus					RowStatus,
		peripheralPackVersion					DisplayString,
		peripheralPackDownloadTime					DateAndTime,
		peripheralPackDirectory					DisplayString,
		peripheralPackZipType					DisplayString,
		peripheralPackDetailVersion					DisplayString
		}


	peripheralPackTypeIndex		 OBJECT-TYPE
		SYNTAX					 INTEGER{ rruEquip(1),relantEquip(2),enviromentEuip(3),gpsEuip(4),pt1588Equip(5),cnssEquip(6),ocuEquip(7)  }
		MAX-ACCESS			 not-accessible
		STATUS					 current
		DESCRIPTION			 " -- "
		::=  { peripheralPackEntry  1 }


	peripheralPackVendorIndex		 OBJECT-TYPE
		SYNTAX					 Integer32( 1 .. 2 )
		MAX-ACCESS			 not-accessible
		STATUS					 current
		DESCRIPTION			 " -- "
		::=  { peripheralPackEntry  2 }


	peripheralPackVersionIndex		 OBJECT-TYPE
		SYNTAX					 Integer32( 1 .. 2 )
		MAX-ACCESS			 not-accessible
		STATUS					 current
		DESCRIPTION			 " -- "
		::=  { peripheralPackEntry  3 }


	peripheralPackRowStatus		 OBJECT-TYPE
		SYNTAX					 RowStatus
		MAX-ACCESS			 read-only
		STATUS					 current
		DESCRIPTION			 " -- "
		::=  { peripheralPackEntry  4 }


	peripheralPackVersion		 OBJECT-TYPE
		SYNTAX					 DisplayString( SIZE ( 1 .. 59 ) )
		MAX-ACCESS			 read-only
		STATUS					 current
		DESCRIPTION			 " -- "
		::=  { peripheralPackEntry  5 }


	peripheralPackDownloadTime		 OBJECT-TYPE
		SYNTAX					 DateAndTime
		MAX-ACCESS			 read-only
		STATUS					 current
		DESCRIPTION			 " -- "
		::=  { peripheralPackEntry  6 }


	peripheralPackDirectory		 OBJECT-TYPE
		SYNTAX					 DisplayString( SIZE ( 1 .. 199 ) )
		MAX-ACCESS			 read-only
		STATUS					 current
		DESCRIPTION			 " -- "
		::=  { peripheralPackEntry  7 }


	peripheralPackZipType		 OBJECT-TYPE
		SYNTAX					 DisplayString( SIZE ( 1 .. 59 ) )
		MAX-ACCESS			 read-only
		STATUS					 current
		DESCRIPTION			 " -- "
		::=  { peripheralPackEntry  8 }


	peripheralPackDetailVersion		 OBJECT-TYPE
		SYNTAX					 DisplayString( SIZE ( 1 .. 59 ) )
		MAX-ACCESS			 read-only
		STATUS					 current
		DESCRIPTION			 " -- "
		::=  { peripheralPackEntry  9 }


	softwareFileTable		 OBJECT-TYPE
		SYNTAX					 SEQUENCE  OF	 SoftwareFileEntry
		MAX-ACCESS			 not-accessible
		STATUS					 current
		DESCRIPTION			 " -- "
		::=  { softwareNB  7 }


	softwareFileEntry		 OBJECT-TYPE
		SYNTAX					 SoftwareFileEntry
		MAX-ACCESS			 not-accessible
		STATUS					 current
		DESCRIPTION			 " -- "
		INDEX						{ swFilePackTypeIndex,swFilePackVersionIndex,swFileIndex }
		::=  { softwareFileTable  1 }


	SoftwareFileEntry		 ::=  SEQUENCE {
		swFilePackTypeIndex					INTEGER,
		swFilePackVersionIndex					Integer32,
		swFileIndex					Integer32,
		swFileRowStatus					RowStatus,
		swFileName					DisplayString,
		swFileVersion					DisplayString
		}


	swFilePackTypeIndex		 OBJECT-TYPE
		SYNTAX					 INTEGER{ equip(1),coldPatch(2),hotPatch(3)  }
		MAX-ACCESS			 not-accessible
		STATUS					 current
		DESCRIPTION			 " -- "
		::=  { softwareFileEntry  1 }


	swFilePackVersionIndex		 OBJECT-TYPE
		SYNTAX					 Integer32( 1 .. 2 )
		MAX-ACCESS			 not-accessible
		STATUS					 current
		DESCRIPTION			 " -- "
		::=  { softwareFileEntry  2 }


	swFileIndex		 OBJECT-TYPE
		SYNTAX					 Integer32( 1 .. 80 )
		MAX-ACCESS			 not-accessible
		STATUS					 current
		DESCRIPTION			 " -- "
		::=  { softwareFileEntry  3 }


	swFileRowStatus		 OBJECT-TYPE
		SYNTAX					 RowStatus
		MAX-ACCESS			 read-only
		STATUS					 current
		DESCRIPTION			 " -- "
		::=  { softwareFileEntry  4 }


	swFileName		 OBJECT-TYPE
		SYNTAX					 DisplayString( SIZE ( 1 .. 59 ) )
		MAX-ACCESS			 read-only
		STATUS					 current
		DESCRIPTION			 " -- "
		::=  { softwareFileEntry  5 }


	swFileVersion		 OBJECT-TYPE
		SYNTAX					 DisplayString( SIZE ( 1 .. 59 ) )
		MAX-ACCESS			 read-only
		STATUS					 current
		DESCRIPTION			 " -- "
		::=  { softwareFileEntry  6 }


	peripheralFileTable		 OBJECT-TYPE
		SYNTAX					 SEQUENCE  OF	 PeripheralFileEntry
		MAX-ACCESS			 not-accessible
		STATUS					 current
		DESCRIPTION			 " -- "
		::=  { softwareNB  8 }


	peripheralFileEntry		 OBJECT-TYPE
		SYNTAX					 PeripheralFileEntry
		MAX-ACCESS			 not-accessible
		STATUS					 current
		DESCRIPTION			 " -- "
		INDEX						{ peripheralFilePackTypeIndex,peripheralSoftwareFilePackVendorIndex,peripheralFilePackVersionIndex,peripheralFileIndex }
		::=  { peripheralFileTable  1 }


	PeripheralFileEntry		 ::=  SEQUENCE {
		peripheralFilePackTypeIndex					INTEGER,
		peripheralSoftwareFilePackVendorIndex					Integer32,
		peripheralFilePackVersionIndex					Integer32,
		peripheralFileIndex					Integer32,
		peripheralFileRowStatus					RowStatus,
		peripheralFileName					DisplayString,
		peripheralFileVersion					DisplayString
		}


	peripheralFilePackTypeIndex		 OBJECT-TYPE
		SYNTAX					 INTEGER{ rruEquip(1),relantEquip(2),enviromentEuip(3),gpsEuip(4),pt1588Equip(5),cnssEquip(6),ocuEquip(7)  }
		MAX-ACCESS			 not-accessible
		STATUS					 current
		DESCRIPTION			 " -- "
		::=  { peripheralFileEntry  1 }


	peripheralSoftwareFilePackVendorIndex		 OBJECT-TYPE
		SYNTAX					 Integer32( 1 .. 2 )
		MAX-ACCESS			 not-accessible
		STATUS					 current
		DESCRIPTION			 " -- "
		::=  { peripheralFileEntry  2 }


	peripheralFilePackVersionIndex		 OBJECT-TYPE
		SYNTAX					 Integer32( 1 .. 2 )
		MAX-ACCESS			 not-accessible
		STATUS					 current
		DESCRIPTION			 " -- "
		::=  { peripheralFileEntry  3 }


	peripheralFileIndex		 OBJECT-TYPE
		SYNTAX					 Integer32( 1 .. 50 )
		MAX-ACCESS			 not-accessible
		STATUS					 current
		DESCRIPTION			 " -- "
		::=  { peripheralFileEntry  4 }


	peripheralFileRowStatus		 OBJECT-TYPE
		SYNTAX					 RowStatus
		MAX-ACCESS			 read-only
		STATUS					 current
		DESCRIPTION			 " -- "
		::=  { peripheralFileEntry  5 }


	peripheralFileName		 OBJECT-TYPE
		SYNTAX					 DisplayString( SIZE ( 1 .. 59 ) )
		MAX-ACCESS			 read-only
		STATUS					 current
		DESCRIPTION			 " -- "
		::=  { peripheralFileEntry  6 }


	peripheralFileVersion		 OBJECT-TYPE
		SYNTAX					 DisplayString( SIZE ( 1 .. 59 ) )
		MAX-ACCESS			 read-only
		STATUS					 current
		DESCRIPTION			 " -- "
		::=  { peripheralFileEntry  7 }


	boardSoftwareFileTable		 OBJECT-TYPE
		SYNTAX					 SEQUENCE  OF	 BoardSoftwareFileEntry
		MAX-ACCESS			 not-accessible
		STATUS					 current
		DESCRIPTION			 " -- "
		::=  { softwareNB  9 }


	boardSoftwareFileEntry		 OBJECT-TYPE
		SYNTAX					 BoardSoftwareFileEntry
		MAX-ACCESS			 not-accessible
		STATUS					 current
		DESCRIPTION			 " -- "
		INDEX						{ boardSoftwareFileRackNo,boardSoftwareFileShelfNo,boardSoftwareFileSlotNo,boardSoftwareFileIndex }
		::=  { boardSoftwareFileTable  1 }


	BoardSoftwareFileEntry		 ::=  SEQUENCE {
		boardSoftwareFileRackNo					Integer32,
		boardSoftwareFileShelfNo					Integer32,
		boardSoftwareFileSlotNo					Integer32,
		boardSoftwareFileIndex					Integer32,
		boardSoftwareFileRowStatus					RowStatus,
		boardSoftwareFileName					DisplayString,
		boardSoftwareFileVersion					DisplayString
		}


	boardSoftwareFileRackNo		 OBJECT-TYPE
		SYNTAX					 Integer32( 0 .. 0 )
		MAX-ACCESS			 not-accessible
		STATUS					 current
		DESCRIPTION			 " -- "
		::=  { boardSoftwareFileEntry  1 }


	boardSoftwareFileShelfNo		 OBJECT-TYPE
		SYNTAX					 Integer32( 0 .. 0 )
		MAX-ACCESS			 not-accessible
		STATUS					 current
		DESCRIPTION			 " -- "
		::=  { boardSoftwareFileEntry  2 }


	boardSoftwareFileSlotNo		 OBJECT-TYPE
		SYNTAX					 Integer32( 0 .. 9 )
		MAX-ACCESS			 not-accessible
		STATUS					 current
		DESCRIPTION			 " -- "
		::=  { boardSoftwareFileEntry  3 }


	boardSoftwareFileIndex		 OBJECT-TYPE
		SYNTAX					 Integer32( 1 .. 50 )
		MAX-ACCESS			 not-accessible
		STATUS					 current
		DESCRIPTION			 " -- "
		::=  { boardSoftwareFileEntry  4 }


	boardSoftwareFileRowStatus		 OBJECT-TYPE
		SYNTAX					 RowStatus
		MAX-ACCESS			 read-only
		STATUS					 current
		DESCRIPTION			 " -- "
		::=  { boardSoftwareFileEntry  5 }


	boardSoftwareFileName		 OBJECT-TYPE
		SYNTAX					 DisplayString( SIZE ( 1 .. 59 ) )
		MAX-ACCESS			 read-only
		STATUS					 current
		DESCRIPTION			 " -- "
		::=  { boardSoftwareFileEntry  6 }


	boardSoftwareFileVersion		 OBJECT-TYPE
		SYNTAX					 DisplayString( SIZE ( 1 .. 59 ) )
		MAX-ACCESS			 read-only
		STATUS					 current
		DESCRIPTION			 " -- "
		::=  { boardSoftwareFileEntry  7 }


	softwarePackCustomerPlanTable		 OBJECT-TYPE
		SYNTAX					 SEQUENCE  OF	 SoftwarePackCustomerPlanEntry
		MAX-ACCESS			 not-accessible
		STATUS					 current
		DESCRIPTION			 " -- "
		::=  { softwareNB  10 }


	softwarePackCustomerPlanEntry		 OBJECT-TYPE
		SYNTAX					 SoftwarePackCustomerPlanEntry
		MAX-ACCESS			 not-accessible
		STATUS					 current
		DESCRIPTION			 " -- "
		INDEX						{ swPackCustomerPlanTypeIndex }
		::=  { softwarePackCustomerPlanTable  1 }


	SoftwarePackCustomerPlanEntry		 ::=  SEQUENCE {
		swPackCustomerPlanTypeIndex					INTEGER,
		swPackCustomerPlanRowStatus					RowStatus,
		swPackCustomerPlanPackName					DisplayString,
		swPackCustomerPlanVendor					DisplayString,
		swPackCustomerPlanVersion					DisplayString,
		swPackCustomerPlanDownloadIndicator					INTEGER,
		swPackCustomerPlanScheduleDownloadTime					DateAndTime,
		swPackCustomerPlanDownloadDirectory					DisplayString,
		swPackCustomerPlanActivateIndicator					INTEGER,
		swPackCustomerPlanScheduleActivateTime					DateAndTime,
		swPackCustomerPlanRelyVesion					DisplayString,
		swPackCustomerPlanFwActiveIndicator					INTEGER,
		swPackCustomerPlanUpgradeState					INTEGER,
		swPackCustomerPlanUpgradePercent					Unsigned32,
		swPackCustomerPlanUpgradeResult					BITS
		}


	swPackCustomerPlanTypeIndex		 OBJECT-TYPE
		SYNTAX					 INTEGER{ equip(1),coldPatch(2),hotPatch(3)  }
		MAX-ACCESS			 not-accessible
		STATUS					 current
		DESCRIPTION			 " -- "
		::=  { softwarePackCustomerPlanEntry  1 }


	swPackCustomerPlanRowStatus		 OBJECT-TYPE
		SYNTAX					 RowStatus
		MAX-ACCESS			 read-create
		STATUS					 current
		DESCRIPTION			 " -- "
		::=  { softwarePackCustomerPlanEntry  2 }


	swPackCustomerPlanPackName		 OBJECT-TYPE
		SYNTAX					 DisplayString( SIZE ( 1 .. 59 ) )
		MAX-ACCESS			 read-create
		STATUS					 current
		DESCRIPTION			 " -- "
		::=  { softwarePackCustomerPlanEntry  3 }


	swPackCustomerPlanVendor		 OBJECT-TYPE
		SYNTAX					 DisplayString( SIZE ( 1 .. 59 ) )
		MAX-ACCESS			 read-create
		STATUS					 current
		DESCRIPTION			 " -- "
		::=  { softwarePackCustomerPlanEntry  4 }


	swPackCustomerPlanVersion		 OBJECT-TYPE
		SYNTAX					 DisplayString( SIZE ( 1 .. 59 ) )
		MAX-ACCESS			 read-create
		STATUS					 current
		DESCRIPTION			 " -- "
		::=  { softwarePackCustomerPlanEntry  5 }


	swPackCustomerPlanDownloadIndicator		 OBJECT-TYPE
		SYNTAX					 INTEGER{ doNothing(0),instantDownload(1),scheduleDownload(2),forcedDownload(3)  }
		MAX-ACCESS			 read-create
		STATUS					 current
		DESCRIPTION			 " -- "
		::=  { softwarePackCustomerPlanEntry  6 }


	swPackCustomerPlanScheduleDownloadTime		 OBJECT-TYPE
		SYNTAX					 DateAndTime
		MAX-ACCESS			 read-create
		STATUS					 current
		DESCRIPTION			 " -- "
		::=  { softwarePackCustomerPlanEntry  7 }


	swPackCustomerPlanDownloadDirectory		 OBJECT-TYPE
		SYNTAX					 DisplayString( SIZE ( 1 .. 199 ) )
		MAX-ACCESS			 read-create
		STATUS					 current
		DESCRIPTION			 " -- "
		::=  { softwarePackCustomerPlanEntry  8 }


	swPackCustomerPlanActivateIndicator		 OBJECT-TYPE
		SYNTAX					 INTEGER{ doNothing(0),instantActivate(1),scheduleActivate(2),instantDeactivate(3),scheduleDeactivate(4)  }
		MAX-ACCESS			 read-create
		STATUS					 current
		DESCRIPTION			 " -- "
		::=  { softwarePackCustomerPlanEntry  9 }


	swPackCustomerPlanScheduleActivateTime		 OBJECT-TYPE
		SYNTAX					 DateAndTime
		MAX-ACCESS			 read-create
		STATUS					 current
		DESCRIPTION			 " -- "
		::=  { softwarePackCustomerPlanEntry  10 }


	swPackCustomerPlanRelyVesion		 OBJECT-TYPE
		SYNTAX					 DisplayString( SIZE ( 1 .. 59 ) )
		MAX-ACCESS			 read-create
		STATUS					 current
		DESCRIPTION			 " -- "
		::=  { softwarePackCustomerPlanEntry  11 }


	swPackCustomerPlanFwActiveIndicator		 OBJECT-TYPE
		SYNTAX					 INTEGER{ notactive(0),active(1)  }
		MAX-ACCESS			 read-create
		STATUS					 current
		DESCRIPTION			 " -- "
		::=  { softwarePackCustomerPlanEntry  12 }


	swPackCustomerPlanUpgradeState		 OBJECT-TYPE
		SYNTAX					 INTEGER{ downloading(1),unzipping(2),activating(3)  }
		MAX-ACCESS			 read-only
		STATUS					 current
		DESCRIPTION			 " -- "
		::=  { softwarePackCustomerPlanEntry  13 }


	swPackCustomerPlanUpgradePercent		 OBJECT-TYPE
		SYNTAX					 Unsigned32( 0 .. 4294967295 )
		MAX-ACCESS			 read-only
		STATUS					 current
		DESCRIPTION			 " -- "
		::=  { softwarePackCustomerPlanEntry  14 }


	swPackCustomerPlanUpgradeResult		 OBJECT-TYPE
		SYNTAX					 BITS{ slot0(0),slot1(1),slot2(2),slot3(3),slot4(4),slot5(5),slot6(6),slot7(7),slot8(8),slot9(9),slot10(10),slot11(11),slot12(12),slot13(13),slot14(14),slot15(15),slot16(16)  }
		MAX-ACCESS			 read-only
		STATUS					 current
		DESCRIPTION			 " -- "
		::=  { softwarePackCustomerPlanEntry  15 }


	softwarePackCustRunningTable		 OBJECT-TYPE
		SYNTAX					 SEQUENCE  OF	 SoftwarePackCustRunningEntry
		MAX-ACCESS			 not-accessible
		STATUS					 current
		DESCRIPTION			 " -- "
		::=  { softwareNB  11 }


	softwarePackCustRunningEntry		 OBJECT-TYPE
		SYNTAX					 SoftwarePackCustRunningEntry
		MAX-ACCESS			 not-accessible
		STATUS					 current
		DESCRIPTION			 " -- "
		INDEX						{ swPackCustRunningTypeIndex }
		::=  { softwarePackCustRunningTable  1 }


	SoftwarePackCustRunningEntry		 ::=  SEQUENCE {
		swPackCustRunningTypeIndex					INTEGER,
		swPackCustRunningRowStatus					RowStatus,
		swPackCustRunningVersion					DisplayString,
		swPackCustRunningDownloadTime					DateAndTime,
		swPackCustRunningDownloadDirectory					DisplayString,
		swPackCustRunningRelyVesion					DisplayString,
		swPackCustRunningZipType					DisplayString
		}


	swPackCustRunningTypeIndex		 OBJECT-TYPE
		SYNTAX					 INTEGER{ equip(1),coldPatch(2),hotPatch(3)  }
		MAX-ACCESS			 not-accessible
		STATUS					 current
		DESCRIPTION			 " -- "
		::=  { softwarePackCustRunningEntry  1 }


	swPackCustRunningRowStatus		 OBJECT-TYPE
		SYNTAX					 RowStatus
		MAX-ACCESS			 read-only
		STATUS					 current
		DESCRIPTION			 " -- "
		::=  { softwarePackCustRunningEntry  2 }


	swPackCustRunningVersion		 OBJECT-TYPE
		SYNTAX					 DisplayString( SIZE ( 1 .. 59 ) )
		MAX-ACCESS			 read-only
		STATUS					 current
		DESCRIPTION			 " -- "
		::=  { softwarePackCustRunningEntry  3 }


	swPackCustRunningDownloadTime		 OBJECT-TYPE
		SYNTAX					 DateAndTime
		MAX-ACCESS			 read-only
		STATUS					 current
		DESCRIPTION			 " -- "
		::=  { softwarePackCustRunningEntry  4 }


	swPackCustRunningDownloadDirectory		 OBJECT-TYPE
		SYNTAX					 DisplayString( SIZE ( 1 .. 199 ) )
		MAX-ACCESS			 read-only
		STATUS					 current
		DESCRIPTION			 " -- "
		::=  { softwarePackCustRunningEntry  5 }


	swPackCustRunningRelyVesion		 OBJECT-TYPE
		SYNTAX					 DisplayString( SIZE ( 1 .. 59 ) )
		MAX-ACCESS			 read-only
		STATUS					 current
		DESCRIPTION			 " -- "
		::=  { softwarePackCustRunningEntry  6 }


	swPackCustRunningZipType		 OBJECT-TYPE
		SYNTAX					 DisplayString( SIZE ( 1 .. 59 ) )
		MAX-ACCESS			 read-only
		STATUS					 current
		DESCRIPTION			 " -- "
		::=  { softwarePackCustRunningEntry  7 }


	softwarePackUpgradeControl		 OBJECT IDENTIFIER
		::=  { softwareNB  12 }


	swPackUpgradeControlSwitch		 OBJECT-TYPE
		SYNTAX					 INTEGER{ normal(0),customer(1)  }
		MAX-ACCESS			 read-write
		STATUS					 current
		DESCRIPTION			 " -- "
		::=  { softwarePackUpgradeControl  1 }


	packStoreOptimizeControl		 OBJECT IDENTIFIER
		::=  { softwareNB  13 }


	packRRUUpgradeCtrlSwitch		 OBJECT-TYPE
		SYNTAX					 INTEGER{ off(0),on(1)  }
		MAX-ACCESS			 read-write
		STATUS					 current
		DESCRIPTION			 " -- "
		::=  { packStoreOptimizeControl  1 }


	packNBUpgradeCtrlSwitch		 OBJECT-TYPE
		SYNTAX					 INTEGER{ off(0),on(1)  }
		MAX-ACCESS			 read-write
		STATUS					 current
		DESCRIPTION			 " -- "
		::=  { packStoreOptimizeControl  2 }


	packHotPackRollbackTrigger		 OBJECT-TYPE
		SYNTAX					 INTEGER{ off(0),on(1)  }
		MAX-ACCESS			 read-write
		STATUS					 current
		DESCRIPTION			 " -- "
		::=  { packStoreOptimizeControl  3 }


	packHotPackRollbackResult		 OBJECT-TYPE
		SYNTAX					 INTEGER{ invalid(0),fail(1),success(2),backloading(3)  }
		MAX-ACCESS			 read-only
		STATUS					 current
		DESCRIPTION			 " -- "
		::=  { packStoreOptimizeControl  4 }


	packActiveControl		 OBJECT IDENTIFIER
		::=  { softwareNB  14 }


	packActiveCtrlSwitch		 OBJECT-TYPE
		SYNTAX					 INTEGER{ off(0),on(1)  }
		MAX-ACCESS			 read-write
		STATUS					 current
		DESCRIPTION			 " -- "
		::=  { packActiveControl  1 }


	softwareBaseBandBoardCfgTable		 OBJECT-TYPE
		SYNTAX					 SEQUENCE  OF	 SoftwareBaseBandBoardCfgEntry
		MAX-ACCESS			 not-accessible
		STATUS					 current
		DESCRIPTION			 " -- "
		::=  { softwareNB  17 }


	softwareBaseBandBoardCfgEntry		 OBJECT-TYPE
		SYNTAX					 SoftwareBaseBandBoardCfgEntry
		MAX-ACCESS			 not-accessible
		STATUS					 current
		DESCRIPTION			 " -- "
		INDEX						{ softwareBaseBandBoardCfgIndex }
		::=  { softwareBaseBandBoardCfgTable  1 }


	SoftwareBaseBandBoardCfgEntry		 ::=  SEQUENCE {
		softwareBaseBandBoardCfgIndex					Integer32,
		softwareBaseBandBoardCfgRowStatus					RowStatus,
		softwareBaseBandBoardType					INTEGER
		}


	softwareBaseBandBoardCfgIndex		 OBJECT-TYPE
		SYNTAX					 Integer32( 1 .. 32 )
		MAX-ACCESS			 not-accessible
		STATUS					 current
		DESCRIPTION			 " -- "
		::=  { softwareBaseBandBoardCfgEntry  1 }


	softwareBaseBandBoardCfgRowStatus		 OBJECT-TYPE
		SYNTAX					 RowStatus
		MAX-ACCESS			 read-create
		STATUS					 current
		DESCRIPTION			 " -- "
		::=  { softwareBaseBandBoardCfgEntry  2 }


	softwareBaseBandBoardType		 OBJECT-TYPE
		SYNTAX					 INTEGER{ unknown(0),riuDof(48),riuE1(49),riuA(50),gcu(52),ccu(54),ceu(56),bbu(58),aifur6C8A(59),ifur3C6A(60),ifur6C1A(61),ifur3C4A(62),aifur9C1A(63),gru(64),ctu(65),iiu(66),bcu(67),biu(68),accu(70),abbut(71),abbuf(72),eiuE1(73),synu(74),eiuDof(75),aifur12C1A(77),aifur9C8A(78),scta(97),bpia(98),bpoa(99),gpscu(100),emu(101),geu(102),emau(103),etpa(104),etpd(105),psu(106),fcu(107),bpoc(108),bpoe(109),emdu(110),etpc(111),bpof(128),etpe(129),sctc(130),sctd(141),mmba(142),bpog(143),bpoh(177),scte(178),mmbc(224),sctf(240),bpoi(241)  }
		MAX-ACCESS			 read-create
		STATUS					 current
		DESCRIPTION			 " -- "
		::=  { softwareBaseBandBoardCfgEntry  3 }


	snmpControl		 OBJECT IDENTIFIER
		::=  { lteCommon  4 }


	snmpInterProcess		 OBJECT IDENTIFIER
		::=  { snmpControl  1 }


	snmpResponseTimer		 OBJECT-TYPE
		SYNTAX					 Integer32( 1 .. 10 )
		MAX-ACCESS			 read-only
		STATUS					 current
		DESCRIPTION			 " -- "
		::=  { snmpInterProcess  1 }


	snmpResponseInformRetryTimer		 OBJECT-TYPE
		SYNTAX					 Integer32( 10 .. 60 )
		MAX-ACCESS			 read-only
		STATUS					 current
		DESCRIPTION			 " -- "
		::=  { snmpInterProcess  2 }


	snmpInformTimer		 OBJECT-TYPE
		SYNTAX					 Integer32( 1 .. 10 )
		MAX-ACCESS			 read-only
		STATUS					 current
		DESCRIPTION			 " -- "
		::=  { snmpInterProcess  3 }


	snmpInformRetrys		 OBJECT-TYPE
		SYNTAX					 Integer32( 1 .. 10 )
		MAX-ACCESS			 read-only
		STATUS					 current
		DESCRIPTION			 " -- "
		::=  { snmpInterProcess  4 }


	snmpAlarmPDUType		 OBJECT-TYPE
		SYNTAX					 INTEGER{ trap(0),inform(1)  }
		MAX-ACCESS			 read-only
		STATUS					 current
		DESCRIPTION			 " -- "
		::=  { snmpInterProcess  5 }


	snmpEventPDUType		 OBJECT-TYPE
		SYNTAX					 INTEGER{ trap(0),inform(1)  }
		MAX-ACCESS			 read-only
		STATUS					 current
		DESCRIPTION			 " -- "
		::=  { snmpInterProcess  6 }


	snmpAlterationPDUType		 OBJECT-TYPE
		SYNTAX					 INTEGER{ trap(0),inform(1)  }
		MAX-ACCESS			 read-only
		STATUS					 current
		DESCRIPTION			 " -- "
		::=  { snmpInterProcess  7 }


	snmpInformBufferNumber		 OBJECT-TYPE
		SYNTAX					 Integer32( 1 .. 100 )
		MAX-ACCESS			 read-only
		STATUS					 current
		DESCRIPTION			 " -- "
		::=  { snmpInterProcess  8 }


	configProcessNode		 OBJECT IDENTIFIER
		::=  { snmpControl  2 }


	configProcessNotifications		 OBJECT IDENTIFIER
		::=  { configProcessNode  1 }


	configProcessNotify		 NOTIFICATION-TYPE
		OBJECTS					 { configProcNotiNEType,configProcNotiNEID,configProcNotiNEVer,configProcSrcRequestID,configProcResult,configProcAdditionInfo,configProcOccurTime }
		STATUS					 current
		DESCRIPTION			 " -- "
		::=  { configProcessNotifications  1 }


	configProcessNotificationObjects		 OBJECT IDENTIFIER
		::=  { configProcessNode  2 }


	configProcNotiNEType		 OBJECT-TYPE
		SYNTAX					 INTEGER{ unknown(0),tlb60a(2),emb5116tdlte(3),emb5132tdlte(4),emb5116(5),epc(21),ims(41)  }
		MAX-ACCESS			 accessible-for-notify
		STATUS					 current
		DESCRIPTION			 " -- "
		::=  { configProcessNotificationObjects  1 }


	configProcNotiNEID		 OBJECT-TYPE
		SYNTAX					 Unsigned32( 0 .. 4294967295 )
		MAX-ACCESS			 accessible-for-notify
		STATUS					 current
		DESCRIPTION			 " -- "
		::=  { configProcessNotificationObjects  2 }


	configProcNotiNEVer		 OBJECT-TYPE
		SYNTAX					 OBJECT IDENTIFIER
		MAX-ACCESS			 accessible-for-notify
		STATUS					 current
		DESCRIPTION			 " -- "
		::=  { configProcessNotificationObjects  3 }


	configProcSrcRequestID		 OBJECT-TYPE
		SYNTAX					 Integer32( -2147483648 .. 2147483647 )
		MAX-ACCESS			 accessible-for-notify
		STATUS					 current
		DESCRIPTION			 " -- "
		::=  { configProcessNotificationObjects  4 }


	configProcResult		 OBJECT-TYPE
		SYNTAX					 INTEGER{ fail(0),success(1),processing(2)  }
		MAX-ACCESS			 accessible-for-notify
		STATUS					 current
		DESCRIPTION			 " -- "
		::=  { configProcessNotificationObjects  5 }


	configProcAdditionInfo		 OBJECT-TYPE
		SYNTAX					 DisplayString( SIZE ( 1 .. 255 ) )
		MAX-ACCESS			 accessible-for-notify
		STATUS					 current
		DESCRIPTION			 " -- "
		::=  { configProcessNotificationObjects  6 }


	configProcOccurTime		 OBJECT-TYPE
		SYNTAX					 DateAndTime
		MAX-ACCESS			 accessible-for-notify
		STATUS					 current
		DESCRIPTION			 " -- "
		::=  { configProcessNotificationObjects  7 }


	configManagement		 OBJECT IDENTIFIER
		::=  { lteCommon  5 }


	configFile		 OBJECT IDENTIFIER
		::=  { configManagement  1 }


	configFileInfo		 OBJECT IDENTIFIER
		::=  { configFile  1 }


	configFileSaveTrigger		 OBJECT-TYPE
		SYNTAX					 INTEGER{ off(0),on(1)  }
		MAX-ACCESS			 read-write
		STATUS					 current
		DESCRIPTION			 " -- "
		::=  { configFileInfo  1 }


	configFileSaveName		 OBJECT-TYPE
		SYNTAX					 DisplayString( SIZE ( 1 .. 59 ) )
		MAX-ACCESS			 read-write
		STATUS					 current
		DESCRIPTION			 " -- "
		::=  { configFileInfo  2 }


	configFileAutoUpgradeIndicator		 OBJECT-TYPE
		SYNTAX					 INTEGER{ off(0),on(1)  }
		MAX-ACCESS			 read-only
		STATUS					 current
		DESCRIPTION			 " -- "
		::=  { configFileInfo  3 }


	configFileTable		 OBJECT-TYPE
		SYNTAX					 SEQUENCE  OF	 ConfigFileEntry
		MAX-ACCESS			 not-accessible
		STATUS					 current
		DESCRIPTION			 " -- "
		::=  { configFile  2 }


	configFileEntry		 OBJECT-TYPE
		SYNTAX					 ConfigFileEntry
		MAX-ACCESS			 not-accessible
		STATUS					 current
		DESCRIPTION			 " -- "
		INDEX						{ configFileIndex }
		::=  { configFileTable  1 }


	ConfigFileEntry		 ::=  SEQUENCE {
		configFileIndex					Integer32,
		configFileRowStatus					RowStatus,
		configFileName					DisplayString,
		configFileRelyMIBVesion					DisplayString,
		configFileSaveTime					DateAndTime,
		configFileDelTrigger					INTEGER
		}


	configFileIndex		 OBJECT-TYPE
		SYNTAX					 Integer32( 1 .. 3 )
		MAX-ACCESS			 not-accessible
		STATUS					 current
		DESCRIPTION			 " -- "
		::=  { configFileEntry  1 }


	configFileRowStatus		 OBJECT-TYPE
		SYNTAX					 RowStatus
		MAX-ACCESS			 read-only
		STATUS					 current
		DESCRIPTION			 " -- "
		::=  { configFileEntry  2 }


	configFileName		 OBJECT-TYPE
		SYNTAX					 DisplayString( SIZE ( 1 .. 59 ) )
		MAX-ACCESS			 read-only
		STATUS					 current
		DESCRIPTION			 " -- "
		::=  { configFileEntry  3 }


	configFileRelyMIBVesion		 OBJECT-TYPE
		SYNTAX					 DisplayString( SIZE ( 1 .. 59 ) )
		MAX-ACCESS			 read-only
		STATUS					 current
		DESCRIPTION			 " -- "
		::=  { configFileEntry  4 }


	configFileSaveTime		 OBJECT-TYPE
		SYNTAX					 DateAndTime
		MAX-ACCESS			 read-only
		STATUS					 current
		DESCRIPTION			 " -- "
		::=  { configFileEntry  5 }


	configFileDelTrigger		 OBJECT-TYPE
		SYNTAX					 INTEGER{ off(0),on(1)  }
		MAX-ACCESS			 read-write
		STATUS					 current
		DESCRIPTION			 " -- "
		::=  { configFileEntry  6 }


	configfilePlanTable		 OBJECT-TYPE
		SYNTAX					 SEQUENCE  OF	 ConfigfilePlanEntry
		MAX-ACCESS			 not-accessible
		STATUS					 current
		DESCRIPTION			 " -- "
		::=  { configFile  3 }


	configfilePlanEntry		 OBJECT-TYPE
		SYNTAX					 ConfigfilePlanEntry
		MAX-ACCESS			 not-accessible
		STATUS					 current
		DESCRIPTION			 " -- "
		INDEX						{ configfilePlanTypeIndex }
		::=  { configfilePlanTable  1 }


	ConfigfilePlanEntry		 ::=  SEQUENCE {
		configfilePlanTypeIndex					INTEGER,
		configfilePlanRowStatus					RowStatus,
		configFileLocationType					INTEGER,
		configfilePlanName					DisplayString,
		configfilePlanDownloadDirectory					DisplayString,
		configfilePlanActivateIndicator					INTEGER,
		configfilePlanScheduleActivateTime					DateAndTime,
		configfilePlanIsActivatedFlag					INTEGER
		}


	configfilePlanTypeIndex		 OBJECT-TYPE
		SYNTAX					 INTEGER{ configFile(1)  }
		MAX-ACCESS			 not-accessible
		STATUS					 current
		DESCRIPTION			 " -- "
		::=  { configfilePlanEntry  1 }


	configfilePlanRowStatus		 OBJECT-TYPE
		SYNTAX					 RowStatus
		MAX-ACCESS			 read-create
		STATUS					 current
		DESCRIPTION			 " -- "
		::=  { configfilePlanEntry  2 }


	configFileLocationType		 OBJECT-TYPE
		SYNTAX					 INTEGER{ localFile(0),remoteFile(1)  }
		MAX-ACCESS			 read-create
		STATUS					 current
		DESCRIPTION			 " -- "
		::=  { configfilePlanEntry  3 }


	configfilePlanName		 OBJECT-TYPE
		SYNTAX					 DisplayString( SIZE ( 1 .. 60 ) )
		MAX-ACCESS			 read-create
		STATUS					 current
		DESCRIPTION			 " -- "
		::=  { configfilePlanEntry  4 }


	configfilePlanDownloadDirectory		 OBJECT-TYPE
		SYNTAX					 DisplayString( SIZE ( 1 .. 200 ) )
		MAX-ACCESS			 read-create
		STATUS					 current
		DESCRIPTION			 " -- "
		::=  { configfilePlanEntry  5 }


	configfilePlanActivateIndicator		 OBJECT-TYPE
		SYNTAX					 INTEGER{ doNothing(0),instantActivate(1),scheduleActivate(2)  }
		MAX-ACCESS			 read-create
		STATUS					 current
		DESCRIPTION			 " -- "
		::=  { configfilePlanEntry  6 }


	configfilePlanScheduleActivateTime		 OBJECT-TYPE
		SYNTAX					 DateAndTime
		MAX-ACCESS			 read-create
		STATUS					 current
		DESCRIPTION			 " -- "
		::=  { configfilePlanEntry  7 }


	configfilePlanIsActivatedFlag		 OBJECT-TYPE
		SYNTAX					 INTEGER{ notActivate(0),activateSuccess(1),activateFailure(2)  }
		MAX-ACCESS			 read-create
		STATUS					 current
		DESCRIPTION			 " -- "
		::=  { configfilePlanEntry  8 }


	alteration		 OBJECT IDENTIFIER
		::=  { configManagement  2 }


	alterationNotificationNode		 OBJECT IDENTIFIER
		::=  { alteration  1 }


	alterationNotifiactions		 OBJECT IDENTIFIER
		::=  { alterationNotificationNode  1 }


	alterationNofication		 NOTIFICATION-TYPE
		OBJECTS					 { alterationNotiNEType,alterationNotiNEID,alterationNotiType,alterationNotiTime }
		STATUS					 current
		DESCRIPTION			 " -- "
		::=  { alterationNotifiactions  1 }


	alterationObjects		 OBJECT IDENTIFIER
		::=  { alterationNotificationNode  2 }


	alterationNotiNEType		 OBJECT-TYPE
		SYNTAX					 INTEGER{ unknown(0),tlb60a(2),emb5116tdlte(3),emb5132tdlte(4),emb5116(5),epc(21),ims(41)  }
		MAX-ACCESS			 accessible-for-notify
		STATUS					 current
		DESCRIPTION			 " -- "
		::=  { alterationObjects  1 }


	alterationNotiNEID		 OBJECT-TYPE
		SYNTAX					 Unsigned32( 0 .. 4294967295 )
		MAX-ACCESS			 accessible-for-notify
		STATUS					 current
		DESCRIPTION			 " -- "
		::=  { alterationObjects  2 }


	alterationNotiType		 OBJECT-TYPE
		SYNTAX					 INTEGER{ create(0),delete(1),modify(3)  }
		MAX-ACCESS			 accessible-for-notify
		STATUS					 current
		DESCRIPTION			 " -- "
		::=  { alterationObjects  3 }


	alterationNotiTime		 OBJECT-TYPE
		SYNTAX					 DateAndTime
		MAX-ACCESS			 accessible-for-notify
		STATUS					 current
		DESCRIPTION			 " -- "
		::=  { alterationObjects  4 }


	alterationStatics		 OBJECT IDENTIFIER
		::=  { alteration  2 }


	alterationNotiSends		 OBJECT IDENTIFIER
		::=  { alterationStatics  1 }


	transaction		 OBJECT IDENTIFIER
		::=  { configManagement  3 }


	transactionControl		 OBJECT IDENTIFIER
		::=  { transaction  1 }


	transactionControlSwitch		 OBJECT-TYPE
		SYNTAX					 INTEGER{ prepare(1),commit(2),abort(3)  }
		MAX-ACCESS			 read-write
		STATUS					 current
		DESCRIPTION			 " -- "
		::=  { transactionControl  1 }


	transactionProcedureStatus		 OBJECT-TYPE
		SYNTAX					 INTEGER{ idle(0),preparing(1),commiting(2),rollbacking(3)  }
		MAX-ACCESS			 read-only
		STATUS					 current
		DESCRIPTION			 " -- "
		::=  { transactionControl  2 }


	transactionExcutiveMode		 OBJECT-TYPE
		SYNTAX					 INTEGER{ batchSet(0),file(1)  }
		MAX-ACCESS			 read-write
		STATUS					 current
		DESCRIPTION			 " -- "
		::=  { transactionControl  3 }


	transactionNextSetTimer		 OBJECT-TYPE
		SYNTAX					 Integer32( -2147483648 .. 2147483647 )
		MAX-ACCESS			 read-write
		STATUS					 current
		DESCRIPTION			 " -- "
		::=  { transactionControl  4 }


	transactionDataFileName		 OBJECT-TYPE
		SYNTAX					 DisplayString( SIZE ( 1 .. 59 ) )
		MAX-ACCESS			 read-write
		STATUS					 current
		DESCRIPTION			 " -- "
		::=  { transactionControl  5 }


	transactionDataFileDirectory		 OBJECT-TYPE
		SYNTAX					 DisplayString( SIZE ( 1 .. 199 ) )
		MAX-ACCESS			 read-write
		STATUS					 current
		DESCRIPTION			 " -- "
		::=  { transactionControl  6 }


	transactionDataFileTimer		 OBJECT-TYPE
		SYNTAX					 Integer32( -2147483648 .. 2147483647 )
		MAX-ACCESS			 read-write
		STATUS					 current
		DESCRIPTION			 " -- "
		::=  { transactionControl  7 }


	transactionResultNotificationNode		 OBJECT IDENTIFIER
		::=  { transaction  2 }


	transactionResultNotifications		 OBJECT IDENTIFIER
		::=  { transactionResultNotificationNode  1 }


	transactionResultNotification		 NOTIFICATION-TYPE
		OBJECTS					 { transactionResultNotiNEType,transactionResultNotiNEID,transactionResultNotiResult,transactionResultNotiFirstErrVariableOID,transactionResultNotiErrCode,transactionResultNotiAddition,transactionResultNotiTime }
		STATUS					 current
		DESCRIPTION			 " -- "
		::=  { transactionResultNotifications  1 }


	transactionResultObjects		 OBJECT IDENTIFIER
		::=  { transactionResultNotificationNode  2 }


	transactionResultNotiNEType		 OBJECT-TYPE
		SYNTAX					 INTEGER{ unknown(0),tlb60a(2),emb5116tdlte(3),emb5132tdlte(4),emb5116(5),epc(21),ims(41)  }
		MAX-ACCESS			 accessible-for-notify
		STATUS					 current
		DESCRIPTION			 " -- "
		::=  { transactionResultObjects  1 }


	transactionResultNotiNEID		 OBJECT-TYPE
		SYNTAX					 Unsigned32( 0 .. 4294967295 )
		MAX-ACCESS			 accessible-for-notify
		STATUS					 current
		DESCRIPTION			 " -- "
		::=  { transactionResultObjects  2 }


	transactionResultNotiResult		 OBJECT-TYPE
		SYNTAX					 INTEGER{ startSuccess(0),commitSuccess(1),fail(2)  }
		MAX-ACCESS			 accessible-for-notify
		STATUS					 current
		DESCRIPTION			 " -- "
		::=  { transactionResultObjects  3 }


	transactionResultNotiFirstErrVariableOID		 OBJECT-TYPE
		SYNTAX					 OBJECT IDENTIFIER
		MAX-ACCESS			 accessible-for-notify
		STATUS					 current
		DESCRIPTION			 " -- "
		::=  { transactionResultObjects  4 }


	transactionResultNotiErrCode		 OBJECT-TYPE
		SYNTAX					 Unsigned32( 0 .. 4294967295 )
		MAX-ACCESS			 accessible-for-notify
		STATUS					 current
		DESCRIPTION			 " -- "
		::=  { transactionResultObjects  5 }


	transactionResultNotiAddition		 OBJECT-TYPE
		SYNTAX					 DisplayString( SIZE ( 1 .. 255 ) )
		MAX-ACCESS			 accessible-for-notify
		STATUS					 current
		DESCRIPTION			 " -- "
		::=  { transactionResultObjects  6 }


	transactionResultNotiTime		 OBJECT-TYPE
		SYNTAX					 DateAndTime
		MAX-ACCESS			 accessible-for-notify
		STATUS					 current
		DESCRIPTION			 " -- "
		::=  { transactionResultObjects  7 }


	commTrapManangement		 OBJECT IDENTIFIER
		::=  { configManagement  4 }


	eventGeneralEvent		 OBJECT IDENTIFIER
		::=  { commTrapManangement  1 }


	eventGeneralEventTraps		 OBJECT IDENTIFIER
		::=  { eventGeneralEvent  1 }


	eventGeneralEventTrap		 NOTIFICATION-TYPE
		OBJECTS					 { eventGeneralEventNEType,eventGeneralEventNEID,eventGeneralEventType,eventGeneralEventResult,eventGeneralEventSource,eventGeneralEventAdditionInfo,eventGeneralEventOccurTime }
		STATUS					 current
		DESCRIPTION			 " -- "
		::=  { eventGeneralEventTraps  1 }


	eventGeneralEventObjects		 OBJECT IDENTIFIER
		::=  { eventGeneralEvent  2 }


	eventGeneralEventNEType		 OBJECT-TYPE
		SYNTAX					 INTEGER{ unknown(0),tlb60a(2),emb5116tdlte(3),emb5132tdlte(4),emb5116(5),epc(21),ims(41)  }
		MAX-ACCESS			 accessible-for-notify
		STATUS					 current
		DESCRIPTION			 " -- "
		::=  { eventGeneralEventObjects  1 }


	eventGeneralEventNEID		 OBJECT-TYPE
		SYNTAX					 Unsigned32( 0 .. 4294967295 )
		MAX-ACCESS			 accessible-for-notify
		STATUS					 current
		DESCRIPTION			 " -- "
		::=  { eventGeneralEventObjects  2 }


	eventGeneralEventType		 OBJECT-TYPE
		SYNTAX					 INTEGER{ cellBlock(1),cellUnblock(2),masterSlaveConsistency(3),ipoaBuild(4),dynCfgActOn(6),softActOnTime(7),masterSlaveSwap(16),boardPowerOn(19),saalCreate(21),saalDestroy(22),pathCreate(23),pathDestroy(24),debugUpload(25),dfgCreate(26),antCfgParse(27),gpsUpgrade(28),ifuNetworkPlanReq(29),programSyn(30),initCfgResult(31),localCellSetup(32),localCellDelete(33),cellSetup(34),cellDelete(35),rruActiveAlarmCheck(38),antCalibration(39),rruProgramDownload(40),rruProgramActive(41),retAntSelfTest(43),retAntProgrameDownload(44),retAntPathCalibrate(45),retAntSetTilt(46),anrAdd(47),anrDel(48),pciCollision(49),pciListInvalid(50),retActiveAlarmCheck(51),bbuProgramActive(52),coldpatchProgramActive(53),hotpatchProgramActive(54),cfgParse(55),snapCfgCreat(56),fileTransStop(57),envProgramActive(58),rruLogUpload(59),rruLoopBack(60),initCfgStart(61),cellLccCongestion(62),cellLccNormal(63),ocuProgramActive(64),rmClkLoopBack(65),cellHighLoag(66),cellLowLoag(67),cellLoadReport(68),cfgFileAmalgamResult(69),rollBackSceneCheckFail(70),rrucellparacheck(71),rHubLogUpload(72),carrierCheck(100),cellPerfStatistics(101),cellR5PerfReport(102),nbapNodeBReset(103),cellPerfDataClear(104),interfereMeasure(105),cellInterfere(106),cellSuspicionfulShift(107),cellShift(108),cellBusyNoDetect(109),raeFileDownload(110),raeFileUpload(111),adiStatus(112),tdsCellBlock(200),tdsCellUnblock(201),cpuOverLoad(301),cpuOverLoadRecv(302),cellPrbAc(303),cellPrbAcRecv(304),ueNumAcHighLoad(305),ueNumAcRecv(306),highLoadAcBar(307),acBarRecv(308),cellPrbCong(309),cellPrbCongRecv(310)  }
		MAX-ACCESS			 accessible-for-notify
		STATUS					 current
		DESCRIPTION			 " -- "
		::=  { eventGeneralEventObjects  3 }


	eventGeneralEventResult		 OBJECT-TYPE
		SYNTAX					 INTEGER{ fail(0),success(1)  }
		MAX-ACCESS			 accessible-for-notify
		STATUS					 current
		DESCRIPTION			 " -- "
		::=  { eventGeneralEventObjects  4 }


	eventGeneralEventSource		 OBJECT-TYPE
		SYNTAX					 DisplayString( SIZE ( 1 .. 255 ) )
		MAX-ACCESS			 accessible-for-notify
		STATUS					 current
		DESCRIPTION			 " -- "
		::=  { eventGeneralEventObjects  5 }


	eventGeneralEventAdditionInfo		 OBJECT-TYPE
		SYNTAX					 DisplayString( SIZE ( 1 .. 255 ) )
		MAX-ACCESS			 accessible-for-notify
		STATUS					 current
		DESCRIPTION			 " -- "
		::=  { eventGeneralEventObjects  6 }


	eventGeneralEventOccurTime		 OBJECT-TYPE
		SYNTAX					 DateAndTime
		MAX-ACCESS			 accessible-for-notify
		STATUS					 current
		DESCRIPTION			 " -- "
		::=  { eventGeneralEventObjects  7 }


	eventSynchronization		 OBJECT IDENTIFIER
		::=  { commTrapManangement  2 }


	eventSynchronizationTraps		 OBJECT IDENTIFIER
		::=  { eventSynchronization  1 }


	eventSynchronizationTrap		 NOTIFICATION-TYPE
		OBJECTS					 { eventSynchronizationNEType,eventSynchronizationNEID,eventSynchronizationType,eventSynchronizationAdditionInfo,eventSynchronizationOccurTime }
		STATUS					 current
		DESCRIPTION			 " -- "
		::=  { eventSynchronizationTraps  1 }


	eventSynchronizationObjects		 OBJECT IDENTIFIER
		::=  { eventSynchronization  2 }


	eventSynchronizationNEType		 OBJECT-TYPE
		SYNTAX					 INTEGER{ unknown(0),tlb60a(2),emb5116tdlte(3),emb5132tdlte(4),emb5116(5),epc(21),ims(41)  }
		MAX-ACCESS			 accessible-for-notify
		STATUS					 current
		DESCRIPTION			 " -- "
		::=  { eventSynchronizationObjects  1 }


	eventSynchronizationNEID		 OBJECT-TYPE
		SYNTAX					 Unsigned32( 0 .. 4294967295 )
		MAX-ACCESS			 accessible-for-notify
		STATUS					 current
		DESCRIPTION			 " -- "
		::=  { eventSynchronizationObjects  2 }


	eventSynchronizationType		 OBJECT-TYPE
		SYNTAX					 BITS{ activeAlarmFile(0),dataConsistency(1)  }
		MAX-ACCESS			 accessible-for-notify
		STATUS					 current
		DESCRIPTION			 " -- "
		::=  { eventSynchronizationObjects  3 }


	eventSynchronizationAdditionInfo		 OBJECT-TYPE
		SYNTAX					 DisplayString( SIZE ( 1 .. 255 ) )
		MAX-ACCESS			 accessible-for-notify
		STATUS					 current
		DESCRIPTION			 " -- "
		::=  { eventSynchronizationObjects  4 }


	eventSynchronizationOccurTime		 OBJECT-TYPE
		SYNTAX					 DateAndTime
		MAX-ACCESS			 accessible-for-notify
		STATUS					 current
		DESCRIPTION			 " -- "
		::=  { eventSynchronizationObjects  5 }


	timeManagement		 OBJECT IDENTIFIER
		::=  { lteCommon  6 }


	sntp		 OBJECT IDENTIFIER
		::=  { timeManagement  1 }


	sntpConfig		 OBJECT IDENTIFIER
		::=  { sntp  1 }


	sntpServerInetAddrType		 OBJECT-TYPE
		SYNTAX					 InetAddressType
		MAX-ACCESS			 read-write
		STATUS					 current
		DESCRIPTION			 " -- "
		::=  { sntpConfig  1 }


	sntpServerInetAddr		 OBJECT-TYPE
		SYNTAX					 InetAddress
		MAX-ACCESS			 read-write
		STATUS					 current
		DESCRIPTION			 " -- "
		::=  { sntpConfig  2 }


	sntpPortId		 OBJECT-TYPE
		SYNTAX					 Integer32( 1234 .. 1234 )
		MAX-ACCESS			 read-only
		STATUS					 current
		DESCRIPTION			 " -- "
		::=  { sntpConfig  3 }


	sntpFirstSynchronizedPeriod		 OBJECT-TYPE
		SYNTAX					 Integer32( 1 .. 300 )
		MAX-ACCESS			 read-write
		STATUS					 current
		DESCRIPTION			 " -- "
		::=  { sntpConfig  4 }


	sntpPeriodicSynchronizedPeriod		 OBJECT-TYPE
		SYNTAX					 Integer32( 1 .. 300 )
		MAX-ACCESS			 read-write
		STATUS					 current
		DESCRIPTION			 " -- "
		::=  { sntpConfig  5 }


	sntpSynchronizedSwitch		 OBJECT-TYPE
		SYNTAX					 INTEGER{ off(0),on(1)  }
		MAX-ACCESS			 read-write
		STATUS					 current
		DESCRIPTION			 " -- "
		::=  { sntpConfig  6 }


	sntpLastSynchronizedTime		 OBJECT-TYPE
		SYNTAX					 DateAndTime
		MAX-ACCESS			 read-only
		STATUS					 current
		DESCRIPTION			 " -- "
		::=  { sntpConfig  7 }


	sntpProtocolVersion		 OBJECT-TYPE
		SYNTAX					 INTEGER{ sntpv2(1),sntpv3(2)  }
		MAX-ACCESS			 read-only
		STATUS					 current
		DESCRIPTION			 " -- "
		::=  { sntpConfig  8 }


	sntpFirstDiscAlarmThreshold		 OBJECT-TYPE
		SYNTAX					 Integer32( 1 .. 3600 )
		MAX-ACCESS			 read-write
		STATUS					 current
		DESCRIPTION			 " -- "
		::=  { sntpConfig  9 }


	sntpPeriodicDiscAlarmThreshold		 OBJECT-TYPE
		SYNTAX					 Integer32( 1 .. 43200 )
		MAX-ACCESS			 read-write
		STATUS					 current
		DESCRIPTION			 " -- "
		::=  { sntpConfig  10 }


	sntpLocalTimeZone		 OBJECT-TYPE
		SYNTAX					 Integer32( -11 .. 12 )
		MAX-ACCESS			 read-write
		STATUS					 current
		DESCRIPTION			 " -- "
		::=  { sntpConfig  11 }


	sntpConnectState		 OBJECT-TYPE
		SYNTAX					 Integer32( 0|1 )
		MAX-ACCESS			 read-only
		STATUS					 current
		DESCRIPTION			 " -- "
		::=  { sntpConfig  12 }


	sntpStatics		 OBJECT IDENTIFIER
		::=  { sntp  2 }


	sntpDisconnects		 OBJECT-TYPE
		SYNTAX					 Integer32( -2147483648 .. 2147483647 )
		MAX-ACCESS			 read-only
		STATUS					 current
		DESCRIPTION			 " -- "
		::=  { sntpStatics  1 }


	inventoryManagement		 OBJECT IDENTIFIER
		::=  { lteCommon  7 }


	inventoryEquipment		 OBJECT IDENTIFIER
		::=  { inventoryManagement  1 }


	invRackTable		 OBJECT-TYPE
		SYNTAX					 SEQUENCE  OF	 InvRackEntry
		MAX-ACCESS			 not-accessible
		STATUS					 current
		DESCRIPTION			 " -- "
		::=  { inventoryEquipment  1 }


	invRackEntry		 OBJECT-TYPE
		SYNTAX					 InvRackEntry
		MAX-ACCESS			 not-accessible
		STATUS					 current
		DESCRIPTION			 " -- "
		INDEX						{ invRackRackNo }
		::=  { invRackTable  1 }


	InvRackEntry		 ::=  SEQUENCE {
		invRackRackNo					Integer32,
		invRackRowStatus					RowStatus,
		invRackType					DisplayString,
		invRackDescription					DisplayString,
		invRackVendorUnitTypeNumber					DisplayString,
		invRackVendorName					DisplayString,
		invRackSerialNumber					DisplayString,
		invRackVersionNumber					DisplayString,
		invRackDateOfManufacture					DisplayString,
		invRackDateOfLastService					DisplayString
		}


	invRackRackNo		 OBJECT-TYPE
		SYNTAX					 Integer32( 0 .. 0 )
		MAX-ACCESS			 not-accessible
		STATUS					 current
		DESCRIPTION			 " -- "
		::=  { invRackEntry  1 }


	invRackRowStatus		 OBJECT-TYPE
		SYNTAX					 RowStatus
		MAX-ACCESS			 read-only
		STATUS					 current
		DESCRIPTION			 " -- "
		::=  { invRackEntry  2 }


	invRackType		 OBJECT-TYPE
		SYNTAX					 DisplayString( SIZE ( 1 .. 255 ) )
		MAX-ACCESS			 read-write
		STATUS					 current
		DESCRIPTION			 " -- "
		::=  { invRackEntry  3 }


	invRackDescription		 OBJECT-TYPE
		SYNTAX					 DisplayString( SIZE ( 1 .. 255 ) )
		MAX-ACCESS			 read-write
		STATUS					 current
		DESCRIPTION			 " -- "
		::=  { invRackEntry  4 }


	invRackVendorUnitTypeNumber		 OBJECT-TYPE
		SYNTAX					 DisplayString( SIZE ( 1 .. 20 ) )
		MAX-ACCESS			 read-write
		STATUS					 current
		DESCRIPTION			 " -- "
		::=  { invRackEntry  5 }


	invRackVendorName		 OBJECT-TYPE
		SYNTAX					 DisplayString( SIZE ( 1 .. 20 ) )
		MAX-ACCESS			 read-write
		STATUS					 current
		DESCRIPTION			 " -- "
		::=  { invRackEntry  6 }


	invRackSerialNumber		 OBJECT-TYPE
		SYNTAX					 DisplayString( SIZE ( 1 .. 50 ) )
		MAX-ACCESS			 read-write
		STATUS					 current
		DESCRIPTION			 " -- "
		::=  { invRackEntry  7 }


	invRackVersionNumber		 OBJECT-TYPE
		SYNTAX					 DisplayString( SIZE ( 1 .. 10 ) )
		MAX-ACCESS			 read-write
		STATUS					 current
		DESCRIPTION			 " -- "
		::=  { invRackEntry  8 }


	invRackDateOfManufacture		 OBJECT-TYPE
		SYNTAX					 DisplayString( SIZE ( 1 .. 30 ) )
		MAX-ACCESS			 read-write
		STATUS					 current
		DESCRIPTION			 " -- "
		::=  { invRackEntry  9 }


	invRackDateOfLastService		 OBJECT-TYPE
		SYNTAX					 DisplayString( SIZE ( 1 .. 30 ) )
		MAX-ACCESS			 read-write
		STATUS					 current
		DESCRIPTION			 " -- "
		::=  { invRackEntry  10 }


	invShelfTable		 OBJECT-TYPE
		SYNTAX					 SEQUENCE  OF	 InvShelfEntry
		MAX-ACCESS			 not-accessible
		STATUS					 current
		DESCRIPTION			 " -- "
		::=  { inventoryEquipment  2 }


	invShelfEntry		 OBJECT-TYPE
		SYNTAX					 InvShelfEntry
		MAX-ACCESS			 not-accessible
		STATUS					 current
		DESCRIPTION			 " -- "
		INDEX						{ invShelfRackNo,invShelfShelfNo }
		::=  { invShelfTable  1 }


	InvShelfEntry		 ::=  SEQUENCE {
		invShelfRackNo					Integer32,
		invShelfShelfNo					Integer32,
		invShelfRowStatus					RowStatus,
		invShelfType					DisplayString,
		invShelfDescription					DisplayString,
		invShelfVendorUnitTypeNumber					DisplayString,
		invShelfVendorName					DisplayString,
		invShelfSerialNumber					DisplayString,
		invShelfVersionNumber					DisplayString,
		invShelfDateOfManufacture					DisplayString,
		invShelfDateOfLastService					DisplayString
		}


	invShelfRackNo		 OBJECT-TYPE
		SYNTAX					 Integer32( 0 .. 0 )
		MAX-ACCESS			 not-accessible
		STATUS					 current
		DESCRIPTION			 " -- "
		::=  { invShelfEntry  1 }


	invShelfShelfNo		 OBJECT-TYPE
		SYNTAX					 Integer32( 0 .. 0 )
		MAX-ACCESS			 not-accessible
		STATUS					 current
		DESCRIPTION			 " -- "
		::=  { invShelfEntry  2 }


	invShelfRowStatus		 OBJECT-TYPE
		SYNTAX					 RowStatus
		MAX-ACCESS			 read-only
		STATUS					 current
		DESCRIPTION			 " -- "
		::=  { invShelfEntry  3 }


	invShelfType		 OBJECT-TYPE
		SYNTAX					 DisplayString( SIZE ( 1 .. 255 ) )
		MAX-ACCESS			 read-write
		STATUS					 current
		DESCRIPTION			 " -- "
		::=  { invShelfEntry  4 }


	invShelfDescription		 OBJECT-TYPE
		SYNTAX					 DisplayString( SIZE ( 1 .. 255 ) )
		MAX-ACCESS			 read-write
		STATUS					 current
		DESCRIPTION			 " -- "
		::=  { invShelfEntry  5 }


	invShelfVendorUnitTypeNumber		 OBJECT-TYPE
		SYNTAX					 DisplayString( SIZE ( 1 .. 20 ) )
		MAX-ACCESS			 read-write
		STATUS					 current
		DESCRIPTION			 " -- "
		::=  { invShelfEntry  6 }


	invShelfVendorName		 OBJECT-TYPE
		SYNTAX					 DisplayString( SIZE ( 1 .. 20 ) )
		MAX-ACCESS			 read-write
		STATUS					 current
		DESCRIPTION			 " -- "
		::=  { invShelfEntry  7 }


	invShelfSerialNumber		 OBJECT-TYPE
		SYNTAX					 DisplayString( SIZE ( 1 .. 50 ) )
		MAX-ACCESS			 read-write
		STATUS					 current
		DESCRIPTION			 " -- "
		::=  { invShelfEntry  8 }


	invShelfVersionNumber		 OBJECT-TYPE
		SYNTAX					 DisplayString( SIZE ( 1 .. 10 ) )
		MAX-ACCESS			 read-write
		STATUS					 current
		DESCRIPTION			 " -- "
		::=  { invShelfEntry  9 }


	invShelfDateOfManufacture		 OBJECT-TYPE
		SYNTAX					 DisplayString( SIZE ( 1 .. 30 ) )
		MAX-ACCESS			 read-write
		STATUS					 current
		DESCRIPTION			 " -- "
		::=  { invShelfEntry  10 }


	invShelfDateOfLastService		 OBJECT-TYPE
		SYNTAX					 DisplayString( SIZE ( 1 .. 30 ) )
		MAX-ACCESS			 read-write
		STATUS					 current
		DESCRIPTION			 " -- "
		::=  { invShelfEntry  11 }


	circuitPackTable		 OBJECT-TYPE
		SYNTAX					 SEQUENCE  OF	 CircuitPackEntry
		MAX-ACCESS			 not-accessible
		STATUS					 current
		DESCRIPTION			 " -- "
		::=  { inventoryEquipment  3 }


	circuitPackEntry		 OBJECT-TYPE
		SYNTAX					 CircuitPackEntry
		MAX-ACCESS			 not-accessible
		STATUS					 current
		DESCRIPTION			 " -- "
		INDEX						{ circuitPackRackNo,circuitPackShelfNo,circuitPackSlotNo }
		::=  { circuitPackTable  1 }


	CircuitPackEntry		 ::=  SEQUENCE {
		circuitPackRackNo					Integer32,
		circuitPackShelfNo					Integer32,
		circuitPackSlotNo					Integer32,
		circuitPackRowStatus					RowStatus,
		circuitPackInventoryUnitType					DisplayString,
		circuitPackVendorUnitFamilyType					DisplayString,
		circuitPackVendorUnitTypeNumber					DisplayString,
		circuitPackVersionNumber					DisplayString,
		circuitPackVendorName					DisplayString,
		circuitPackSerialNumber					DisplayString,
		circuitPackDateOfManufacture					DisplayString,
		circuitPackDateOfLastService					DisplayString,
		circuitPackManufacturerData					DisplayString,
		circuitPackManufacturerFlag					Integer32
		}


	circuitPackRackNo		 OBJECT-TYPE
		SYNTAX					 Integer32( 0 .. 0 )
		MAX-ACCESS			 not-accessible
		STATUS					 current
		DESCRIPTION			 " -- "
		::=  { circuitPackEntry  1 }


	circuitPackShelfNo		 OBJECT-TYPE
		SYNTAX					 Integer32( 0 .. 0 )
		MAX-ACCESS			 not-accessible
		STATUS					 current
		DESCRIPTION			 " -- "
		::=  { circuitPackEntry  2 }


	circuitPackSlotNo		 OBJECT-TYPE
		SYNTAX					 Integer32( 0 .. 16 )
		MAX-ACCESS			 not-accessible
		STATUS					 current
		DESCRIPTION			 " -- "
		::=  { circuitPackEntry  3 }


	circuitPackRowStatus		 OBJECT-TYPE
		SYNTAX					 RowStatus
		MAX-ACCESS			 read-only
		STATUS					 current
		DESCRIPTION			 " -- "
		::=  { circuitPackEntry  4 }


	circuitPackInventoryUnitType		 OBJECT-TYPE
		SYNTAX					 DisplayString( SIZE ( 1 .. 255 ) )
		MAX-ACCESS			 read-only
		STATUS					 current
		DESCRIPTION			 " -- "
		::=  { circuitPackEntry  5 }


	circuitPackVendorUnitFamilyType		 OBJECT-TYPE
		SYNTAX					 DisplayString( SIZE ( 1 .. 255 ) )
		MAX-ACCESS			 read-only
		STATUS					 current
		DESCRIPTION			 " -- "
		::=  { circuitPackEntry  6 }


	circuitPackVendorUnitTypeNumber		 OBJECT-TYPE
		SYNTAX					 DisplayString( SIZE ( 1 .. 255 ) )
		MAX-ACCESS			 read-only
		STATUS					 current
		DESCRIPTION			 " -- "
		::=  { circuitPackEntry  7 }


	circuitPackVersionNumber		 OBJECT-TYPE
		SYNTAX					 DisplayString( SIZE ( 1 .. 255 ) )
		MAX-ACCESS			 read-only
		STATUS					 current
		DESCRIPTION			 " -- "
		::=  { circuitPackEntry  8 }


	circuitPackVendorName		 OBJECT-TYPE
		SYNTAX					 DisplayString( SIZE ( 1 .. 255 ) )
		MAX-ACCESS			 read-only
		STATUS					 current
		DESCRIPTION			 " -- "
		::=  { circuitPackEntry  9 }


	circuitPackSerialNumber		 OBJECT-TYPE
		SYNTAX					 DisplayString( SIZE ( 1 .. 255 ) )
		MAX-ACCESS			 read-only
		STATUS					 current
		DESCRIPTION			 " -- "
		::=  { circuitPackEntry  10 }


	circuitPackDateOfManufacture		 OBJECT-TYPE
		SYNTAX					 DisplayString( SIZE ( 1 .. 255 ) )
		MAX-ACCESS			 read-only
		STATUS					 current
		DESCRIPTION			 " -- "
		::=  { circuitPackEntry  11 }


	circuitPackDateOfLastService		 OBJECT-TYPE
		SYNTAX					 DisplayString( SIZE ( 1 .. 255 ) )
		MAX-ACCESS			 read-only
		STATUS					 current
		DESCRIPTION			 " -- "
		::=  { circuitPackEntry  12 }


	circuitPackManufacturerData		 OBJECT-TYPE
		SYNTAX					 DisplayString( SIZE ( 1 .. 255 ) )
		MAX-ACCESS			 read-only
		STATUS					 current
		DESCRIPTION			 " -- "
		::=  { circuitPackEntry  13 }


	circuitPackManufacturerFlag		 OBJECT-TYPE
		SYNTAX					 Integer32( 0 .. 255 )
		MAX-ACCESS			 read-write
		STATUS					 current
		DESCRIPTION			 " -- "
		::=  { circuitPackEntry  14 }


	invRruTable		 OBJECT-TYPE
		SYNTAX					 SEQUENCE  OF	 InvRruEntry
		MAX-ACCESS			 not-accessible
		STATUS					 current
		DESCRIPTION			 " -- "
		::=  { inventoryEquipment  4 }


	invRruEntry		 OBJECT-TYPE
		SYNTAX					 InvRruEntry
		MAX-ACCESS			 not-accessible
		STATUS					 current
		DESCRIPTION			 " -- "
		INDEX						{ invRruNo }
		::=  { invRruTable  1 }


	InvRruEntry		 ::=  SEQUENCE {
		invRruNo					Integer32,
		invRruRowStatus					RowStatus,
		invRruInventoryUnitType					DisplayString,
		invRruVersionNumber					DisplayString,
		invRruManufactureName					DisplayString,
		invRruVendorName					DisplayString,
		invRruSerialNumber					DisplayString,
		invRruDateOfManufacture					DisplayString,
		invRruDateOfLastService					DisplayString,
		invRruManufacturerData					DisplayString,
		invRruRealUnitType					DisplayString
		}


	invRruNo		 OBJECT-TYPE
		SYNTAX					 Integer32( 0 .. 191 )
		MAX-ACCESS			 not-accessible
		STATUS					 current
		DESCRIPTION			 " -- "
		::=  { invRruEntry  1 }


	invRruRowStatus		 OBJECT-TYPE
		SYNTAX					 RowStatus
		MAX-ACCESS			 read-only
		STATUS					 current
		DESCRIPTION			 " -- "
		::=  { invRruEntry  2 }


	invRruInventoryUnitType		 OBJECT-TYPE
		SYNTAX					 DisplayString( SIZE ( 1 .. 255 ) )
		MAX-ACCESS			 read-only
		STATUS					 current
		DESCRIPTION			 " -- "
		::=  { invRruEntry  3 }


	invRruVersionNumber		 OBJECT-TYPE
		SYNTAX					 DisplayString( SIZE ( 1 .. 255 ) )
		MAX-ACCESS			 read-only
		STATUS					 current
		DESCRIPTION			 " -- "
		::=  { invRruEntry  4 }


	invRruManufactureName		 OBJECT-TYPE
		SYNTAX					 DisplayString( SIZE ( 1 .. 255 ) )
		MAX-ACCESS			 read-only
		STATUS					 current
		DESCRIPTION			 " -- "
		::=  { invRruEntry  5 }


	invRruVendorName		 OBJECT-TYPE
		SYNTAX					 DisplayString( SIZE ( 1 .. 255 ) )
		MAX-ACCESS			 read-only
		STATUS					 current
		DESCRIPTION			 " -- "
		::=  { invRruEntry  6 }


	invRruSerialNumber		 OBJECT-TYPE
		SYNTAX					 DisplayString( SIZE ( 1 .. 255 ) )
		MAX-ACCESS			 read-only
		STATUS					 current
		DESCRIPTION			 " -- "
		::=  { invRruEntry  7 }


	invRruDateOfManufacture		 OBJECT-TYPE
		SYNTAX					 DisplayString( SIZE ( 1 .. 255 ) )
		MAX-ACCESS			 read-only
		STATUS					 current
		DESCRIPTION			 " -- "
		::=  { invRruEntry  8 }


	invRruDateOfLastService		 OBJECT-TYPE
		SYNTAX					 DisplayString( SIZE ( 1 .. 255 ) )
		MAX-ACCESS			 read-only
		STATUS					 current
		DESCRIPTION			 " -- "
		::=  { invRruEntry  9 }


	invRruManufacturerData		 OBJECT-TYPE
		SYNTAX					 DisplayString( SIZE ( 1 .. 255 ) )
		MAX-ACCESS			 read-only
		STATUS					 current
		DESCRIPTION			 " -- "
		::=  { invRruEntry  10 }


	invRruRealUnitType		 OBJECT-TYPE
		SYNTAX					 DisplayString( SIZE ( 1 .. 255 ) )
		MAX-ACCESS			 read-only
		STATUS					 current
		DESCRIPTION			 " -- "
		::=  { invRruEntry  11 }


	daughterBoardTable		 OBJECT-TYPE
		SYNTAX					 SEQUENCE  OF	 DaughterBoardEntry
		MAX-ACCESS			 not-accessible
		STATUS					 current
		DESCRIPTION			 " -- "
		::=  { inventoryEquipment  5 }


	daughterBoardEntry		 OBJECT-TYPE
		SYNTAX					 DaughterBoardEntry
		MAX-ACCESS			 not-accessible
		STATUS					 current
		DESCRIPTION			 " -- "
		INDEX						{ daughterBoardRackNo,daughterBoardShelfNo,daughterBoardSlotNo,daughterBoardNo }
		::=  { daughterBoardTable  1 }


	DaughterBoardEntry		 ::=  SEQUENCE {
		daughterBoardRackNo					Integer32,
		daughterBoardShelfNo					Integer32,
		daughterBoardSlotNo					Integer32,
		daughterBoardNo					Integer32,
		daughterBoardRowStatus					RowStatus,
		daughterBoardInventoryUnitType					DisplayString,
		daughterBoardVendorUnitFamilyType					DisplayString,
		daughterBoardVendorUnitTypeNumber					DisplayString,
		daughterBoardVersionNumber					DisplayString,
		daughterBoardVendorName					DisplayString,
		daughterBoardSerialNumber					DisplayString,
		daughterBoardDateOfManufacture					DisplayString,
		daughterBoardDateOfLastService					DisplayString,
		daughterBoardManufacturerData					DisplayString
		}


	daughterBoardRackNo		 OBJECT-TYPE
		SYNTAX					 Integer32( 0 .. 0 )
		MAX-ACCESS			 not-accessible
		STATUS					 current
		DESCRIPTION			 " -- "
		::=  { daughterBoardEntry  1 }


	daughterBoardShelfNo		 OBJECT-TYPE
		SYNTAX					 Integer32( 0 .. 0 )
		MAX-ACCESS			 not-accessible
		STATUS					 current
		DESCRIPTION			 " -- "
		::=  { daughterBoardEntry  2 }


	daughterBoardSlotNo		 OBJECT-TYPE
		SYNTAX					 Integer32( 0 .. 16 )
		MAX-ACCESS			 not-accessible
		STATUS					 current
		DESCRIPTION			 " -- "
		::=  { daughterBoardEntry  3 }


	daughterBoardNo		 OBJECT-TYPE
		SYNTAX					 Integer32( 0 .. 16 )
		MAX-ACCESS			 not-accessible
		STATUS					 current
		DESCRIPTION			 " -- "
		::=  { daughterBoardEntry  4 }


	daughterBoardRowStatus		 OBJECT-TYPE
		SYNTAX					 RowStatus
		MAX-ACCESS			 read-only
		STATUS					 current
		DESCRIPTION			 " -- "
		::=  { daughterBoardEntry  5 }


	daughterBoardInventoryUnitType		 OBJECT-TYPE
		SYNTAX					 DisplayString( SIZE ( 1 .. 255 ) )
		MAX-ACCESS			 read-only
		STATUS					 current
		DESCRIPTION			 " -- "
		::=  { daughterBoardEntry  6 }


	daughterBoardVendorUnitFamilyType		 OBJECT-TYPE
		SYNTAX					 DisplayString( SIZE ( 1 .. 255 ) )
		MAX-ACCESS			 read-only
		STATUS					 current
		DESCRIPTION			 " -- "
		::=  { daughterBoardEntry  7 }


	daughterBoardVendorUnitTypeNumber		 OBJECT-TYPE
		SYNTAX					 DisplayString( SIZE ( 1 .. 255 ) )
		MAX-ACCESS			 read-only
		STATUS					 current
		DESCRIPTION			 " -- "
		::=  { daughterBoardEntry  8 }


	daughterBoardVersionNumber		 OBJECT-TYPE
		SYNTAX					 DisplayString( SIZE ( 1 .. 255 ) )
		MAX-ACCESS			 read-only
		STATUS					 current
		DESCRIPTION			 " -- "
		::=  { daughterBoardEntry  9 }


	daughterBoardVendorName		 OBJECT-TYPE
		SYNTAX					 DisplayString( SIZE ( 1 .. 255 ) )
		MAX-ACCESS			 read-only
		STATUS					 current
		DESCRIPTION			 " -- "
		::=  { daughterBoardEntry  10 }


	daughterBoardSerialNumber		 OBJECT-TYPE
		SYNTAX					 DisplayString( SIZE ( 1 .. 255 ) )
		MAX-ACCESS			 read-only
		STATUS					 current
		DESCRIPTION			 " -- "
		::=  { daughterBoardEntry  11 }


	daughterBoardDateOfManufacture		 OBJECT-TYPE
		SYNTAX					 DisplayString( SIZE ( 1 .. 255 ) )
		MAX-ACCESS			 read-only
		STATUS					 current
		DESCRIPTION			 " -- "
		::=  { daughterBoardEntry  12 }


	daughterBoardDateOfLastService		 OBJECT-TYPE
		SYNTAX					 DisplayString( SIZE ( 1 .. 255 ) )
		MAX-ACCESS			 read-only
		STATUS					 current
		DESCRIPTION			 " -- "
		::=  { daughterBoardEntry  13 }


	daughterBoardManufacturerData		 OBJECT-TYPE
		SYNTAX					 DisplayString( SIZE ( 1 .. 255 ) )
		MAX-ACCESS			 read-only
		STATUS					 current
		DESCRIPTION			 " -- "
		::=  { daughterBoardEntry  14 }


	invAntennaArrayTable		 OBJECT-TYPE
		SYNTAX					 SEQUENCE  OF	 InvAntennaArrayEntry
		MAX-ACCESS			 not-accessible
		STATUS					 current
		DESCRIPTION			 " -- "
		::=  { inventoryEquipment  6 }


	invAntennaArrayEntry		 OBJECT-TYPE
		SYNTAX					 InvAntennaArrayEntry
		MAX-ACCESS			 not-accessible
		STATUS					 current
		DESCRIPTION			 " -- "
		INDEX						{ invAntArrayNo }
		::=  { invAntennaArrayTable  1 }


	InvAntennaArrayEntry		 ::=  SEQUENCE {
		invAntArrayNo					Integer32,
		invAntArrayRowStatus					RowStatus,
		invAntArrayVendor					DisplayString,
		invAntArrayModel					DisplayString,
		invAntArraySerialNumber					DisplayString,
		invAntArrayLocalInfo					DisplayString
		}


	invAntArrayNo		 OBJECT-TYPE
		SYNTAX					 Integer32( 0 .. 191 )
		MAX-ACCESS			 not-accessible
		STATUS					 current
		DESCRIPTION			 " -- "
		::=  { invAntennaArrayEntry  1 }


	invAntArrayRowStatus		 OBJECT-TYPE
		SYNTAX					 RowStatus
		MAX-ACCESS			 read-only
		STATUS					 current
		DESCRIPTION			 " -- "
		::=  { invAntennaArrayEntry  2 }


	invAntArrayVendor		 OBJECT-TYPE
		SYNTAX					 DisplayString( SIZE ( 1 .. 20 ) )
		MAX-ACCESS			 read-write
		STATUS					 current
		DESCRIPTION			 " -- "
		::=  { invAntennaArrayEntry  3 }


	invAntArrayModel		 OBJECT-TYPE
		SYNTAX					 DisplayString( SIZE ( 1 .. 60 ) )
		MAX-ACCESS			 read-write
		STATUS					 current
		DESCRIPTION			 " -- "
		::=  { invAntennaArrayEntry  4 }


	invAntArraySerialNumber		 OBJECT-TYPE
		SYNTAX					 DisplayString( SIZE ( 1 .. 50 ) )
		MAX-ACCESS			 read-write
		STATUS					 current
		DESCRIPTION			 " -- "
		::=  { invAntennaArrayEntry  5 }


	invAntArrayLocalInfo		 OBJECT-TYPE
		SYNTAX					 DisplayString( SIZE ( 1 .. 100 ) )
		MAX-ACCESS			 read-write
		STATUS					 current
		DESCRIPTION			 " -- "
		::=  { invAntennaArrayEntry  6 }


	outDoorCabinetTable		 OBJECT-TYPE
		SYNTAX					 SEQUENCE  OF	 OutDoorCabinetEntry
		MAX-ACCESS			 not-accessible
		STATUS					 current
		DESCRIPTION			 " -- "
		::=  { inventoryEquipment  7 }


	outDoorCabinetEntry		 OBJECT-TYPE
		SYNTAX					 OutDoorCabinetEntry
		MAX-ACCESS			 not-accessible
		STATUS					 current
		DESCRIPTION			 " -- "
		INDEX						{ outDoorCabinetNo }
		::=  { outDoorCabinetTable  1 }


	OutDoorCabinetEntry		 ::=  SEQUENCE {
		outDoorCabinetNo					Integer32,
		outDoorCabinetRowStatus					RowStatus,
		outDoorCabinetPosition					DisplayString,
		outDoorCabinetSerialNumber					DisplayString,
		outDoorCabinetPowerSupplyType					DisplayString,
		outDoorCabinetLocalInfo					DisplayString
		}


	outDoorCabinetNo		 OBJECT-TYPE
		SYNTAX					 Integer32( 0 .. 0 )
		MAX-ACCESS			 not-accessible
		STATUS					 current
		DESCRIPTION			 " -- "
		::=  { outDoorCabinetEntry  1 }


	outDoorCabinetRowStatus		 OBJECT-TYPE
		SYNTAX					 RowStatus
		MAX-ACCESS			 read-create
		STATUS					 current
		DESCRIPTION			 " -- "
		::=  { outDoorCabinetEntry  2 }


	outDoorCabinetPosition		 OBJECT-TYPE
		SYNTAX					 DisplayString( SIZE ( 1 .. 100 ) )
		MAX-ACCESS			 read-create
		STATUS					 current
		DESCRIPTION			 " -- "
		::=  { outDoorCabinetEntry  3 }


	outDoorCabinetSerialNumber		 OBJECT-TYPE
		SYNTAX					 DisplayString( SIZE ( 1 .. 50 ) )
		MAX-ACCESS			 read-create
		STATUS					 current
		DESCRIPTION			 " -- "
		::=  { outDoorCabinetEntry  4 }


	outDoorCabinetPowerSupplyType		 OBJECT-TYPE
		SYNTAX					 DisplayString( SIZE ( 1 .. 20 ) )
		MAX-ACCESS			 read-create
		STATUS					 current
		DESCRIPTION			 " -- "
		::=  { outDoorCabinetEntry  5 }


	outDoorCabinetLocalInfo		 OBJECT-TYPE
		SYNTAX					 DisplayString( SIZE ( 1 .. 100 ) )
		MAX-ACCESS			 read-create
		STATUS					 current
		DESCRIPTION			 " -- "
		::=  { outDoorCabinetEntry  6 }


	invIocTable		 OBJECT-TYPE
		SYNTAX					 SEQUENCE  OF	 InvIocEntry
		MAX-ACCESS			 not-accessible
		STATUS					 current
		DESCRIPTION			 " -- "
		::=  { inventoryEquipment  8 }


	invIocEntry		 OBJECT-TYPE
		SYNTAX					 InvIocEntry
		MAX-ACCESS			 not-accessible
		STATUS					 current
		DESCRIPTION			 " -- "
		INDEX						{ invIocIndex }
		::=  { invIocTable  1 }


	InvIocEntry		 ::=  SEQUENCE {
		invIocIndex					Integer32,
		invIocRowStatus					RowStatus,
		invIocPosition					DisplayString,
		invIocSerialNumber					DisplayString,
		invIocPowerSupplyType					DisplayString,
		invIocLocalInfo					DisplayString
		}


	invIocIndex		 OBJECT-TYPE
		SYNTAX					 Integer32( 0 .. 0 )
		MAX-ACCESS			 not-accessible
		STATUS					 current
		DESCRIPTION			 " -- "
		::=  { invIocEntry  1 }


	invIocRowStatus		 OBJECT-TYPE
		SYNTAX					 RowStatus
		MAX-ACCESS			 read-create
		STATUS					 current
		DESCRIPTION			 " -- "
		::=  { invIocEntry  2 }


	invIocPosition		 OBJECT-TYPE
		SYNTAX					 DisplayString( SIZE ( 1 .. 100 ) )
		MAX-ACCESS			 read-create
		STATUS					 current
		DESCRIPTION			 " -- "
		::=  { invIocEntry  3 }


	invIocSerialNumber		 OBJECT-TYPE
		SYNTAX					 DisplayString( SIZE ( 1 .. 50 ) )
		MAX-ACCESS			 read-create
		STATUS					 current
		DESCRIPTION			 " -- "
		::=  { invIocEntry  4 }


	invIocPowerSupplyType		 OBJECT-TYPE
		SYNTAX					 DisplayString( SIZE ( 1 .. 20 ) )
		MAX-ACCESS			 read-create
		STATUS					 current
		DESCRIPTION			 " -- "
		::=  { invIocEntry  5 }


	invIocLocalInfo		 OBJECT-TYPE
		SYNTAX					 DisplayString( SIZE ( 1 .. 100 ) )
		MAX-ACCESS			 read-create
		STATUS					 current
		DESCRIPTION			 " -- "
		::=  { invIocEntry  6 }


	invRhubTable		 OBJECT-TYPE
		SYNTAX					 SEQUENCE  OF	 InvRhubEntry
		MAX-ACCESS			 not-accessible
		STATUS					 current
		DESCRIPTION			 " -- "
		::=  { inventoryEquipment  9 }


	invRhubEntry		 OBJECT-TYPE
		SYNTAX					 InvRhubEntry
		MAX-ACCESS			 not-accessible
		STATUS					 current
		DESCRIPTION			 " -- "
		INDEX						{ invRhubNo }
		::=  { invRhubTable  1 }


	InvRhubEntry		 ::=  SEQUENCE {
		invRhubNo					Integer32,
		invRhubRowStatus					RowStatus,
		invRhubInventoryUnitType					DisplayString,
		invRhubVersionNumber					DisplayString,
		invRhubManufactureName					DisplayString,
		invRhubVendorName					DisplayString,
		invRhubSerialNumber					DisplayString,
		invRhubDateOfManufacture					DisplayString,
		invRhubDateOfLastService					DisplayString,
		invRhubManufacturerData					DisplayString,
		invRhubRealUnitType					DisplayString
		}


	invRhubNo		 OBJECT-TYPE
		SYNTAX					 Integer32( 0 .. 191 )
		MAX-ACCESS			 not-accessible
		STATUS					 current
		DESCRIPTION			 " -- "
		::=  { invRhubEntry  1 }


	invRhubRowStatus		 OBJECT-TYPE
		SYNTAX					 RowStatus
		MAX-ACCESS			 read-only
		STATUS					 current
		DESCRIPTION			 " -- "
		::=  { invRhubEntry  2 }


	invRhubInventoryUnitType		 OBJECT-TYPE
		SYNTAX					 DisplayString( SIZE ( 1 .. 255 ) )
		MAX-ACCESS			 read-only
		STATUS					 current
		DESCRIPTION			 " -- "
		::=  { invRhubEntry  3 }


	invRhubVersionNumber		 OBJECT-TYPE
		SYNTAX					 DisplayString( SIZE ( 1 .. 255 ) )
		MAX-ACCESS			 read-only
		STATUS					 current
		DESCRIPTION			 " -- "
		::=  { invRhubEntry  4 }


	invRhubManufactureName		 OBJECT-TYPE
		SYNTAX					 DisplayString( SIZE ( 1 .. 255 ) )
		MAX-ACCESS			 read-only
		STATUS					 current
		DESCRIPTION			 " -- "
		::=  { invRhubEntry  5 }


	invRhubVendorName		 OBJECT-TYPE
		SYNTAX					 DisplayString( SIZE ( 1 .. 255 ) )
		MAX-ACCESS			 read-only
		STATUS					 current
		DESCRIPTION			 " -- "
		::=  { invRhubEntry  6 }


	invRhubSerialNumber		 OBJECT-TYPE
		SYNTAX					 DisplayString( SIZE ( 1 .. 255 ) )
		MAX-ACCESS			 read-only
		STATUS					 current
		DESCRIPTION			 " -- "
		::=  { invRhubEntry  7 }


	invRhubDateOfManufacture		 OBJECT-TYPE
		SYNTAX					 DisplayString( SIZE ( 1 .. 255 ) )
		MAX-ACCESS			 read-only
		STATUS					 current
		DESCRIPTION			 " -- "
		::=  { invRhubEntry  8 }


	invRhubDateOfLastService		 OBJECT-TYPE
		SYNTAX					 DisplayString( SIZE ( 1 .. 255 ) )
		MAX-ACCESS			 read-only
		STATUS					 current
		DESCRIPTION			 " -- "
		::=  { invRhubEntry  9 }


	invRhubManufacturerData		 OBJECT-TYPE
		SYNTAX					 DisplayString( SIZE ( 1 .. 255 ) )
		MAX-ACCESS			 read-only
		STATUS					 current
		DESCRIPTION			 " -- "
		::=  { invRhubEntry  10 }


	invRhubRealUnitType		 OBJECT-TYPE
		SYNTAX					 DisplayString( SIZE ( 1 .. 255 ) )
		MAX-ACCESS			 read-only
		STATUS					 current
		DESCRIPTION			 " -- "
		::=  { invRhubEntry  11 }


	inventoryPort		 OBJECT IDENTIFIER
		::=  { inventoryManagement  2 }


	invPortTable		 OBJECT-TYPE
		SYNTAX					 SEQUENCE  OF	 InvPortEntry
		MAX-ACCESS			 not-accessible
		STATUS					 current
		DESCRIPTION			 " -- "
		::=  { inventoryPort  1 }


	invPortEntry		 OBJECT-TYPE
		SYNTAX					 InvPortEntry
		MAX-ACCESS			 not-accessible
		STATUS					 current
		DESCRIPTION			 " -- "
		INDEX						{ invPortRackNo,invPortShelfNo,invPortSlotNo,invPortPortNo }
		::=  { invPortTable  1 }


	InvPortEntry		 ::=  SEQUENCE {
		invPortRackNo					Integer32,
		invPortShelfNo					Integer32,
		invPortSlotNo					Integer32,
		invPortPortNo					Integer32,
		invPortRowStatus					RowStatus,
		invPortType					INTEGER,
		invPortDescription					DisplayString,
		invPortLocation					DisplayString
		}


	invPortRackNo		 OBJECT-TYPE
		SYNTAX					 Integer32( 0 .. 0 )
		MAX-ACCESS			 not-accessible
		STATUS					 current
		DESCRIPTION			 " -- "
		::=  { invPortEntry  1 }


	invPortShelfNo		 OBJECT-TYPE
		SYNTAX					 Integer32( 0 .. 0 )
		MAX-ACCESS			 not-accessible
		STATUS					 current
		DESCRIPTION			 " -- "
		::=  { invPortEntry  2 }


	invPortSlotNo		 OBJECT-TYPE
		SYNTAX					 Integer32( 0 .. 16 )
		MAX-ACCESS			 not-accessible
		STATUS					 current
		DESCRIPTION			 " -- "
		::=  { invPortEntry  3 }


	invPortPortNo		 OBJECT-TYPE
		SYNTAX					 Integer32( 0 .. 5 )
		MAX-ACCESS			 not-accessible
		STATUS					 current
		DESCRIPTION			 " -- "
		::=  { invPortEntry  4 }


	invPortRowStatus		 OBJECT-TYPE
		SYNTAX					 RowStatus
		MAX-ACCESS			 read-only
		STATUS					 current
		DESCRIPTION			 " -- "
		::=  { invPortEntry  5 }


	invPortType		 OBJECT-TYPE
		SYNTAX					 INTEGER{ feport(1),e1port(2)  }
		MAX-ACCESS			 read-only
		STATUS					 current
		DESCRIPTION			 " -- "
		::=  { invPortEntry  6 }


	invPortDescription		 OBJECT-TYPE
		SYNTAX					 DisplayString( SIZE ( 1 .. 255 ) )
		MAX-ACCESS			 read-write
		STATUS					 current
		DESCRIPTION			 " -- "
		::=  { invPortEntry  7 }


	invPortLocation		 OBJECT-TYPE
		SYNTAX					 DisplayString( SIZE ( 1 .. 255 ) )
		MAX-ACCESS			 read-only
		STATUS					 current
		DESCRIPTION			 " -- "
		::=  { invPortEntry  8 }


	performanceManagement		 OBJECT IDENTIFIER
		::=  { lteCommon  8 }


	pmTask		 OBJECT IDENTIFIER
		::=  { performanceManagement  1 }


	pmTaskTable		 OBJECT-TYPE
		SYNTAX					 SEQUENCE  OF	 PmTaskEntry
		MAX-ACCESS			 not-accessible
		STATUS					 current
		DESCRIPTION			 " -- "
		::=  { pmTask  1 }


	pmTaskEntry		 OBJECT-TYPE
		SYNTAX					 PmTaskEntry
		MAX-ACCESS			 not-accessible
		STATUS					 current
		DESCRIPTION			 " -- "
		INDEX						{ pmTaskIndex }
		::=  { pmTaskTable  1 }


	PmTaskEntry		 ::=  SEQUENCE {
		pmTaskIndex					Integer32,
		pmTaskRowStatus					RowStatus,
		pmTaskDescription					DisplayString,
		pmTaskCollectInterval					INTEGER,
		pmTaskReportInterval					INTEGER,
		pmTaskCouterGroup					OBJECT IDENTIFIER,
		pmTaskReportManagerIndex					Integer32
		}


	pmTaskIndex		 OBJECT-TYPE
		SYNTAX					 Integer32( 1 .. 600 )
		MAX-ACCESS			 not-accessible
		STATUS					 current
		DESCRIPTION			 " -- "
		::=  { pmTaskEntry  1 }


	pmTaskRowStatus		 OBJECT-TYPE
		SYNTAX					 RowStatus
		MAX-ACCESS			 read-create
		STATUS					 current
		DESCRIPTION			 " -- "
		::=  { pmTaskEntry  2 }


	pmTaskDescription		 OBJECT-TYPE
		SYNTAX					 DisplayString( SIZE ( 1 .. 255 ) )
		MAX-ACCESS			 read-create
		STATUS					 current
		DESCRIPTION			 " -- "
		::=  { pmTaskEntry  3 }


	pmTaskCollectInterval		 OBJECT-TYPE
		SYNTAX					 INTEGER{ min5(5),min15(15),min30(30),min60(60)  }
		MAX-ACCESS			 read-create
		STATUS					 current
		DESCRIPTION			 " -- "
		::=  { pmTaskEntry  4 }


	pmTaskReportInterval		 OBJECT-TYPE
		SYNTAX					 INTEGER{ min5(5),min15(15),min30(30),min60(60)  }
		MAX-ACCESS			 read-create
		STATUS					 current
		DESCRIPTION			 " -- "
		::=  { pmTaskEntry  5 }


	pmTaskCouterGroup		 OBJECT-TYPE
		SYNTAX					 OBJECT IDENTIFIER
		MAX-ACCESS			 read-create
		STATUS					 current
		DESCRIPTION			 " -- "
		::=  { pmTaskEntry  6 }


	pmTaskReportManagerIndex		 OBJECT-TYPE
		SYNTAX					 Integer32( 0 .. 15 )
		MAX-ACCESS			 read-only
		STATUS					 current
		DESCRIPTION			 " -- "
		::=  { pmTaskEntry  7 }


	pmDerivedCounterExpressionDefine		 OBJECT IDENTIFIER
		::=  { performanceManagement  2 }


	pmExpressionTable		 OBJECT-TYPE
		SYNTAX					 SEQUENCE  OF	 PmExpressionEntry
		MAX-ACCESS			 not-accessible
		STATUS					 current
		DESCRIPTION			 " -- "
		::=  { pmDerivedCounterExpressionDefine  1 }


	pmExpressionEntry		 OBJECT-TYPE
		SYNTAX					 PmExpressionEntry
		MAX-ACCESS			 not-accessible
		STATUS					 current
		DESCRIPTION			 " -- "
		INDEX						{ pmExpressionIndex }
		::=  { pmExpressionTable  1 }


	PmExpressionEntry		 ::=  SEQUENCE {
		pmExpressionIndex					Integer32,
		pmExpressionRowStatus					RowStatus,
		pmExpression					DisplayString,
		pmExpressionName					DisplayString,
		pmExpressionValueType					INTEGER,
		pmExpressionCounterGroup					OBJECT IDENTIFIER,
		pmExpressionCounter					VariablePointer
		}


	pmExpressionIndex		 OBJECT-TYPE
		SYNTAX					 Integer32( 1 .. 1 )
		MAX-ACCESS			 not-accessible
		STATUS					 current
		DESCRIPTION			 " -- "
		::=  { pmExpressionEntry  1 }


	pmExpressionRowStatus		 OBJECT-TYPE
		SYNTAX					 RowStatus
		MAX-ACCESS			 read-create
		STATUS					 current
		DESCRIPTION			 " -- "
		::=  { pmExpressionEntry  2 }


	pmExpression		 OBJECT-TYPE
		SYNTAX					 DisplayString( SIZE ( 1 .. 255 ) )
		MAX-ACCESS			 read-create
		STATUS					 current
		DESCRIPTION			 " -- "
		::=  { pmExpressionEntry  3 }


	pmExpressionName		 OBJECT-TYPE
		SYNTAX					 DisplayString( SIZE ( 1 .. 255 ) )
		MAX-ACCESS			 read-create
		STATUS					 current
		DESCRIPTION			 " -- "
		::=  { pmExpressionEntry  4 }


	pmExpressionValueType		 OBJECT-TYPE
		SYNTAX					 INTEGER{ invalid(0),counter32(1),unsigned32(2),integer32(4)  }
		MAX-ACCESS			 read-create
		STATUS					 current
		DESCRIPTION			 " -- "
		::=  { pmExpressionEntry  5 }


	pmExpressionCounterGroup		 OBJECT-TYPE
		SYNTAX					 OBJECT IDENTIFIER
		MAX-ACCESS			 read-create
		STATUS					 current
		DESCRIPTION			 " -- "
		::=  { pmExpressionEntry  6 }


	pmExpressionCounter		 OBJECT-TYPE
		SYNTAX					 VariablePointer
		MAX-ACCESS			 read-create
		STATUS					 current
		DESCRIPTION			 " -- "
		::=  { pmExpressionEntry  7 }


	pmExpObjectTable		 OBJECT-TYPE
		SYNTAX					 SEQUENCE  OF	 PmExpObjectEntry
		MAX-ACCESS			 not-accessible
		STATUS					 current
		DESCRIPTION			 " -- "
		::=  { pmDerivedCounterExpressionDefine  2 }


	pmExpObjectEntry		 OBJECT-TYPE
		SYNTAX					 PmExpObjectEntry
		MAX-ACCESS			 not-accessible
		STATUS					 current
		DESCRIPTION			 " -- "
		INDEX						{ pmExpObjectExpressionIndex,pmExpObjectIndex }
		::=  { pmExpObjectTable  1 }


	PmExpObjectEntry		 ::=  SEQUENCE {
		pmExpObjectExpressionIndex					Integer32,
		pmExpObjectIndex					Integer32,
		pmExpObjectRowStatus					RowStatus,
		pmExpObjectID					VariablePointer
		}


	pmExpObjectExpressionIndex		 OBJECT-TYPE
		SYNTAX					 Integer32( 1 .. 1 )
		MAX-ACCESS			 not-accessible
		STATUS					 current
		DESCRIPTION			 " -- "
		::=  { pmExpObjectEntry  1 }


	pmExpObjectIndex		 OBJECT-TYPE
		SYNTAX					 Integer32( 1 .. 1 )
		MAX-ACCESS			 not-accessible
		STATUS					 current
		DESCRIPTION			 " -- "
		::=  { pmExpObjectEntry  2 }


	pmExpObjectRowStatus		 OBJECT-TYPE
		SYNTAX					 RowStatus
		MAX-ACCESS			 read-create
		STATUS					 current
		DESCRIPTION			 " -- "
		::=  { pmExpObjectEntry  3 }


	pmExpObjectID		 OBJECT-TYPE
		SYNTAX					 VariablePointer
		MAX-ACCESS			 read-create
		STATUS					 current
		DESCRIPTION			 " -- "
		::=  { pmExpObjectEntry  4 }


	pmExpValueTable		 OBJECT-TYPE
		SYNTAX					 SEQUENCE  OF	 PmExpValueEntry
		MAX-ACCESS			 not-accessible
		STATUS					 current
		DESCRIPTION			 " -- "
		::=  { pmDerivedCounterExpressionDefine  3 }


	pmExpValueEntry		 OBJECT-TYPE
		SYNTAX					 PmExpValueEntry
		MAX-ACCESS			 not-accessible
		STATUS					 current
		DESCRIPTION			 " -- "
		INDEX						{ pmExpValueExpressionIndex,pmExpValueInstanceIndex }
		::=  { pmExpValueTable  1 }


	PmExpValueEntry		 ::=  SEQUENCE {
		pmExpValueExpressionIndex					Integer32,
		pmExpValueInstanceIndex					Integer32,
		pmExpValueRowStatus					RowStatus,
		pmExpValueCounter32Val					Counter32,
		pmExpValueUnsigned32Val					Unsigned32,
		pmExpValueInteger32Val					Integer32
		}


	pmExpValueExpressionIndex		 OBJECT-TYPE
		SYNTAX					 Integer32( 1 .. 1 )
		MAX-ACCESS			 not-accessible
		STATUS					 current
		DESCRIPTION			 " -- "
		::=  { pmExpValueEntry  1 }


	pmExpValueInstanceIndex		 OBJECT-TYPE
		SYNTAX					 Integer32( 1 .. 1 )
		MAX-ACCESS			 not-accessible
		STATUS					 current
		DESCRIPTION			 " -- "
		::=  { pmExpValueEntry  2 }


	pmExpValueRowStatus		 OBJECT-TYPE
		SYNTAX					 RowStatus
		MAX-ACCESS			 read-only
		STATUS					 current
		DESCRIPTION			 " -- "
		::=  { pmExpValueEntry  3 }


	pmExpValueCounter32Val		 OBJECT-TYPE
		SYNTAX					 Counter32
		MAX-ACCESS			 read-only
		STATUS					 current
		DESCRIPTION			 " -- "
		::=  { pmExpValueEntry  4 }


	pmExpValueUnsigned32Val		 OBJECT-TYPE
		SYNTAX					 Unsigned32( 0 .. 4294967295 )
		MAX-ACCESS			 read-only
		STATUS					 current
		DESCRIPTION			 " -- "
		::=  { pmExpValueEntry  5 }


	pmExpValueInteger32Val		 OBJECT-TYPE
		SYNTAX					 Integer32( -2147483648 .. 2147483647 )
		MAX-ACCESS			 read-only
		STATUS					 current
		DESCRIPTION			 " -- "
		::=  { pmExpValueEntry  6 }


	equipmentInfo		 OBJECT IDENTIFIER
		::=  { lteCommon  9 }


	equipmentCommon		 OBJECT IDENTIFIER
		::=  { equipmentInfo  1 }


	equipNEType		 OBJECT-TYPE
		SYNTAX					 INTEGER{ unknown(0),tlb60a(2),emb5116tdlte(3),emb5132tdlte(4),emb5116(5),epc(21),ims(41)  }
		MAX-ACCESS			 read-only
		STATUS					 current
		DESCRIPTION			 " -- "
		::=  { equipmentCommon  1 }


	equipMIBVersion		 OBJECT-TYPE
		SYNTAX					 DisplayString( SIZE ( 1 .. 255 ) )
		MAX-ACCESS			 read-only
		STATUS					 current
		DESCRIPTION			 " -- "
		::=  { equipmentCommon  2 }


	equipMIBLastUpdate		 OBJECT-TYPE
		SYNTAX					 DisplayString( SIZE ( 1 .. 255 ) )
		MAX-ACCESS			 read-only
		STATUS					 current
		DESCRIPTION			 " -- "
		::=  { equipmentCommon  3 }


	equipMIBContact		 OBJECT-TYPE
		SYNTAX					 DisplayString( SIZE ( 1 .. 255 ) )
		MAX-ACCESS			 read-only
		STATUS					 current
		DESCRIPTION			 " -- "
		::=  { equipmentCommon  4 }


	equipLoginPassword		 OBJECT-TYPE
		SYNTAX					 DisplayString( SIZE ( 1 .. 255 ) )
		MAX-ACCESS			 read-write
		STATUS					 current
		DESCRIPTION			 " -- "
		::=  { equipmentCommon  5 }


	equipMIBDevVersion		 OBJECT-TYPE
		SYNTAX					 DisplayString( SIZE ( 1 .. 255 ) )
		MAX-ACCESS			 read-only
		STATUS					 current
		DESCRIPTION			 " -- "
		::=  { equipmentCommon  6 }


	equipStartupNotificationNode		 OBJECT IDENTIFIER
		::=  { equipmentInfo  2 }


	equipStartupNotifications		 OBJECT IDENTIFIER
		::=  { equipStartupNotificationNode  1 }


	equipStartupNotify		 NOTIFICATION-TYPE
		OBJECTS					 { equipStartupNotiNEType,equipStartupNotiInetAddrType,equipStartupNotiInetAddress,equipStartupNotiNEID,equipStartupNotiNEVersion,equipStartupNotiMIBVersion,equipStartupNotiCfgFileName,equipStartupNotiDataTypeIndicator,equipStartupNotiTime }
		STATUS					 current
		DESCRIPTION			 " -- "
		::=  { equipStartupNotifications  1 }


	equipStartupNotificationObjects		 OBJECT IDENTIFIER
		::=  { equipStartupNotificationNode  2 }


	equipStartupNotiNEType		 OBJECT-TYPE
		SYNTAX					 INTEGER{ unknown(0),tlb60a(2),emb5116tdlte(3),emb5116(5),epc(21),ims(41)  }
		MAX-ACCESS			 accessible-for-notify
		STATUS					 current
		DESCRIPTION			 " -- "
		::=  { equipStartupNotificationObjects  1 }


	equipStartupNotiInetAddrType		 OBJECT-TYPE
		SYNTAX					 InetAddressType
		MAX-ACCESS			 accessible-for-notify
		STATUS					 current
		DESCRIPTION			 " -- "
		::=  { equipStartupNotificationObjects  2 }


	equipStartupNotiInetAddress		 OBJECT-TYPE
		SYNTAX					 InetAddress
		MAX-ACCESS			 accessible-for-notify
		STATUS					 current
		DESCRIPTION			 " -- "
		::=  { equipStartupNotificationObjects  3 }


	equipStartupNotiNEID		 OBJECT-TYPE
		SYNTAX					 Unsigned32( 0 .. 4294967295 )
		MAX-ACCESS			 accessible-for-notify
		STATUS					 current
		DESCRIPTION			 " -- "
		::=  { equipStartupNotificationObjects  4 }


	equipStartupNotiNEVersion		 OBJECT-TYPE
		SYNTAX					 OBJECT IDENTIFIER
		MAX-ACCESS			 accessible-for-notify
		STATUS					 current
		DESCRIPTION			 " -- "
		::=  { equipStartupNotificationObjects  5 }


	equipStartupNotiMIBVersion		 OBJECT-TYPE
		SYNTAX					 OBJECT IDENTIFIER
		MAX-ACCESS			 accessible-for-notify
		STATUS					 current
		DESCRIPTION			 " -- "
		::=  { equipStartupNotificationObjects  6 }


	equipStartupNotiCfgFileName		 OBJECT-TYPE
		SYNTAX					 DisplayString( SIZE ( 1 .. 255 ) )
		MAX-ACCESS			 accessible-for-notify
		STATUS					 current
		DESCRIPTION			 " -- "
		::=  { equipStartupNotificationObjects  7 }


	equipStartupNotiDataTypeIndicator		 OBJECT-TYPE
		SYNTAX					 INTEGER{ startup(1),reConnect(2)  }
		MAX-ACCESS			 accessible-for-notify
		STATUS					 current
		DESCRIPTION			 " -- "
		::=  { equipStartupNotificationObjects  8 }


	equipStartupNotiTime		 OBJECT-TYPE
		SYNTAX					 DateAndTime
		MAX-ACCESS			 accessible-for-notify
		STATUS					 current
		DESCRIPTION			 " -- "
		::=  { equipStartupNotificationObjects  9 }


	managerTable		 OBJECT-TYPE
		SYNTAX					 SEQUENCE  OF	 ManagerEntry
		MAX-ACCESS			 not-accessible
		STATUS					 current
		DESCRIPTION			 " -- "
		::=  { equipmentInfo  3 }


	managerEntry		 OBJECT-TYPE
		SYNTAX					 ManagerEntry
		MAX-ACCESS			 not-accessible
		STATUS					 current
		DESCRIPTION			 " -- "
		INDEX						{ managerIndex }
		::=  { managerTable  1 }


	ManagerEntry		 ::=  SEQUENCE {
		managerIndex					Integer32,
		managerRowStatus					RowStatus,
		managerType					INTEGER,
		managerInetAddrType					InetAddressType,
		managerInetAddress					InetAddress,
		managerHeartbeatInterval					Unsigned32,
		managerHeartbeatToleranceRetrys					Unsigned32,
		managerOnlineState					INTEGER,
		managerTrapPort					Integer32,
		managerPerformanceReportSwitch					INTEGER,
		managerStatelessAlarmReportSwitch					INTEGER,
		managerAlterationReportSwitch					INTEGER,
		managerKickTrigger					INTEGER,
		managerMode					INTEGER
		}


	managerIndex		 OBJECT-TYPE
		SYNTAX					 Integer32( 0 .. 15 )
		MAX-ACCESS			 not-accessible
		STATUS					 current
		DESCRIPTION			 " -- "
		::=  { managerEntry  1 }


	managerRowStatus		 OBJECT-TYPE
		SYNTAX					 RowStatus
		MAX-ACCESS			 read-only
		STATUS					 current
		DESCRIPTION			 " -- "
		::=  { managerEntry  2 }


	managerType		 OBJECT-TYPE
		SYNTAX					 INTEGER{ omc(1),dci(2),lmt(4),patrol(16)  }
		MAX-ACCESS			 read-only
		STATUS					 current
		DESCRIPTION			 " -- "
		::=  { managerEntry  3 }


	managerInetAddrType		 OBJECT-TYPE
		SYNTAX					 InetAddressType
		MAX-ACCESS			 read-only
		STATUS					 current
		DESCRIPTION			 " -- "
		::=  { managerEntry  4 }


	managerInetAddress		 OBJECT-TYPE
		SYNTAX					 InetAddress
		MAX-ACCESS			 read-only
		STATUS					 current
		DESCRIPTION			 " -- "
		::=  { managerEntry  5 }


	managerHeartbeatInterval		 OBJECT-TYPE
		SYNTAX					 Unsigned32( 0 .. 4294967295 )
		MAX-ACCESS			 read-only
		STATUS					 current
		DESCRIPTION			 " -- "
		::=  { managerEntry  6 }


	managerHeartbeatToleranceRetrys		 OBJECT-TYPE
		SYNTAX					 Unsigned32( 0 .. 4294967295 )
		MAX-ACCESS			 read-only
		STATUS					 current
		DESCRIPTION			 " -- "
		::=  { managerEntry  7 }


	managerOnlineState		 OBJECT-TYPE
		SYNTAX					 INTEGER{ offline(0),online(1)  }
		MAX-ACCESS			 read-only
		STATUS					 current
		DESCRIPTION			 " -- "
		::=  { managerEntry  8 }


	managerTrapPort		 OBJECT-TYPE
		SYNTAX					 Integer32( -2147483648 .. 2147483647 )
		MAX-ACCESS			 read-only
		STATUS					 current
		DESCRIPTION			 " -- "
		::=  { managerEntry  9 }


	managerPerformanceReportSwitch		 OBJECT-TYPE
		SYNTAX					 INTEGER{ off(0),on(1)  }
		MAX-ACCESS			 read-write
		STATUS					 current
		DESCRIPTION			 " -- "
		::=  { managerEntry  10 }


	managerStatelessAlarmReportSwitch		 OBJECT-TYPE
		SYNTAX					 INTEGER{ off(0),on(1)  }
		MAX-ACCESS			 read-write
		STATUS					 current
		DESCRIPTION			 " -- "
		::=  { managerEntry  11 }


	managerAlterationReportSwitch		 OBJECT-TYPE
		SYNTAX					 INTEGER{ off(0),on(1)  }
		MAX-ACCESS			 read-write
		STATUS					 current
		DESCRIPTION			 " -- "
		::=  { managerEntry  12 }


	managerKickTrigger		 OBJECT-TYPE
		SYNTAX					 INTEGER{ off(0),on(1)  }
		MAX-ACCESS			 read-write
		STATUS					 current
		DESCRIPTION			 " -- "
		::=  { managerEntry  14 }


	managerMode		 OBJECT-TYPE
		SYNTAX					 INTEGER{ tds(0),tdl(1),dual(2)  }
		MAX-ACCESS			 read-only
		STATUS					 current
		DESCRIPTION			 " -- "
		::=  { managerEntry  15 }


	equipmentSysInfo		 OBJECT IDENTIFIER
		::=  { equipmentInfo  4 }


	equipNEID		 OBJECT-TYPE
		SYNTAX					 Unsigned32( 0 .. 1048575 )
		MAX-ACCESS			 read-write
		STATUS					 current
		DESCRIPTION			 " -- "
		::=  { equipmentSysInfo  1 }


	equipPhyID		 OBJECT-TYPE
		SYNTAX					 DisplayString( SIZE ( 12 .. 12 ) )
		MAX-ACCESS			 read-only
		STATUS					 current
		DESCRIPTION			 " -- "
		::=  { equipmentSysInfo  2 }


	equipFriendName		 OBJECT-TYPE
		SYNTAX					 DisplayString( SIZE ( 1 .. 255 ) )
		MAX-ACCESS			 read-write
		STATUS					 current
		DESCRIPTION			 " -- "
		::=  { equipmentSysInfo  3 }


	equipLongitude		 OBJECT-TYPE
		SYNTAX					 DisplayString( SIZE ( 1 .. 255 ) )
		MAX-ACCESS			 read-write
		STATUS					 current
		DESCRIPTION			 " -- "
		::=  { equipmentSysInfo  4 }


	equipLatitude		 OBJECT-TYPE
		SYNTAX					 DisplayString( SIZE ( 1 .. 255 ) )
		MAX-ACCESS			 read-write
		STATUS					 current
		DESCRIPTION			 " -- "
		::=  { equipmentSysInfo  5 }


	equipElevation		 OBJECT-TYPE
		SYNTAX					 DisplayString( SIZE ( 1 .. 255 ) )
		MAX-ACCESS			 read-write
		STATUS					 current
		DESCRIPTION			 " -- "
		::=  { equipmentSysInfo  6 }


	equipDescription		 OBJECT-TYPE
		SYNTAX					 DisplayString( SIZE ( 1 .. 255 ) )
		MAX-ACCESS			 read-write
		STATUS					 current
		DESCRIPTION			 " -- "
		::=  { equipmentSysInfo  7 }


	equipContact		 OBJECT-TYPE
		SYNTAX					 DisplayString( SIZE ( 1 .. 255 ) )
		MAX-ACCESS			 read-write
		STATUS					 current
		DESCRIPTION			 " -- "
		::=  { equipmentSysInfo  8 }


	equipLocation		 OBJECT-TYPE
		SYNTAX					 DisplayString( SIZE ( 1 .. 255 ) )
		MAX-ACCESS			 read-write
		STATUS					 current
		DESCRIPTION			 " -- "
		::=  { equipmentSysInfo  9 }


	equipCurrentTime		 OBJECT-TYPE
		SYNTAX					 DateAndTime
		MAX-ACCESS			 read-only
		STATUS					 current
		DESCRIPTION			 " -- "
		::=  { equipmentSysInfo  10 }


	equipUpTime		 OBJECT-TYPE
		SYNTAX					 DateAndTime
		MAX-ACCESS			 read-only
		STATUS					 current
		DESCRIPTION			 " -- "
		::=  { equipmentSysInfo  11 }


	equipProceduralStatus		 OBJECT-TYPE
		SYNTAX					 INTEGER{ initializationRequired(0),notInitialized(1),initializing(2),reporting(3),terminating(4)  }
		MAX-ACCESS			 read-only
		STATUS					 current
		DESCRIPTION			 " -- "
		::=  { equipmentSysInfo  12 }


	equipOperationalState		 OBJECT-TYPE
		SYNTAX					 INTEGER{ disabled(0),enabled(1)  }
		MAX-ACCESS			 read-only
		STATUS					 current
		DESCRIPTION			 " -- "
		::=  { equipmentSysInfo  13 }


	equipMaintenceState		 OBJECT-TYPE
		SYNTAX					 INTEGER{ waitForEstablish(0),establishing(1),inMaintenance(2),inService(3)  }
		MAX-ACCESS			 read-write
		STATUS					 current
		DESCRIPTION			 " -- "
		::=  { equipmentSysInfo  15 }


	equipEnvironmentMonitorMode		 OBJECT-TYPE
		SYNTAX					 BITS{ oab(0),monitor(1),rootnode(2),air(3),heatEx(4)  }
		MAX-ACCESS			 read-write
		STATUS					 current
		DESCRIPTION			 " -- "
		::=  { equipmentSysInfo  16 }


	equipResetTrigger		 OBJECT-TYPE
		SYNTAX					 INTEGER{ off(0),on(1),onWithNoDfg(2)  }
		MAX-ACCESS			 read-write
		STATUS					 current
		DESCRIPTION			 " -- "
		::=  { equipmentSysInfo  17 }


	equipStartupStage		 OBJECT-TYPE
		SYNTAX					 INTEGER{ startupinfoget(1),authentication(2),omlinkcreate(3),synchronization(4),configuring(5),configured(6)  }
		MAX-ACCESS			 read-only
		STATUS					 current
		DESCRIPTION			 " -- "
		::=  { equipmentSysInfo  21 }


	equipInitCfgStopTrigger		 OBJECT-TYPE
		SYNTAX					 INTEGER{ off(0),on(1)  }
		MAX-ACCESS			 read-write
		STATUS					 current
		DESCRIPTION			 " -- "
		::=  { equipmentSysInfo  22 }


	equipSysFunctionId		 OBJECT-TYPE
		SYNTAX					 Unsigned32( 0 .. 4294967295 )
		MAX-ACCESS			 read-write
		STATUS					 current
		DESCRIPTION			 " -- "
		::=  { equipmentSysInfo  23 }


	equipMaintenceStatePDFSwitch		 OBJECT-TYPE
		SYNTAX					 INTEGER{ off(0),on(1)  }
		MAX-ACCESS			 read-write
		STATUS					 current
		DESCRIPTION			 " -- "
		::=  { equipmentSysInfo  24 }


	equipDisguiseEquipMaintenceState		 OBJECT-TYPE
		SYNTAX					 INTEGER{ inMaintenance(2),inService(3)  }
		MAX-ACCESS			 read-write
		STATUS					 current
		DESCRIPTION			 " -- "
		::=  { equipmentSysInfo  28 }


	equipLoAutoUpdateSwitch		 OBJECT-TYPE
		SYNTAX					 INTEGER{ off(0),on(1)  }
		MAX-ACCESS			 read-write
		STATUS					 current
		DESCRIPTION			 " -- "
		::=  { equipmentSysInfo  29 }


	board		 OBJECT IDENTIFIER
		::=  { equipmentInfo  5 }


	boardTable		 OBJECT-TYPE
		SYNTAX					 SEQUENCE  OF	 BoardEntry
		MAX-ACCESS			 not-accessible
		STATUS					 current
		DESCRIPTION			 " -- "
		::=  { board  1 }


	boardEntry		 OBJECT-TYPE
		SYNTAX					 BoardEntry
		MAX-ACCESS			 not-accessible
		STATUS					 current
		DESCRIPTION			 " -- "
		INDEX						{ boardRackNo,boardShelfNo,boardSlotNo }
		::=  { boardTable  1 }


	BoardEntry		 ::=  SEQUENCE {
		boardRackNo					Integer32,
		boardShelfNo					Integer32,
		boardSlotNo					Integer32,
		boardRowStatus					RowStatus,
		boardHardwareType					INTEGER,
		boardApplicationType					INTEGER,
		boardDescription					DisplayString,
		boardHardwareTypeMatchStatus					INTEGER,
		boardUpTime					DateAndTime,
		boardStartupFailureReason					DisplayString,
		boardProceduralStatus					INTEGER,
		boardOperationalState					INTEGER,
		boardAdministrativeState					INTEGER,
		boardPowerState					INTEGER,
		boardAlarmStatus					BITS,
		boardAlarmStatics					Unsigned32Array,
		boardUpdateState					INTEGER,
		boardResetTrigger					INTEGER,
		boardPcbVersion					DisplayString,
		boardContainMainCpu					INTEGER,
		boardFpgaFrameType					INTEGER,
		boardPowerManufacturer					INTEGER,
		boardPowerType					INTEGER,
		boardEmdSeriesMode					INTEGER,
		boardTimeslotoffset					INTEGER,
		boardBspMainStatus					INTEGER,
		boardBspBackupStatus					INTEGER,
		boardSBootUpdateTrigger					INTEGER
		}


	boardRackNo		 OBJECT-TYPE
		SYNTAX					 Integer32( 0 .. 0 )
		MAX-ACCESS			 not-accessible
		STATUS					 current
		DESCRIPTION			 " -- "
		::=  { boardEntry  1 }


	boardShelfNo		 OBJECT-TYPE
		SYNTAX					 Integer32( 0 .. 0 )
		MAX-ACCESS			 not-accessible
		STATUS					 current
		DESCRIPTION			 " -- "
		::=  { boardEntry  2 }


	boardSlotNo		 OBJECT-TYPE
		SYNTAX					 Integer32( 0 .. 16 )
		MAX-ACCESS			 not-accessible
		STATUS					 current
		DESCRIPTION			 " -- "
		::=  { boardEntry  3 }


	boardRowStatus		 OBJECT-TYPE
		SYNTAX					 RowStatus
		MAX-ACCESS			 read-only
		STATUS					 current
		DESCRIPTION			 " -- "
		::=  { boardEntry  4 }


	boardHardwareType		 OBJECT-TYPE
		SYNTAX					 INTEGER{ unknown(0),riuDof(48),riuE1(49),riuA(50),gcu(52),ccu(54),ceu(56),bbu(58),aifur6C8A(59),ifur3C6A(60),ifur6C1A(61),ifur3C4A(62),aifur9C1A(63),gru(64),ctu(65),iiu(66),bcu(67),biu(68),accu(70),abbut(71),abbuf(72),eiuE1(73),synu(74),eiuDof(75),aifur12C1A(77),aifur9C8A(78),scta(97),bpia(98),bpoa(99),gpscu(100),emu(101),geu(102),emau(103),etpa(104),etpd(105),psu(106),fcu(107),bpoc(108),bpoe(109),emdu(110),etpc(111),bpof(128),etpe(129),sctc(130),sctd(141),mmba(142),bpog(143),bpoh(177),scte(178),mmbc(224),sctf(240),bpoi(241)  }
		MAX-ACCESS			 read-only
		STATUS					 current
		DESCRIPTION			 " -- "
		::=  { boardEntry  5 }


	boardApplicationType		 OBJECT-TYPE
		SYNTAX					 INTEGER{ unknown(0),riuDof(48),riuE1(49),riuA(50),gcu(52),ccu(54),ceu(56),bbu(58),aifur6C8A(59),ifur3C6A(60),ifur6C1A(61),ifur3C4A(62),aifur9C1A(63),gru(64),ctu(65),iiu(66),bcu(67),biu(68),accu(70),abbut(71),abbuf(72),eiuE1(73),synu(74),eiuDof(75),aifur12C1A(77),aifur9C8A(78),scta(97),bpia(98),bpoa(99),gpscu(100),emu(101),geu(102),emau(103),etpa(104),etpd(105),psu(106),fcu(107),bpoc(108),bpoe(109),emdu(110),etpc(111),bpof(128),etpe(129),sctc(130),sctd(141),mmba(142),bpog(143),bpoh(177),scte(178),mmbc(224),sctf(240),bpoi(241)  }
		MAX-ACCESS			 read-only
		STATUS					 current
		DESCRIPTION			 " -- "
		::=  { boardEntry  6 }


	boardDescription		 OBJECT-TYPE
		SYNTAX					 DisplayString( SIZE ( 1 .. 255 ) )
		MAX-ACCESS			 read-only
		STATUS					 current
		DESCRIPTION			 " -- "
		::=  { boardEntry  7 }


	boardHardwareTypeMatchStatus		 OBJECT-TYPE
		SYNTAX					 INTEGER{ notMatched(0),matched(1)  }
		MAX-ACCESS			 read-only
		STATUS					 current
		DESCRIPTION			 " -- "
		::=  { boardEntry  8 }


	boardUpTime		 OBJECT-TYPE
		SYNTAX					 DateAndTime
		MAX-ACCESS			 read-only
		STATUS					 current
		DESCRIPTION			 " -- "
		::=  { boardEntry  9 }


	boardStartupFailureReason		 OBJECT-TYPE
		SYNTAX					 DisplayString( SIZE ( 1 .. 255 ) )
		MAX-ACCESS			 read-only
		STATUS					 current
		DESCRIPTION			 " -- "
		::=  { boardEntry  10 }


	boardProceduralStatus		 OBJECT-TYPE
		SYNTAX					 INTEGER{ initializationRequired(0),notInitialized(1),initializing(2),reporting(3),terminating(4)  }
		MAX-ACCESS			 read-only
		STATUS					 current
		DESCRIPTION			 " -- "
		::=  { boardEntry  11 }


	boardOperationalState		 OBJECT-TYPE
		SYNTAX					 INTEGER{ disabled(0),enabled(1)  }
		MAX-ACCESS			 read-only
		STATUS					 current
		DESCRIPTION			 " -- "
		::=  { boardEntry  12 }


	boardAdministrativeState		 OBJECT-TYPE
		SYNTAX					 INTEGER{ locked(0),unlocked(1),shuttingDown(2)  }
		MAX-ACCESS			 read-write
		STATUS					 current
		DESCRIPTION			 " -- "
		::=  { boardEntry  14 }


	boardPowerState		 OBJECT-TYPE
		SYNTAX					 INTEGER{ normal(0),powerOff(1),highTempPowerOff(2)  }
		MAX-ACCESS			 read-write
		STATUS					 current
		DESCRIPTION			 " -- "
		::=  { boardEntry  16 }


	boardAlarmStatus		 OBJECT-TYPE
		SYNTAX					 BITS{ underRepair(0),critical(1),major(2),minor(3),alarmOutstanding(4)  }
		MAX-ACCESS			 read-only
		STATUS					 current
		DESCRIPTION			 " -- "
		::=  { boardEntry  17 }


	boardAlarmStatics		 OBJECT-TYPE
		SYNTAX					 Unsigned32Array
		MAX-ACCESS			 read-only
		STATUS					 current
		DESCRIPTION			 " -- "
		::=  { boardEntry  18 }


	boardUpdateState		 OBJECT-TYPE
		SYNTAX					 INTEGER{ normal(0),download(1),upgrade(2)  }
		MAX-ACCESS			 read-only
		STATUS					 current
		DESCRIPTION			 " -- "
		::=  { boardEntry  19 }


	boardResetTrigger		 OBJECT-TYPE
		SYNTAX					 INTEGER{ off(0),on(1)  }
		MAX-ACCESS			 read-write
		STATUS					 current
		DESCRIPTION			 " -- "
		::=  { boardEntry  20 }


	boardPcbVersion		 OBJECT-TYPE
		SYNTAX					 DisplayString( SIZE ( 1 .. 255 ) )
		MAX-ACCESS			 read-only
		STATUS					 current
		DESCRIPTION			 " -- "
		::=  { boardEntry  21 }


	boardContainMainCpu		 OBJECT-TYPE
		SYNTAX					 INTEGER{ false(0),true(1)  }
		MAX-ACCESS			 read-only
		STATUS					 current
		DESCRIPTION			 " -- "
		::=  { boardEntry  22 }


	boardFpgaFrameType		 OBJECT-TYPE
		SYNTAX					 INTEGER{ tdriTd(0),tdriLte(1),cpri(2),cprihdlc(3)  }
		MAX-ACCESS			 read-write
		STATUS					 current
		DESCRIPTION			 " -- "
		::=  { boardEntry  23 }


	boardPowerManufacturer		 OBJECT-TYPE
		SYNTAX					 INTEGER{ unknown(0),emerson(1),goldpower(2),raypower(4),anpower(8),synQor(16),dctec(32)  }
		MAX-ACCESS			 read-only
		STATUS					 current
		DESCRIPTION			 " -- "
		::=  { boardEntry  25 }


	boardPowerType		 OBJECT-TYPE
		SYNTAX					 INTEGER{ unknown(0),dc(64),ac(128)  }
		MAX-ACCESS			 read-only
		STATUS					 current
		DESCRIPTION			 " -- "
		::=  { boardEntry  26 }


	boardEmdSeriesMode		 OBJECT-TYPE
		SYNTAX					 INTEGER{ invalid(0),input(1),output(2)  }
		MAX-ACCESS			 read-write
		STATUS					 current
		DESCRIPTION			 " -- "
		::=  { boardEntry  27 }


	boardTimeslotoffset		 OBJECT-TYPE
		SYNTAX					 INTEGER{ none(0),us700(1),us1025(2)  }
		MAX-ACCESS			 read-only
		STATUS					 current
		DESCRIPTION			 " -- "
		::=  { boardEntry  28 }


	boardBspMainStatus		 OBJECT-TYPE
		SYNTAX					 INTEGER{ unknown(-1),unAvailable(0),available(1),unLoad(2)  }
		MAX-ACCESS			 read-only
		STATUS					 current
		DESCRIPTION			 " -- "
		::=  { boardEntry  29 }


	boardBspBackupStatus		 OBJECT-TYPE
		SYNTAX					 INTEGER{ unknown(-1),unAvailable(0),available(1),unLoad(2)  }
		MAX-ACCESS			 read-only
		STATUS					 current
		DESCRIPTION			 " -- "
		::=  { boardEntry  30 }


	boardSBootUpdateTrigger		 OBJECT-TYPE
		SYNTAX					 INTEGER{ off(0),on(1)  }
		MAX-ACCESS			 read-write
		STATUS					 current
		DESCRIPTION			 " -- "
		::=  { boardEntry  31 }


	boardSwapControl		 OBJECT IDENTIFIER
		::=  { board  2 }


	boardSwapTrigger		 OBJECT-TYPE
		SYNTAX					 INTEGER{ off(0),on(1)  }
		MAX-ACCESS			 read-write
		STATUS					 current
		DESCRIPTION			 " -- "
		::=  { boardSwapControl  1 }


	boardSwapType		 OBJECT-TYPE
		SYNTAX					 INTEGER{ notSpecifyDest(0),specifyDest(1)  }
		MAX-ACCESS			 read-write
		STATUS					 current
		DESCRIPTION			 " -- "
		::=  { boardSwapControl  2 }


	boardSwapSourceRackNo		 OBJECT-TYPE
		SYNTAX					 Integer32( 0 .. 0 )
		MAX-ACCESS			 read-write
		STATUS					 current
		DESCRIPTION			 " -- "
		::=  { boardSwapControl  3 }


	boardSwapSourceShelfNo		 OBJECT-TYPE
		SYNTAX					 Integer32( 0 .. 0 )
		MAX-ACCESS			 read-write
		STATUS					 current
		DESCRIPTION			 " -- "
		::=  { boardSwapControl  4 }


	boardSwapSourceSlotNo		 OBJECT-TYPE
		SYNTAX					 Integer32( 0 .. 16 )
		MAX-ACCESS			 read-write
		STATUS					 current
		DESCRIPTION			 " -- "
		::=  { boardSwapControl  5 }


	boardSwapDestRackNo		 OBJECT-TYPE
		SYNTAX					 Integer32( 0 .. 0 )
		MAX-ACCESS			 read-write
		STATUS					 current
		DESCRIPTION			 " -- "
		::=  { boardSwapControl  6 }


	boardSwapDestShelfNo		 OBJECT-TYPE
		SYNTAX					 Integer32( 0 .. 0 )
		MAX-ACCESS			 read-write
		STATUS					 current
		DESCRIPTION			 " -- "
		::=  { boardSwapControl  7 }


	boardSwapDestSlotNo		 OBJECT-TYPE
		SYNTAX					 Integer32( 0 .. 16 )
		MAX-ACCESS			 read-write
		STATUS					 current
		DESCRIPTION			 " -- "
		::=  { boardSwapControl  8 }


	boardProcessor		 OBJECT IDENTIFIER
		::=  { equipmentInfo  6 }


	processorTable		 OBJECT-TYPE
		SYNTAX					 SEQUENCE  OF	 ProcessorEntry
		MAX-ACCESS			 not-accessible
		STATUS					 current
		DESCRIPTION			 " -- "
		::=  { boardProcessor  1 }


	processorEntry		 OBJECT-TYPE
		SYNTAX					 ProcessorEntry
		MAX-ACCESS			 not-accessible
		STATUS					 current
		DESCRIPTION			 " -- "
		INDEX						{ procRackNo,procShelfNo,procSlotNo,procIndexOnBoard }
		::=  { processorTable  1 }


	ProcessorEntry		 ::=  SEQUENCE {
		procRackNo					Integer32,
		procShelfNo					Integer32,
		procSlotNo					Integer32,
		procIndexOnBoard					Integer32,
		procRowStatus					RowStatus,
		procType					INTEGER,
		procDescription					DisplayString,
		procProceduralStatus					INTEGER,
		procOperationalState					INTEGER,
		procCPUCheckInterval					Integer32,
		procCoreNum					Integer32,
		procResetTrigger					INTEGER,
		procStatCPUOccupation					Integer32
		}


	procRackNo		 OBJECT-TYPE
		SYNTAX					 Integer32( 0 .. 0 )
		MAX-ACCESS			 not-accessible
		STATUS					 current
		DESCRIPTION			 " -- "
		::=  { processorEntry  1 }


	procShelfNo		 OBJECT-TYPE
		SYNTAX					 Integer32( 0 .. 0 )
		MAX-ACCESS			 not-accessible
		STATUS					 current
		DESCRIPTION			 " -- "
		::=  { processorEntry  2 }


	procSlotNo		 OBJECT-TYPE
		SYNTAX					 Integer32( 0 .. 16 )
		MAX-ACCESS			 not-accessible
		STATUS					 current
		DESCRIPTION			 " -- "
		::=  { processorEntry  3 }


	procIndexOnBoard		 OBJECT-TYPE
		SYNTAX					 Integer32( 0 .. 9 )
		MAX-ACCESS			 not-accessible
		STATUS					 current
		DESCRIPTION			 " -- "
		::=  { processorEntry  4 }


	procRowStatus		 OBJECT-TYPE
		SYNTAX					 RowStatus
		MAX-ACCESS			 read-only
		STATUS					 current
		DESCRIPTION			 " -- "
		::=  { processorEntry  5 }


	procType		 OBJECT-TYPE
		SYNTAX					 INTEGER{ unknown(0),mcu(1),dsp(2),fpga(3),mcmcu(4)  }
		MAX-ACCESS			 read-only
		STATUS					 current
		DESCRIPTION			 " -- "
		::=  { processorEntry  6 }


	procDescription		 OBJECT-TYPE
		SYNTAX					 DisplayString( SIZE ( 1 .. 255 ) )
		MAX-ACCESS			 read-only
		STATUS					 current
		DESCRIPTION			 " -- "
		::=  { processorEntry  7 }


	procProceduralStatus		 OBJECT-TYPE
		SYNTAX					 INTEGER{ initializationRequired(0),notInitialized(1),initializing(2),reporting(3),terminating(4)  }
		MAX-ACCESS			 read-only
		STATUS					 current
		DESCRIPTION			 " -- "
		::=  { processorEntry  8 }


	procOperationalState		 OBJECT-TYPE
		SYNTAX					 INTEGER{ disabled(0),enabled(1)  }
		MAX-ACCESS			 read-only
		STATUS					 current
		DESCRIPTION			 " -- "
		::=  { processorEntry  9 }


	procCPUCheckInterval		 OBJECT-TYPE
		SYNTAX					 Integer32( 1 .. 60 )
		MAX-ACCESS			 read-write
		STATUS					 current
		DESCRIPTION			 " -- "
		::=  { processorEntry  11 }


	procCoreNum		 OBJECT-TYPE
		SYNTAX					 Integer32( 1 .. 6 )
		MAX-ACCESS			 read-only
		STATUS					 current
		DESCRIPTION			 " -- "
		::=  { processorEntry  12 }


	procResetTrigger		 OBJECT-TYPE
		SYNTAX					 INTEGER{ off(0),on(1)  }
		MAX-ACCESS			 read-write
		STATUS					 current
		DESCRIPTION			 " -- "
		::=  { processorEntry  13 }


	procStatCPUOccupation		 OBJECT-TYPE
		SYNTAX					 Integer32( 0 .. 100 )
		MAX-ACCESS			 read-only
		STATUS					 current
		DESCRIPTION			 " -- "
		::=  { processorEntry  14 }


	boardSensor		 OBJECT IDENTIFIER
		::=  { equipmentInfo  7 }


	boardTemperature		 OBJECT IDENTIFIER
		::=  { boardSensor  1 }


	boardTemperatureTable		 OBJECT-TYPE
		SYNTAX					 SEQUENCE  OF	 BoardTemperatureEntry
		MAX-ACCESS			 not-accessible
		STATUS					 current
		DESCRIPTION			 " -- "
		::=  { boardTemperature  1 }


	boardTemperatureEntry		 OBJECT-TYPE
		SYNTAX					 BoardTemperatureEntry
		MAX-ACCESS			 not-accessible
		STATUS					 current
		DESCRIPTION			 " -- "
		INDEX						{ boardTempRackNo,boardTempShelfNo,boardTempSlotNo,boardTempIndexOnBoard }
		::=  { boardTemperatureTable  1 }


	BoardTemperatureEntry		 ::=  SEQUENCE {
		boardTempRackNo					Integer32,
		boardTempShelfNo					Integer32,
		boardTempSlotNo					Integer32,
		boardTempIndexOnBoard					Integer32,
		boardTempRowStatus					RowStatus,
		boardTempDescription					DisplayString,
		boardTempIdeal					Integer32,
		boardTempUpperThreshold					Integer32,
		boardTempLowerThreshold					Integer32,
		boardTempUpperCriticalThreshold					Integer32,
		boardTempStatTemperature					Integer32
		}


	boardTempRackNo		 OBJECT-TYPE
		SYNTAX					 Integer32( 0 .. 0 )
		MAX-ACCESS			 not-accessible
		STATUS					 current
		DESCRIPTION			 " -- "
		::=  { boardTemperatureEntry  1 }


	boardTempShelfNo		 OBJECT-TYPE
		SYNTAX					 Integer32( 0 .. 0 )
		MAX-ACCESS			 not-accessible
		STATUS					 current
		DESCRIPTION			 " -- "
		::=  { boardTemperatureEntry  2 }


	boardTempSlotNo		 OBJECT-TYPE
		SYNTAX					 Integer32( 0 .. 16 )
		MAX-ACCESS			 not-accessible
		STATUS					 current
		DESCRIPTION			 " -- "
		::=  { boardTemperatureEntry  3 }


	boardTempIndexOnBoard		 OBJECT-TYPE
		SYNTAX					 Integer32( 0 .. 5 )
		MAX-ACCESS			 not-accessible
		STATUS					 current
		DESCRIPTION			 " -- "
		::=  { boardTemperatureEntry  4 }


	boardTempRowStatus		 OBJECT-TYPE
		SYNTAX					 RowStatus
		MAX-ACCESS			 read-only
		STATUS					 current
		DESCRIPTION			 " -- "
		::=  { boardTemperatureEntry  5 }


	boardTempDescription		 OBJECT-TYPE
		SYNTAX					 DisplayString( SIZE ( 1 .. 255 ) )
		MAX-ACCESS			 read-only
		STATUS					 current
		DESCRIPTION			 " -- "
		::=  { boardTemperatureEntry  6 }


	boardTempIdeal		 OBJECT-TYPE
		SYNTAX					 Integer32( 0 .. 100 )
		MAX-ACCESS			 read-write
		STATUS					 current
		DESCRIPTION			 " -- "
		::=  { boardTemperatureEntry  7 }


	boardTempUpperThreshold		 OBJECT-TYPE
		SYNTAX					 Integer32( 50 .. 200 )
		MAX-ACCESS			 read-write
		STATUS					 current
		DESCRIPTION			 " -- "
		::=  { boardTemperatureEntry  8 }


	boardTempLowerThreshold		 OBJECT-TYPE
		SYNTAX					 Integer32( -50 .. 50 )
		MAX-ACCESS			 read-write
		STATUS					 current
		DESCRIPTION			 " -- "
		::=  { boardTemperatureEntry  9 }


	boardTempUpperCriticalThreshold		 OBJECT-TYPE
		SYNTAX					 Integer32( 50 .. 200 )
		MAX-ACCESS			 read-write
		STATUS					 current
		DESCRIPTION			 " -- "
		::=  { boardTemperatureEntry  10 }


	boardTempStatTemperature		 OBJECT-TYPE
		SYNTAX					 Integer32( -2147483648 .. 2147483647 )
		MAX-ACCESS			 read-only
		STATUS					 current
		DESCRIPTION			 " -- "
		::=  { boardTemperatureEntry  11 }


	boardVoltage		 OBJECT IDENTIFIER
		::=  { boardSensor  2 }


	boardVoltageTable		 OBJECT-TYPE
		SYNTAX					 SEQUENCE  OF	 BoardVoltageEntry
		MAX-ACCESS			 not-accessible
		STATUS					 current
		DESCRIPTION			 " -- "
		::=  { boardVoltage  1 }


	boardVoltageEntry		 OBJECT-TYPE
		SYNTAX					 BoardVoltageEntry
		MAX-ACCESS			 not-accessible
		STATUS					 current
		DESCRIPTION			 " -- "
		INDEX						{ boardVoltRackNo,boardVoltShelfNo,boardVoltSlotNo,boardVoltIndexOnBoard }
		::=  { boardVoltageTable  1 }


	BoardVoltageEntry		 ::=  SEQUENCE {
		boardVoltRackNo					Integer32,
		boardVoltShelfNo					Integer32,
		boardVoltSlotNo					Integer32,
		boardVoltIndexOnBoard					Integer32,
		boardVoltRowStatus					RowStatus,
		boardVoltDescription					DisplayString,
		boardVoltUpperThreshold					Integer32,
		boardVoltLowerThreshold					Integer32,
		boardStatVoltage					Integer32
		}


	boardVoltRackNo		 OBJECT-TYPE
		SYNTAX					 Integer32( 0 .. 0 )
		MAX-ACCESS			 not-accessible
		STATUS					 current
		DESCRIPTION			 " -- "
		::=  { boardVoltageEntry  1 }


	boardVoltShelfNo		 OBJECT-TYPE
		SYNTAX					 Integer32( 0 .. 0 )
		MAX-ACCESS			 not-accessible
		STATUS					 current
		DESCRIPTION			 " -- "
		::=  { boardVoltageEntry  2 }


	boardVoltSlotNo		 OBJECT-TYPE
		SYNTAX					 Integer32( 0 .. 16 )
		MAX-ACCESS			 not-accessible
		STATUS					 current
		DESCRIPTION			 " -- "
		::=  { boardVoltageEntry  3 }


	boardVoltIndexOnBoard		 OBJECT-TYPE
		SYNTAX					 Integer32( 0 .. 5 )
		MAX-ACCESS			 not-accessible
		STATUS					 current
		DESCRIPTION			 " -- "
		::=  { boardVoltageEntry  4 }


	boardVoltRowStatus		 OBJECT-TYPE
		SYNTAX					 RowStatus
		MAX-ACCESS			 read-only
		STATUS					 current
		DESCRIPTION			 " -- "
		::=  { boardVoltageEntry  5 }


	boardVoltDescription		 OBJECT-TYPE
		SYNTAX					 DisplayString( SIZE ( 1 .. 255 ) )
		MAX-ACCESS			 read-only
		STATUS					 current
		DESCRIPTION			 " -- "
		::=  { boardVoltageEntry  6 }


	boardVoltUpperThreshold		 OBJECT-TYPE
		SYNTAX					 Integer32( -2147483648 .. 2147483647 )
		MAX-ACCESS			 read-write
		STATUS					 current
		DESCRIPTION			 " -- "
		::=  { boardVoltageEntry  7 }


	boardVoltLowerThreshold		 OBJECT-TYPE
		SYNTAX					 Integer32( -2147483648 .. 2147483647 )
		MAX-ACCESS			 read-write
		STATUS					 current
		DESCRIPTION			 " -- "
		::=  { boardVoltageEntry  8 }


	boardStatVoltage		 OBJECT-TYPE
		SYNTAX					 Integer32( -2147483648 .. 2147483647 )
		MAX-ACCESS			 read-only
		STATUS					 current
		DESCRIPTION			 " -- "
		::=  { boardVoltageEntry  9 }


	boardLed		 OBJECT IDENTIFIER
		::=  { boardSensor  3 }


	boardLedTable		 OBJECT-TYPE
		SYNTAX					 SEQUENCE  OF	 BoardLedEntry
		MAX-ACCESS			 not-accessible
		STATUS					 current
		DESCRIPTION			 " -- "
		::=  { boardLed  1 }


	boardLedEntry		 OBJECT-TYPE
		SYNTAX					 BoardLedEntry
		MAX-ACCESS			 not-accessible
		STATUS					 current
		DESCRIPTION			 " -- "
		INDEX						{ boardLedRackNo,boardLedShelfNo,boardLedSlotNo,boardLedIndexOnBoard }
		::=  { boardLedTable  1 }


	BoardLedEntry		 ::=  SEQUENCE {
		boardLedRackNo					Integer32,
		boardLedShelfNo					Integer32,
		boardLedSlotNo					Integer32,
		boardLedIndexOnBoard					Integer32,
		boardLedRowStatus					RowStatus,
		boardLedDescription					DisplayString,
		boardLedStatus					INTEGER
		}


	boardLedRackNo		 OBJECT-TYPE
		SYNTAX					 Integer32( 0 .. 0 )
		MAX-ACCESS			 not-accessible
		STATUS					 current
		DESCRIPTION			 " -- "
		::=  { boardLedEntry  1 }


	boardLedShelfNo		 OBJECT-TYPE
		SYNTAX					 Integer32( 0 .. 0 )
		MAX-ACCESS			 not-accessible
		STATUS					 current
		DESCRIPTION			 " -- "
		::=  { boardLedEntry  2 }


	boardLedSlotNo		 OBJECT-TYPE
		SYNTAX					 Integer32( 0 .. 16 )
		MAX-ACCESS			 not-accessible
		STATUS					 current
		DESCRIPTION			 " -- "
		::=  { boardLedEntry  3 }


	boardLedIndexOnBoard		 OBJECT-TYPE
		SYNTAX					 Integer32( 0 .. 10 )
		MAX-ACCESS			 not-accessible
		STATUS					 current
		DESCRIPTION			 " -- "
		::=  { boardLedEntry  4 }


	boardLedRowStatus		 OBJECT-TYPE
		SYNTAX					 RowStatus
		MAX-ACCESS			 read-only
		STATUS					 current
		DESCRIPTION			 " -- "
		::=  { boardLedEntry  5 }


	boardLedDescription		 OBJECT-TYPE
		SYNTAX					 DisplayString( SIZE ( 1 .. 255 ) )
		MAX-ACCESS			 read-only
		STATUS					 current
		DESCRIPTION			 " -- "
		::=  { boardLedEntry  6 }


	boardLedStatus		 OBJECT-TYPE
		SYNTAX					 INTEGER{ off(0),slow(1),normal(2),fast(3)  }
		MAX-ACCESS			 read-only
		STATUS					 current
		DESCRIPTION			 " -- "
		::=  { boardLedEntry  7 }


	boardStorageDev		 OBJECT IDENTIFIER
		::=  { equipmentInfo  8 }


	boardStorageDevTable		 OBJECT-TYPE
		SYNTAX					 SEQUENCE  OF	 BoardStorageDevEntry
		MAX-ACCESS			 not-accessible
		STATUS					 current
		DESCRIPTION			 " -- "
		::=  { boardStorageDev  1 }


	boardStorageDevEntry		 OBJECT-TYPE
		SYNTAX					 BoardStorageDevEntry
		MAX-ACCESS			 not-accessible
		STATUS					 current
		DESCRIPTION			 " -- "
		INDEX						{ boardStorageDevRackNo,boardStorageDevShelfNo,boardStorageDevSlotNo,boardStorageDevOnBoard }
		::=  { boardStorageDevTable  1 }


	BoardStorageDevEntry		 ::=  SEQUENCE {
		boardStorageDevRackNo					Integer32,
		boardStorageDevShelfNo					Integer32,
		boardStorageDevSlotNo					Integer32,
		boardStorageDevOnBoard					Integer32,
		boardStorageDevRowStatus					RowStatus,
		boardStorageDevTotalSize					Unsigned32,
		boardStorageDevUsedSize					Unsigned32,
		boardStorageDevFreeBytes					Unsigned32,
		boardStorageDevFreePercent					Integer32,
		boardStorageMountPath					DisplayString
		}


	boardStorageDevRackNo		 OBJECT-TYPE
		SYNTAX					 Integer32( 0 .. 0 )
		MAX-ACCESS			 not-accessible
		STATUS					 current
		DESCRIPTION			 " -- "
		::=  { boardStorageDevEntry  1 }


	boardStorageDevShelfNo		 OBJECT-TYPE
		SYNTAX					 Integer32( 0 .. 0 )
		MAX-ACCESS			 not-accessible
		STATUS					 current
		DESCRIPTION			 " -- "
		::=  { boardStorageDevEntry  2 }


	boardStorageDevSlotNo		 OBJECT-TYPE
		SYNTAX					 Integer32( 0 .. 16 )
		MAX-ACCESS			 not-accessible
		STATUS					 current
		DESCRIPTION			 " -- "
		::=  { boardStorageDevEntry  3 }


	boardStorageDevOnBoard		 OBJECT-TYPE
		SYNTAX					 Integer32( 0 .. 4 )
		MAX-ACCESS			 not-accessible
		STATUS					 current
		DESCRIPTION			 " -- "
		::=  { boardStorageDevEntry  4 }


	boardStorageDevRowStatus		 OBJECT-TYPE
		SYNTAX					 RowStatus
		MAX-ACCESS			 read-only
		STATUS					 current
		DESCRIPTION			 " -- "
		::=  { boardStorageDevEntry  5 }


	boardStorageDevTotalSize		 OBJECT-TYPE
		SYNTAX					 Unsigned32( 0 .. 4294967295 )
		MAX-ACCESS			 read-only
		STATUS					 current
		DESCRIPTION			 " -- "
		::=  { boardStorageDevEntry  6 }


	boardStorageDevUsedSize		 OBJECT-TYPE
		SYNTAX					 Unsigned32( 0 .. 4294967295 )
		MAX-ACCESS			 read-only
		STATUS					 current
		DESCRIPTION			 " -- "
		::=  { boardStorageDevEntry  7 }


	boardStorageDevFreeBytes		 OBJECT-TYPE
		SYNTAX					 Unsigned32( 0 .. 4294967295 )
		MAX-ACCESS			 read-only
		STATUS					 current
		DESCRIPTION			 " -- "
		::=  { boardStorageDevEntry  8 }


	boardStorageDevFreePercent		 OBJECT-TYPE
		SYNTAX					 Integer32( 0 .. 100 )
		MAX-ACCESS			 read-only
		STATUS					 current
		DESCRIPTION			 " -- "
		::=  { boardStorageDevEntry  9 }


	boardStorageMountPath		 OBJECT-TYPE
		SYNTAX					 DisplayString( SIZE ( 1 .. 255 ) )
		MAX-ACCESS			 read-only
		STATUS					 current
		DESCRIPTION			 " -- "
		::=  { boardStorageDevEntry  10 }


	traceManagement		 OBJECT IDENTIFIER
		::=  { lteCommon  10 }


	traceTask		 OBJECT IDENTIFIER
		::=  { traceManagement  1 }


	traceTaskTable		 OBJECT-TYPE
		SYNTAX					 SEQUENCE  OF	 TraceTaskEntry
		MAX-ACCESS			 not-accessible
		STATUS					 current
		DESCRIPTION			 " -- "
		::=  { traceTask  1 }


	traceTaskEntry		 OBJECT-TYPE
		SYNTAX					 TraceTaskEntry
		MAX-ACCESS			 not-accessible
		STATUS					 current
		DESCRIPTION			 " -- "
		INDEX						{ traceTaskId }
		::=  { traceTaskTable  1 }


	TraceTaskEntry		 ::=  SEQUENCE {
		traceTaskId					Integer32,
		traceTaskRowStatus					RowStatus,
		traceTaskCollectEntityInetAddrType					InetAddressType,
		traceTaskCollectEntityInetAddr					InetAddress,
		traceTaskCollectEntityPort					Integer32,
		traceTaskTceInetAddrType					InetAddressType,
		traceTaskTceInetAddr					InetAddress,
		traceTaskManagerIndex					Integer32,
		traceTaskBandWidthThreshold					Integer32,
		traceTaskType					INTEGER,
		traceTaskObjectID					Integer32,
		traceTaskPlmnMcc					MncMccType,
		traceTaskPlmnMnc					MncMccType,
		traceTaskReferenceId					Integer32,
		traceDepth					INTEGER,
		traceTaskTrcList					BITS,
		traceTaskUeId					Integer32,
		traceCellTrcNotiMme					INTEGER,
		traceMsgTypeBitMap					Unsigned32Array
		}


	traceTaskId		 OBJECT-TYPE
		SYNTAX					 Integer32( 1 .. 64 )
		MAX-ACCESS			 not-accessible
		STATUS					 current
		DESCRIPTION			 " -- "
		::=  { traceTaskEntry  1 }


	traceTaskRowStatus		 OBJECT-TYPE
		SYNTAX					 RowStatus
		MAX-ACCESS			 read-create
		STATUS					 current
		DESCRIPTION			 " -- "
		::=  { traceTaskEntry  2 }


	traceTaskCollectEntityInetAddrType		 OBJECT-TYPE
		SYNTAX					 InetAddressType
		MAX-ACCESS			 read-create
		STATUS					 current
		DESCRIPTION			 " -- "
		::=  { traceTaskEntry  3 }


	traceTaskCollectEntityInetAddr		 OBJECT-TYPE
		SYNTAX					 InetAddress
		MAX-ACCESS			 read-create
		STATUS					 current
		DESCRIPTION			 " -- "
		::=  { traceTaskEntry  4 }


	traceTaskCollectEntityPort		 OBJECT-TYPE
		SYNTAX					 Integer32( 0 .. 65535 )
		MAX-ACCESS			 read-create
		STATUS					 current
		DESCRIPTION			 " -- "
		::=  { traceTaskEntry  5 }


	traceTaskTceInetAddrType		 OBJECT-TYPE
		SYNTAX					 InetAddressType
		MAX-ACCESS			 read-create
		STATUS					 current
		DESCRIPTION			 " -- "
		::=  { traceTaskEntry  6 }


	traceTaskTceInetAddr		 OBJECT-TYPE
		SYNTAX					 InetAddress
		MAX-ACCESS			 read-create
		STATUS					 current
		DESCRIPTION			 " -- "
		::=  { traceTaskEntry  7 }


	traceTaskManagerIndex		 OBJECT-TYPE
		SYNTAX					 Integer32( 0 .. 15 )
		MAX-ACCESS			 read-only
		STATUS					 current
		DESCRIPTION			 " -- "
		::=  { traceTaskEntry  8 }


	traceTaskBandWidthThreshold		 OBJECT-TYPE
		SYNTAX					 Integer32( 10 .. 2000 )
		MAX-ACCESS			 read-create
		STATUS					 current
		DESCRIPTION			 " -- "
		::=  { traceTaskEntry  9 }


	traceTaskType		 OBJECT-TYPE
		SYNTAX					 INTEGER{ itf(1),cell(2),ue(3)  }
		MAX-ACCESS			 read-create
		STATUS					 current
		DESCRIPTION			 " -- "
		::=  { traceTaskEntry  10 }


	traceTaskObjectID		 OBJECT-TYPE
		SYNTAX					 Integer32( -2147483648 .. 2147483647 )
		MAX-ACCESS			 read-create
		STATUS					 current
		DESCRIPTION			 " -- "
		::=  { traceTaskEntry  11 }


	traceTaskPlmnMcc		 OBJECT-TYPE
		SYNTAX					 MncMccType
		MAX-ACCESS			 read-create
		STATUS					 current
		DESCRIPTION			 " -- "
		::=  { traceTaskEntry  12 }


	traceTaskPlmnMnc		 OBJECT-TYPE
		SYNTAX					 MncMccType
		MAX-ACCESS			 read-create
		STATUS					 current
		DESCRIPTION			 " -- "
		::=  { traceTaskEntry  13 }


	traceTaskReferenceId		 OBJECT-TYPE
		SYNTAX					 Integer32( 0 .. 16777215 )
		MAX-ACCESS			 read-create
		STATUS					 current
		DESCRIPTION			 " -- "
		::=  { traceTaskEntry  14 }


	traceDepth		 OBJECT-TYPE
		SYNTAX					 INTEGER{ min(1),medium(2),max(3)  }
		MAX-ACCESS			 read-create
		STATUS					 current
		DESCRIPTION			 " -- "
		::=  { traceTaskEntry  15 }


	traceTaskTrcList		 OBJECT-TYPE
		SYNTAX					 BITS{ s1(0),x2(1),uu(2)  }
		MAX-ACCESS			 read-create
		STATUS					 current
		DESCRIPTION			 " -- "
		::=  { traceTaskEntry  16 }


	traceTaskUeId		 OBJECT-TYPE
		SYNTAX					 Integer32( -2147483648 .. 2147483647 )
		MAX-ACCESS			 read-create
		STATUS					 current
		DESCRIPTION			 " -- "
		::=  { traceTaskEntry  17 }


	traceCellTrcNotiMme		 OBJECT-TYPE
		SYNTAX					 INTEGER{ false(0),ture(1)  }
		MAX-ACCESS			 read-create
		STATUS					 current
		DESCRIPTION			 " -- "
		::=  { traceTaskEntry  18 }


	traceMsgTypeBitMap		 OBJECT-TYPE
		SYNTAX					 Unsigned32Array
		MAX-ACCESS			 read-create
		STATUS					 current
		DESCRIPTION			 " -- "
		::=  { traceTaskEntry  19 }


	traceServer		 OBJECT IDENTIFIER
		::=  { traceManagement  2 }


	traceMmeUeTrcSrvCfg		 OBJECT IDENTIFIER
		::=  { traceServer  1 }


	traceUeSrvInetAddrType		 OBJECT-TYPE
		SYNTAX					 InetAddressType
		MAX-ACCESS			 read-write
		STATUS					 current
		DESCRIPTION			 " -- "
		::=  { traceMmeUeTrcSrvCfg  1 }


	traceUeSrvInetAddr		 OBJECT-TYPE
		SYNTAX					 InetAddress
		MAX-ACCESS			 read-write
		STATUS					 current
		DESCRIPTION			 " -- "
		::=  { traceMmeUeTrcSrvCfg  2 }


	traceUeSrvPort		 OBJECT-TYPE
		SYNTAX					 Integer32( 0 .. 65535 )
		MAX-ACCESS			 read-write
		STATUS					 current
		DESCRIPTION			 " -- "
		::=  { traceMmeUeTrcSrvCfg  3 }


	traceLiscence		 OBJECT IDENTIFIER
		::=  { traceManagement  3 }


	traceLiscenceCfg		 OBJECT IDENTIFIER
		::=  { traceLiscence  1 }


	traceMmeUeTrcSwitch		 OBJECT-TYPE
		SYNTAX					 INTEGER{ off(0),on(1)  }
		MAX-ACCESS			 read-write
		STATUS					 current
		DESCRIPTION			 " -- "
		::=  { traceLiscenceCfg  1 }


	traceManagementTrcSwitch		 OBJECT-TYPE
		SYNTAX					 INTEGER{ off(0),on(1)  }
		MAX-ACCESS			 read-write
		STATUS					 current
		DESCRIPTION			 " -- "
		::=  { traceLiscenceCfg  2 }


	outPutManagement		 OBJECT IDENTIFIER
		::=  { lteCommon  11 }


	syslogServerControlTable		 OBJECT-TYPE
		SYNTAX					 SEQUENCE  OF	 SyslogServerControlEntry
		MAX-ACCESS			 not-accessible
		STATUS					 current
		DESCRIPTION			 " -- "
		::=  { outPutManagement  1 }


	syslogServerControlEntry		 OBJECT-TYPE
		SYNTAX					 SyslogServerControlEntry
		MAX-ACCESS			 not-accessible
		STATUS					 current
		DESCRIPTION			 " -- "
		INDEX						{ syslogServerManagerIndex }
		::=  { syslogServerControlTable  1 }


	SyslogServerControlEntry		 ::=  SEQUENCE {
		syslogServerManagerIndex					Integer32,
		syslogServerRowStatus					RowStatus,
		syslogServerSendSwitch					INTEGER,
		syslogServerSendSeverity					BITS,
		syslogServerSendFacility					BITS,
		syslogServerMsgSendEncapsulation					INTEGER,
		syslogServerDescr					DisplayString,
		syslogServerInetAddrType					InetAddressType,
		syslogServerInetAddr					InetAddress,
		syslogServerPort					Unsigned32
		}


	syslogServerManagerIndex		 OBJECT-TYPE
		SYNTAX					 Integer32( 0 .. 15 )
		MAX-ACCESS			 not-accessible
		STATUS					 current
		DESCRIPTION			 " -- "
		::=  { syslogServerControlEntry  1 }


	syslogServerRowStatus		 OBJECT-TYPE
		SYNTAX					 RowStatus
		MAX-ACCESS			 read-create
		STATUS					 current
		DESCRIPTION			 " -- "
		::=  { syslogServerControlEntry  2 }


	syslogServerSendSwitch		 OBJECT-TYPE
		SYNTAX					 INTEGER{ off(0),on(1)  }
		MAX-ACCESS			 read-create
		STATUS					 current
		DESCRIPTION			 " -- "
		::=  { syslogServerControlEntry  3 }


	syslogServerSendSeverity		 OBJECT-TYPE
		SYNTAX					 BITS{ emergency(0),alert(1),critical(2),error(3),warning(4),notice(5),informational(6),debug(7)  }
		MAX-ACCESS			 read-create
		STATUS					 current
		DESCRIPTION			 " -- "
		::=  { syslogServerControlEntry  4 }


	syslogServerSendFacility		 OBJECT-TYPE
		SYNTAX					 BITS{ om(16),dd(17),hl(18),pl(19)  }
		MAX-ACCESS			 read-create
		STATUS					 current
		DESCRIPTION			 " -- "
		::=  { syslogServerControlEntry  5 }


	syslogServerMsgSendEncapsulation		 OBJECT-TYPE
		SYNTAX					 INTEGER{ none(0),tls(1),beep(2),other(3)  }
		MAX-ACCESS			 read-create
		STATUS					 current
		DESCRIPTION			 " -- "
		::=  { syslogServerControlEntry  6 }


	syslogServerDescr		 OBJECT-TYPE
		SYNTAX					 DisplayString( SIZE ( 1 .. 255 ) )
		MAX-ACCESS			 read-create
		STATUS					 current
		DESCRIPTION			 " -- "
		::=  { syslogServerControlEntry  7 }


	syslogServerInetAddrType		 OBJECT-TYPE
		SYNTAX					 InetAddressType
		MAX-ACCESS			 read-create
		STATUS					 current
		DESCRIPTION			 " -- "
		::=  { syslogServerControlEntry  8 }


	syslogServerInetAddr		 OBJECT-TYPE
		SYNTAX					 InetAddress
		MAX-ACCESS			 read-create
		STATUS					 current
		DESCRIPTION			 " -- "
		::=  { syslogServerControlEntry  9 }


	syslogServerPort		 OBJECT-TYPE
		SYNTAX					 Unsigned32( 0 .. 4294967295 )
		MAX-ACCESS			 read-only
		STATUS					 current
		DESCRIPTION			 " -- "
		::=  { syslogServerControlEntry  10 }


	syslogConsoleControlTable		 OBJECT-TYPE
		SYNTAX					 SEQUENCE  OF	 SyslogConsoleControlEntry
		MAX-ACCESS			 not-accessible
		STATUS					 current
		DESCRIPTION			 " -- "
		::=  { outPutManagement  2 }


	syslogConsoleControlEntry		 OBJECT-TYPE
		SYNTAX					 SyslogConsoleControlEntry
		MAX-ACCESS			 not-accessible
		STATUS					 current
		DESCRIPTION			 " -- "
		INDEX						{ syslogConsoleManagerIndex }
		::=  { syslogConsoleControlTable  1 }


	SyslogConsoleControlEntry		 ::=  SEQUENCE {
		syslogConsoleManagerIndex					Integer32,
		syslogConsoleRowStatus					RowStatus,
		syslogConsoleSwitch					INTEGER,
		syslogConsoleSeverity					BITS,
		syslogConsoleFacility					BITS
		}


	syslogConsoleManagerIndex		 OBJECT-TYPE
		SYNTAX					 Integer32( 0 .. 15 )
		MAX-ACCESS			 not-accessible
		STATUS					 current
		DESCRIPTION			 " -- "
		::=  { syslogConsoleControlEntry  1 }


	syslogConsoleRowStatus		 OBJECT-TYPE
		SYNTAX					 RowStatus
		MAX-ACCESS			 read-create
		STATUS					 current
		DESCRIPTION			 " -- "
		::=  { syslogConsoleControlEntry  2 }


	syslogConsoleSwitch		 OBJECT-TYPE
		SYNTAX					 INTEGER{ off(0),on(1)  }
		MAX-ACCESS			 read-create
		STATUS					 current
		DESCRIPTION			 " -- "
		::=  { syslogConsoleControlEntry  3 }


	syslogConsoleSeverity		 OBJECT-TYPE
		SYNTAX					 BITS{ emergency(0),alert(1),critical(2),error(3),warning(4),notice(5),informational(6),debug(7)  }
		MAX-ACCESS			 read-create
		STATUS					 current
		DESCRIPTION			 " -- "
		::=  { syslogConsoleControlEntry  4 }


	syslogConsoleFacility		 OBJECT-TYPE
		SYNTAX					 BITS{ om(16),dd(17),hl(18),pl(19)  }
		MAX-ACCESS			 read-create
		STATUS					 current
		DESCRIPTION			 " -- "
		::=  { syslogConsoleControlEntry  5 }


	syslogStatis		 OBJECT IDENTIFIER
		::=  { outPutManagement  3 }


	syslogMsgSends		 OBJECT-TYPE
		SYNTAX					 Unsigned32( 0 .. 4294967295 )
		MAX-ACCESS			 read-only
		STATUS					 current
		DESCRIPTION			 " -- "
		::=  { syslogStatis  1 }


	syslogMsgHostName		 OBJECT-TYPE
		SYNTAX					 DisplayString( SIZE ( 1 .. 255 ) )
		MAX-ACCESS			 read-write
		STATUS					 current
		DESCRIPTION			 " -- "
		::=  { syslogStatis  2 }


	licenseManagement		 OBJECT IDENTIFIER
		::=  { lteCommon  12 }


	licenseAuthorization		 OBJECT IDENTIFIER
		::=  { licenseManagement  1 }


	licenseFeatureTable		 OBJECT-TYPE
		SYNTAX					 SEQUENCE  OF	 LicenseFeatureEntry
		MAX-ACCESS			 not-accessible
		STATUS					 current
		DESCRIPTION			 " -- "
		::=  { licenseAuthorization  1 }


	licenseFeatureEntry		 OBJECT-TYPE
		SYNTAX					 LicenseFeatureEntry
		MAX-ACCESS			 not-accessible
		STATUS					 current
		DESCRIPTION			 " -- "
		INDEX						{ licenseFeatureIndex }
		::=  { licenseFeatureTable  1 }


	LicenseFeatureEntry		 ::=  SEQUENCE {
		licenseFeatureIndex					Integer32,
		licenseFeatureRowStatus					RowStatus,
		licenseFeatureName					DisplayString,
		licenseFeatureSupportable					INTEGER,
		licenseFeatureAuthorizedState					INTEGER,
		licenseFeatureSwitch					INTEGER
		}


	licenseFeatureIndex		 OBJECT-TYPE
		SYNTAX					 Integer32( 0 .. 0 )
		MAX-ACCESS			 not-accessible
		STATUS					 current
		DESCRIPTION			 " -- "
		::=  { licenseFeatureEntry  1 }


	licenseFeatureRowStatus		 OBJECT-TYPE
		SYNTAX					 RowStatus
		MAX-ACCESS			 read-only
		STATUS					 current
		DESCRIPTION			 " -- "
		::=  { licenseFeatureEntry  2 }


	licenseFeatureName		 OBJECT-TYPE
		SYNTAX					 DisplayString( SIZE ( 1 .. 59 ) )
		MAX-ACCESS			 read-only
		STATUS					 current
		DESCRIPTION			 " -- "
		::=  { licenseFeatureEntry  3 }


	licenseFeatureSupportable		 OBJECT-TYPE
		SYNTAX					 INTEGER{ unsupported(0),supported(1)  }
		MAX-ACCESS			 read-only
		STATUS					 current
		DESCRIPTION			 " -- "
		::=  { licenseFeatureEntry  4 }


	licenseFeatureAuthorizedState		 OBJECT-TYPE
		SYNTAX					 INTEGER{ unauthorized(0),authorized(1)  }
		MAX-ACCESS			 read-write
		STATUS					 current
		DESCRIPTION			 " -- "
		::=  { licenseFeatureEntry  5 }


	licenseFeatureSwitch		 OBJECT-TYPE
		SYNTAX					 INTEGER{ off(0),on(1)  }
		MAX-ACCESS			 read-write
		STATUS					 current
		DESCRIPTION			 " -- "
		::=  { licenseFeatureEntry  6 }


	licenseCapacity		 OBJECT IDENTIFIER
		::=  { licenseAuthorization  2 }


	securityManagement		 OBJECT IDENTIFIER
		::=  { lteCommon  13 }


	accessControlManagement		 OBJECT IDENTIFIER
		::=  { securityManagement  1 }


	accessUserTable		 OBJECT-TYPE
		SYNTAX					 SEQUENCE  OF	 AccessUserEntry
		MAX-ACCESS			 not-accessible
		STATUS					 current
		DESCRIPTION			 " -- "
		::=  { accessControlManagement  1 }


	accessUserEntry		 OBJECT-TYPE
		SYNTAX					 AccessUserEntry
		MAX-ACCESS			 not-accessible
		STATUS					 current
		DESCRIPTION			 " -- "
		INDEX						{ accessUserIndex }
		::=  { accessUserTable  1 }


	AccessUserEntry		 ::=  SEQUENCE {
		accessUserIndex					Integer32,
		accessUserRowStatus					RowStatus,
		accessUserName					DisplayString,
		accessUserPassword					DisplayString,
		accessUserGroupView					INTEGER
		}


	accessUserIndex		 OBJECT-TYPE
		SYNTAX					 Integer32( 1 .. 1 )
		MAX-ACCESS			 not-accessible
		STATUS					 current
		DESCRIPTION			 " -- "
		::=  { accessUserEntry  1 }


	accessUserRowStatus		 OBJECT-TYPE
		SYNTAX					 RowStatus
		MAX-ACCESS			 read-create
		STATUS					 current
		DESCRIPTION			 " -- "
		::=  { accessUserEntry  2 }


	accessUserName		 OBJECT-TYPE
		SYNTAX					 DisplayString( SIZE ( 1 .. 255 ) )
		MAX-ACCESS			 read-create
		STATUS					 current
		DESCRIPTION			 " -- "
		::=  { accessUserEntry  3 }


	accessUserPassword		 OBJECT-TYPE
		SYNTAX					 DisplayString( SIZE ( 1 .. 255 ) )
		MAX-ACCESS			 read-create
		STATUS					 current
		DESCRIPTION			 " -- "
		::=  { accessUserEntry  4 }


	accessUserGroupView		 OBJECT-TYPE
		SYNTAX					 INTEGER{ unknown(0),administrator(1),systemUser(2),commonUser(3),guest(4)  }
		MAX-ACCESS			 read-create
		STATUS					 current
		DESCRIPTION			 " -- "
		::=  { accessUserEntry  5 }


	cmdAuthorizationManagement		 OBJECT IDENTIFIER
		::=  { securityManagement  2 }


	cmdAuthorizationTable		 OBJECT-TYPE
		SYNTAX					 SEQUENCE  OF	 CmdAuthorizationEntry
		MAX-ACCESS			 not-accessible
		STATUS					 current
		DESCRIPTION			 " -- "
		::=  { cmdAuthorizationManagement  1 }


	cmdAuthorizationEntry		 OBJECT-TYPE
		SYNTAX					 CmdAuthorizationEntry
		MAX-ACCESS			 not-accessible
		STATUS					 current
		DESCRIPTION			 " -- "
		INDEX						{ cmdAuthorizationIndex }
		::=  { cmdAuthorizationTable  1 }


	CmdAuthorizationEntry		 ::=  SEQUENCE {
		cmdAuthorizationIndex					Integer32,
		cmdAuthorizationRowStatus					RowStatus,
		cmdAuthorizationCMDOID					OBJECT IDENTIFIER,
		cmdAuthorizationCMDName					DisplayString,
		cmdAuthorizationCMDType					INTEGER,
		cmdAuthorizationGroupView					BITS
		}


	cmdAuthorizationIndex		 OBJECT-TYPE
		SYNTAX					 Integer32( 1 .. 1 )
		MAX-ACCESS			 not-accessible
		STATUS					 current
		DESCRIPTION			 " -- "
		::=  { cmdAuthorizationEntry  1 }


	cmdAuthorizationRowStatus		 OBJECT-TYPE
		SYNTAX					 RowStatus
		MAX-ACCESS			 read-only
		STATUS					 current
		DESCRIPTION			 " -- "
		::=  { cmdAuthorizationEntry  2 }


	cmdAuthorizationCMDOID		 OBJECT-TYPE
		SYNTAX					 OBJECT IDENTIFIER
		MAX-ACCESS			 read-only
		STATUS					 current
		DESCRIPTION			 " -- "
		::=  { cmdAuthorizationEntry  3 }


	cmdAuthorizationCMDName		 OBJECT-TYPE
		SYNTAX					 DisplayString( SIZE ( 1 .. 255 ) )
		MAX-ACCESS			 read-only
		STATUS					 current
		DESCRIPTION			 " -- "
		::=  { cmdAuthorizationEntry  4 }


	cmdAuthorizationCMDType		 OBJECT-TYPE
		SYNTAX					 INTEGER{ get(1),config(2),action(3)  }
		MAX-ACCESS			 read-only
		STATUS					 current
		DESCRIPTION			 " -- "
		::=  { cmdAuthorizationEntry  5 }


	cmdAuthorizationGroupView		 OBJECT-TYPE
		SYNTAX					 BITS{ unknown(0),administrator(1),systemUser(2),commonUser(3),guest(4)  }
		MAX-ACCESS			 read-write
		STATUS					 current
		DESCRIPTION			 " -- "
		::=  { cmdAuthorizationEntry  6 }


	mibAuthorizationTable		 OBJECT-TYPE
		SYNTAX					 SEQUENCE  OF	 MibAuthorizationEntry
		MAX-ACCESS			 not-accessible
		STATUS					 current
		DESCRIPTION			 " -- "
		::=  { cmdAuthorizationManagement  2 }


	mibAuthorizationEntry		 OBJECT-TYPE
		SYNTAX					 MibAuthorizationEntry
		MAX-ACCESS			 not-accessible
		STATUS					 current
		DESCRIPTION			 " -- "
		INDEX						{ mibAuthorizationIndex }
		::=  { mibAuthorizationTable  1 }


	MibAuthorizationEntry		 ::=  SEQUENCE {
		mibAuthorizationIndex					Integer32,
		mibAuthorizationRowStatus					RowStatus,
		mibAuthorizationMIBOID					OBJECT IDENTIFIER,
		mibAuthorizationMIBName					DisplayString,
		mibAuthorizationMIBMaxAccess					INTEGER,
		mibAuthorizationGroupView					INTEGER
		}


	mibAuthorizationIndex		 OBJECT-TYPE
		SYNTAX					 Integer32( 1 .. 1 )
		MAX-ACCESS			 not-accessible
		STATUS					 current
		DESCRIPTION			 " -- "
		::=  { mibAuthorizationEntry  1 }


	mibAuthorizationRowStatus		 OBJECT-TYPE
		SYNTAX					 RowStatus
		MAX-ACCESS			 read-only
		STATUS					 current
		DESCRIPTION			 " -- "
		::=  { mibAuthorizationEntry  2 }


	mibAuthorizationMIBOID		 OBJECT-TYPE
		SYNTAX					 OBJECT IDENTIFIER
		MAX-ACCESS			 read-only
		STATUS					 current
		DESCRIPTION			 " -- "
		::=  { mibAuthorizationEntry  3 }


	mibAuthorizationMIBName		 OBJECT-TYPE
		SYNTAX					 DisplayString( SIZE ( 1 .. 255 ) )
		MAX-ACCESS			 read-only
		STATUS					 current
		DESCRIPTION			 " -- "
		::=  { mibAuthorizationEntry  4 }


	mibAuthorizationMIBMaxAccess		 OBJECT-TYPE
		SYNTAX					 INTEGER{ read(0),write(1),create(2)  }
		MAX-ACCESS			 read-only
		STATUS					 current
		DESCRIPTION			 " -- "
		::=  { mibAuthorizationEntry  5 }


	mibAuthorizationGroupView		 OBJECT-TYPE
		SYNTAX					 INTEGER{ unknown(0),administrator(1),systemUser(2),commonUser(3),guest(4)  }
		MAX-ACCESS			 read-write
		STATUS					 current
		DESCRIPTION			 " -- "
		::=  { mibAuthorizationEntry  6 }


	securityCommSetting		 OBJECT IDENTIFIER
		::=  { securityManagement  3 }


	userFailLimits		 OBJECT-TYPE
		SYNTAX					 Unsigned32( 1 .. 6 )
		MAX-ACCESS			 read-write
		STATUS					 current
		DESCRIPTION			 " -- "
		::=  { securityCommSetting  1 }


	userLogOutNoOpTime		 OBJECT-TYPE
		SYNTAX					 Unsigned32( 1 .. 60 )
		MAX-ACCESS			 read-write
		STATUS					 current
		DESCRIPTION			 " -- "
		::=  { securityCommSetting  2 }


	userAutoUnlockTime		 OBJECT-TYPE
		SYNTAX					 Unsigned32( 1 .. 60 )
		MAX-ACCESS			 read-write
		STATUS					 current
		DESCRIPTION			 " -- "
		::=  { securityCommSetting  3 }


	pwdMinLength		 OBJECT-TYPE
		SYNTAX					 Unsigned32( 8 .. 20 )
		MAX-ACCESS			 read-write
		STATUS					 current
		DESCRIPTION			 " -- "
		::=  { securityCommSetting  4 }


	pwdPolicy		 OBJECT-TYPE
		SYNTAX					 INTEGER{ weak(0),strict(1)  }
		MAX-ACCESS			 read-write
		STATUS					 current
		DESCRIPTION			 " -- "
		::=  { securityCommSetting  5 }


	pwdNoRepeatNum		 OBJECT-TYPE
		SYNTAX					 Integer32( 0|1 .. 6 )
		MAX-ACCESS			 read-write
		STATUS					 current
		DESCRIPTION			 " -- "
		::=  { securityCommSetting  6 }


	pwdExpireReminderTime		 OBJECT-TYPE
		SYNTAX					 Integer32( 0|1 .. 10 )
		MAX-ACCESS			 read-write
		STATUS					 current
		DESCRIPTION			 " -- "
		::=  { securityCommSetting  7 }


	userTable		 OBJECT-TYPE
		SYNTAX					 SEQUENCE  OF	 UserEntry
		MAX-ACCESS			 not-accessible
		STATUS					 current
		DESCRIPTION			 " -- "
		::=  { securityManagement  4 }


	userEntry		 OBJECT-TYPE
		SYNTAX					 UserEntry
		MAX-ACCESS			 not-accessible
		STATUS					 current
		DESCRIPTION			 " -- "
		INDEX						{ userIndex }
		::=  { userTable  1 }


	UserEntry		 ::=  SEQUENCE {
		userIndex					Integer32,
		userRowStatus					RowStatus,
		userType					INTEGER,
		userName					DisplayString,
		userPwd					DisplayString,
		userPwdlifeCycle					Integer32,
		userLockedState					INTEGER,
		userAlarmReportSwitch					INTEGER,
		userRemoteLoginSwitch					INTEGER
		}


	userIndex		 OBJECT-TYPE
		SYNTAX					 Integer32( 1 .. 10 )
		MAX-ACCESS			 not-accessible
		STATUS					 current
		DESCRIPTION			 " -- "
		::=  { userEntry  1 }


	userRowStatus		 OBJECT-TYPE
		SYNTAX					 RowStatus
		MAX-ACCESS			 read-create
		STATUS					 current
		DESCRIPTION			 " -- "
		::=  { userEntry  2 }


	userType		 OBJECT-TYPE
		SYNTAX					 INTEGER{ admin(1),system(2),normal(3),patrol(4)  }
		MAX-ACCESS			 read-create
		STATUS					 current
		DESCRIPTION			 " -- "
		::=  { userEntry  3 }


	userName		 OBJECT-TYPE
		SYNTAX					 DisplayString( SIZE ( 1 .. 64 ) )
		MAX-ACCESS			 read-create
		STATUS					 current
		DESCRIPTION			 " -- "
		::=  { userEntry  4 }


	userPwd		 OBJECT-TYPE
		SYNTAX					 DisplayString( SIZE ( 8 .. 255 ) )
		MAX-ACCESS			 read-create
		STATUS					 current
		DESCRIPTION			 " -- "
		::=  { userEntry  5 }


	userPwdlifeCycle		 OBJECT-TYPE
		SYNTAX					 Integer32( 0|1 .. 90 )
		MAX-ACCESS			 read-create
		STATUS					 current
		DESCRIPTION			 " -- "
		::=  { userEntry  6 }


	userLockedState		 OBJECT-TYPE
		SYNTAX					 INTEGER{ locked(0),unlocked(1),pwdErrLocked(2)  }
		MAX-ACCESS			 read-create
		STATUS					 current
		DESCRIPTION			 " -- "
		::=  { userEntry  7 }


	userAlarmReportSwitch		 OBJECT-TYPE
		SYNTAX					 INTEGER{ off(0),on(1)  }
		MAX-ACCESS			 read-write
		STATUS					 current
		DESCRIPTION			 " -- "
		::=  { userEntry  8 }


	userRemoteLoginSwitch		 OBJECT-TYPE
		SYNTAX					 INTEGER{ off(0),on(1)  }
		MAX-ACCESS			 read-write
		STATUS					 current
		DESCRIPTION			 " -- "
		::=  { userEntry  9 }


	userHandoverInfo		 OBJECT IDENTIFIER
		::=  { securityManagement  5 }


	userHandoverUserName		 OBJECT-TYPE
		SYNTAX					 DisplayString( SIZE ( 1 .. 64 ) )
		MAX-ACCESS			 read-write
		STATUS					 current
		DESCRIPTION			 " -- "
		::=  { userHandoverInfo  1 }


	userHandoverUserPwd		 OBJECT-TYPE
		SYNTAX					 DisplayString( SIZE ( 8 .. 255 ) )
		MAX-ACCESS			 read-write
		STATUS					 current
		DESCRIPTION			 " -- "
		::=  { userHandoverInfo  2 }


	userHandoverDisplayTypeListTrigger		 OBJECT-TYPE
		SYNTAX					 INTEGER{ off(0),on(1)  }
		MAX-ACCESS			 read-write
		STATUS					 current
		DESCRIPTION			 " -- "
		::=  { userHandoverInfo  3 }


	eNB		 OBJECT IDENTIFIER
		::=  { lte  2 }


	nodeBSys		 OBJECT IDENTIFIER
		::=  { eNB  1 }


	nodeBInfo		 OBJECT IDENTIFIER
		::=  { nodeBSys  1 }


	nodeBSynTrigger		 OBJECT-TYPE
		SYNTAX					 INTEGER{ off(0),on(1)  }
		MAX-ACCESS			 read-write
		STATUS					 current
		DESCRIPTION			 " -- "
		::=  { nodeBInfo  1 }


	nodeBProtocolVer		 OBJECT-TYPE
		SYNTAX					 INTEGER{ protocolVer1(1),protocolVer2(2),protocolVer3(3)  }
		MAX-ACCESS			 read-only
		STATUS					 current
		DESCRIPTION			 " -- "
		::=  { nodeBInfo  2 }


	nodeBTimeslotOffsetMode		 OBJECT-TYPE
		SYNTAX					 INTEGER{ none(0),tdscdma(1)  }
		MAX-ACCESS			 read-write
		STATUS					 current
		DESCRIPTION			 " -- "
		::=  { nodeBInfo  3 }


	nodeBRRUTimeslotOffset		 OBJECT-TYPE
		SYNTAX					 INTEGER{ none(0),us700(1),us1025(2)  }
		MAX-ACCESS			 read-write
		STATUS					 current
		DESCRIPTION			 " -- "
		::=  { nodeBInfo  4 }


	nodeBModeInfo		 OBJECT-TYPE
		SYNTAX					 BITS{ tds(0),tdl(1)  }
		MAX-ACCESS			 read-only
		STATUS					 current
		DESCRIPTION			 " -- "
		::=  { nodeBInfo  5 }


	maintenceStateNode		 OBJECT IDENTIFIER
		::=  { nodeBSys  2 }


	maintenceStateNotifications		 OBJECT IDENTIFIER
		::=  { maintenceStateNode  1 }


	maintenceStateNotify		 NOTIFICATION-TYPE
		OBJECTS					 { maintenceStateNotiNEType,maintenceStateNotiNEID,maintenceStateValue,maintenceStateOccurTime }
		STATUS					 current
		DESCRIPTION			 " -- "
		::=  { maintenceStateNotifications  1 }


	maintenceStateNotificationObjects		 OBJECT IDENTIFIER
		::=  { maintenceStateNode  2 }


	maintenceStateNotiNEType		 OBJECT-TYPE
		SYNTAX					 INTEGER{ unknown(0),tlb60a(2),emb5116tdlte(3),emb5132tdlte(4),emb5116(5),epc(21),ims(41)  }
		MAX-ACCESS			 accessible-for-notify
		STATUS					 current
		DESCRIPTION			 " -- "
		::=  { maintenceStateNotificationObjects  1 }


	maintenceStateNotiNEID		 OBJECT-TYPE
		SYNTAX					 Unsigned32( 0 .. 4294967295 )
		MAX-ACCESS			 accessible-for-notify
		STATUS					 current
		DESCRIPTION			 " -- "
		::=  { maintenceStateNotificationObjects  2 }


	maintenceStateValue		 OBJECT-TYPE
		SYNTAX					 INTEGER{ waitForEstablish(0),establishing(1),inMaintenance(2),inService(3)  }
		MAX-ACCESS			 accessible-for-notify
		STATUS					 current
		DESCRIPTION			 " -- "
		::=  { maintenceStateNotificationObjects  3 }


	maintenceStateOccurTime		 OBJECT-TYPE
		SYNTAX					 DateAndTime
		MAX-ACCESS			 accessible-for-notify
		STATUS					 current
		DESCRIPTION			 " -- "
		::=  { maintenceStateNotificationObjects  4 }


	nodebBlockStateNode		 OBJECT IDENTIFIER
		::=  { nodeBSys  3 }


	nodebBlockStateNotifications		 OBJECT IDENTIFIER
		::=  { nodebBlockStateNode  1 }


	nodebBlockStateNotify		 NOTIFICATION-TYPE
		OBJECTS					 { nodebBlockStateNotiNEType,nodebBlockStateNotiNEID,nodebBlockStateValue,nodebBlockStatLcId,nodebBlockStateOccurTime }
		STATUS					 current
		DESCRIPTION			 " -- "
		::=  { nodebBlockStateNotifications  1 }


	nodebBlockStateNotificationObjects		 OBJECT IDENTIFIER
		::=  { nodebBlockStateNode  2 }


	nodebBlockStateNotiNEType		 OBJECT-TYPE
		SYNTAX					 INTEGER{ unknown(0),tlb60a(2),emb5116tdlte(3),emb5132tdlte(4),emb5116(5),epc(21),ims(41)  }
		MAX-ACCESS			 accessible-for-notify
		STATUS					 current
		DESCRIPTION			 " -- "
		::=  { nodebBlockStateNotificationObjects  1 }


	nodebBlockStateNotiNEID		 OBJECT-TYPE
		SYNTAX					 Unsigned32( 0 .. 4294967295 )
		MAX-ACCESS			 accessible-for-notify
		STATUS					 current
		DESCRIPTION			 " -- "
		::=  { nodebBlockStateNotificationObjects  2 }


	nodebBlockStateValue		 OBJECT-TYPE
		SYNTAX					 INTEGER{ inMaintenance(2),inService(3)  }
		MAX-ACCESS			 accessible-for-notify
		STATUS					 current
		DESCRIPTION			 " -- "
		::=  { nodebBlockStateNotificationObjects  3 }


	nodebBlockStatLcId		 OBJECT-TYPE
		SYNTAX					 Integer32( 0 .. 255|-1 )
		MAX-ACCESS			 accessible-for-notify
		STATUS					 current
		DESCRIPTION			 " -- "
		::=  { nodebBlockStateNotificationObjects  4 }


	nodebBlockStateOccurTime		 OBJECT-TYPE
		SYNTAX					 DateAndTime
		MAX-ACCESS			 accessible-for-notify
		STATUS					 current
		DESCRIPTION			 " -- "
		::=  { nodebBlockStateNotificationObjects  5 }


	debug		 OBJECT IDENTIFIER
		::=  { eNB  2 }


	policy		 OBJECT IDENTIFIER
		::=  { debug  1 }


	sysStartMode		 OBJECT IDENTIFIER
		::=  { policy  1 }


	sysStartIsNoClkSrcMode		 OBJECT-TYPE
		SYNTAX					 INTEGER{ normal(0),noClkSrc(1)  }
		MAX-ACCESS			 read-write
		STATUS					 current
		DESCRIPTION			 " -- "
		::=  { sysStartMode  1 }


	sysS1CreateMode		 OBJECT-TYPE
		SYNTAX					 INTEGER{ normal(0),noPeerMme(1)  }
		MAX-ACCESS			 read-write
		STATUS					 current
		DESCRIPTION			 " -- "
		::=  { sysStartMode  2 }


	sysX2CreateMode		 OBJECT-TYPE
		SYNTAX					 INTEGER{ normal(0),noPeerEnb(1)  }
		MAX-ACCESS			 read-write
		STATUS					 current
		DESCRIPTION			 " -- "
		::=  { sysStartMode  3 }


	sysPrintMode		 OBJECT-TYPE
		SYNTAX					 INTEGER{ emergency(0),alert(1),critical(2),error(3),warning(4),notice(5),information(6),debug(7),noprint(8)  }
		MAX-ACCESS			 read-write
		STATUS					 current
		DESCRIPTION			 " -- "
		::=  { sysStartMode  4 }


	sysStartIsNoRNCMode		 OBJECT-TYPE
		SYNTAX					 INTEGER{ normal(0),noRNC(1)  }
		MAX-ACCESS			 read-write
		STATUS					 current
		DESCRIPTION			 " -- "
		::=  { sysStartMode  5 }


	logFileConfiguration		 OBJECT IDENTIFIER
		::=  { policy  2 }


	logFileConfigurationTable		 OBJECT-TYPE
		SYNTAX					 SEQUENCE  OF	 LogFileConfigurationEntry
		MAX-ACCESS			 not-accessible
		STATUS					 current
		DESCRIPTION			 " -- "
		::=  { logFileConfiguration  1 }


	logFileConfigurationEntry		 OBJECT-TYPE
		SYNTAX					 LogFileConfigurationEntry
		MAX-ACCESS			 not-accessible
		STATUS					 current
		DESCRIPTION			 " -- "
		INDEX						{ logFileConfigurationIndex }
		::=  { logFileConfigurationTable  1 }


	LogFileConfigurationEntry		 ::=  SEQUENCE {
		logFileConfigurationIndex					INTEGER,
		logFileConfigurationRowStatus					RowStatus,
		logFileConfigurationMaxBytes					Integer32,
		logFileConfigurationMaxNumber					Integer32
		}


	logFileConfigurationIndex		 OBJECT-TYPE
		SYNTAX					 INTEGER{ operationLog(1),alterLog(2),omSecurityLog(3),alarmLog(4),omKeyLog(5),updateLog(6),debugLog(7),statelessAlarmLog(8),eventLog(9),mmlOplog(39),secStatelessAlarmLog(54)  }
		MAX-ACCESS			 not-accessible
		STATUS					 current
		DESCRIPTION			 " -- "
		::=  { logFileConfigurationEntry  1 }


	logFileConfigurationRowStatus		 OBJECT-TYPE
		SYNTAX					 RowStatus
		MAX-ACCESS			 read-create
		STATUS					 current
		DESCRIPTION			 " -- "
		::=  { logFileConfigurationEntry  2 }


	logFileConfigurationMaxBytes		 OBJECT-TYPE
		SYNTAX					 Integer32( 1 .. 5120 )
		MAX-ACCESS			 read-create
		STATUS					 current
		DESCRIPTION			 " -- "
		::=  { logFileConfigurationEntry  3 }


	logFileConfigurationMaxNumber		 OBJECT-TYPE
		SYNTAX					 Integer32( 2 .. 5 )
		MAX-ACCESS			 read-create
		STATUS					 current
		DESCRIPTION			 " -- "
		::=  { logFileConfigurationEntry  4 }


	debugUpload		 OBJECT IDENTIFIER
		::=  { debug  2 }


	debugUploadTable		 OBJECT-TYPE
		SYNTAX					 SEQUENCE  OF	 DebugUploadEntry
		MAX-ACCESS			 not-accessible
		STATUS					 current
		DESCRIPTION			 " -- "
		::=  { debugUpload  1 }


	debugUploadEntry		 OBJECT-TYPE
		SYNTAX					 DebugUploadEntry
		MAX-ACCESS			 not-accessible
		STATUS					 current
		DESCRIPTION			 " -- "
		INDEX						{ debugUploadRackNo,debugUploadShelfNo,debugUploadSlotNo,debugUploadProcNo }
		::=  { debugUploadTable  1 }


	DebugUploadEntry		 ::=  SEQUENCE {
		debugUploadRackNo					Integer32,
		debugUploadShelfNo					Integer32,
		debugUploadSlotNo					Integer32,
		debugUploadProcNo					Integer32,
		debugUploadRowStatus					RowStatus,
		debugUploadType					DisplayString,
		debugUploadDestination					DisplayString,
		debugUploadPercent					Unsigned32
		}


	debugUploadRackNo		 OBJECT-TYPE
		SYNTAX					 Integer32( 0 .. 0 )
		MAX-ACCESS			 not-accessible
		STATUS					 current
		DESCRIPTION			 " -- "
		::=  { debugUploadEntry  1 }


	debugUploadShelfNo		 OBJECT-TYPE
		SYNTAX					 Integer32( 0 .. 0 )
		MAX-ACCESS			 not-accessible
		STATUS					 current
		DESCRIPTION			 " -- "
		::=  { debugUploadEntry  2 }


	debugUploadSlotNo		 OBJECT-TYPE
		SYNTAX					 Integer32( 0 .. 16 )
		MAX-ACCESS			 not-accessible
		STATUS					 current
		DESCRIPTION			 " -- "
		::=  { debugUploadEntry  3 }


	debugUploadProcNo		 OBJECT-TYPE
		SYNTAX					 Integer32( 0 .. 30 )
		MAX-ACCESS			 not-accessible
		STATUS					 current
		DESCRIPTION			 " -- "
		::=  { debugUploadEntry  4 }


	debugUploadRowStatus		 OBJECT-TYPE
		SYNTAX					 RowStatus
		MAX-ACCESS			 read-create
		STATUS					 current
		DESCRIPTION			 " -- "
		::=  { debugUploadEntry  5 }


	debugUploadType		 OBJECT-TYPE
		SYNTAX					 DisplayString( SIZE ( 1 .. 255 ) )
		MAX-ACCESS			 read-create
		STATUS					 current
		DESCRIPTION			 " -- "
		::=  { debugUploadEntry  6 }


	debugUploadDestination		 OBJECT-TYPE
		SYNTAX					 DisplayString( SIZE ( 1 .. 200 ) )
		MAX-ACCESS			 read-create
		STATUS					 current
		DESCRIPTION			 " -- "
		::=  { debugUploadEntry  7 }


	debugUploadPercent		 OBJECT-TYPE
		SYNTAX					 Unsigned32( 0 .. 4294967295 )
		MAX-ACCESS			 read-only
		STATUS					 current
		DESCRIPTION			 " -- "
		::=  { debugUploadEntry  8 }


	processorCore		 OBJECT IDENTIFIER
		::=  { debug  3 }


	processorCoreTable		 OBJECT-TYPE
		SYNTAX					 SEQUENCE  OF	 ProcessorCoreEntry
		MAX-ACCESS			 not-accessible
		STATUS					 current
		DESCRIPTION			 " -- "
		::=  { processorCore  1 }


	processorCoreEntry		 OBJECT-TYPE
		SYNTAX					 ProcessorCoreEntry
		MAX-ACCESS			 not-accessible
		STATUS					 current
		DESCRIPTION			 " -- "
		INDEX						{ procCoreRackNo,procCoreShelfNo,procCoreSlotNo,procCoreIndexOnBoard,procCoreNo }
		::=  { processorCoreTable  1 }


	ProcessorCoreEntry		 ::=  SEQUENCE {
		procCoreRackNo					Integer32,
		procCoreShelfNo					Integer32,
		procCoreSlotNo					Integer32,
		procCoreIndexOnBoard					Integer32,
		procCoreNo					Integer32,
		procCoreRowStatus					RowStatus,
		procCoreType					INTEGER,
		procCoreToProId					Unsigned32,
		procCoreIndexSameType					Integer32,
		procSoftCoreStatus					INTEGER,
		procSoftCoreLoad					Unsigned32
		}


	procCoreRackNo		 OBJECT-TYPE
		SYNTAX					 Integer32( 0 .. 0 )
		MAX-ACCESS			 not-accessible
		STATUS					 current
		DESCRIPTION			 " -- "
		::=  { processorCoreEntry  1 }


	procCoreShelfNo		 OBJECT-TYPE
		SYNTAX					 Integer32( 0 .. 0 )
		MAX-ACCESS			 not-accessible
		STATUS					 current
		DESCRIPTION			 " -- "
		::=  { processorCoreEntry  2 }


	procCoreSlotNo		 OBJECT-TYPE
		SYNTAX					 Integer32( 0 .. 16 )
		MAX-ACCESS			 not-accessible
		STATUS					 current
		DESCRIPTION			 " -- "
		::=  { processorCoreEntry  3 }


	procCoreIndexOnBoard		 OBJECT-TYPE
		SYNTAX					 Integer32( 0 .. 9 )
		MAX-ACCESS			 not-accessible
		STATUS					 current
		DESCRIPTION			 " -- "
		::=  { processorCoreEntry  4 }


	procCoreNo		 OBJECT-TYPE
		SYNTAX					 Integer32( 0 .. 21 )
		MAX-ACCESS			 not-accessible
		STATUS					 current
		DESCRIPTION			 " -- "
		::=  { processorCoreEntry  5 }


	procCoreRowStatus		 OBJECT-TYPE
		SYNTAX					 RowStatus
		MAX-ACCESS			 read-only
		STATUS					 current
		DESCRIPTION			 " -- "
		::=  { processorCoreEntry  6 }


	procCoreType		 OBJECT-TYPE
		SYNTAX					 INTEGER{ unknown(0),mcu(1),dsp(2),fpga(3)  }
		MAX-ACCESS			 read-only
		STATUS					 current
		DESCRIPTION			 " -- "
		::=  { processorCoreEntry  7 }


	procCoreToProId		 OBJECT-TYPE
		SYNTAX					 Unsigned32( 0 .. 4294967295 )
		MAX-ACCESS			 read-only
		STATUS					 current
		DESCRIPTION			 " -- "
		::=  { processorCoreEntry  8 }


	procCoreIndexSameType		 OBJECT-TYPE
		SYNTAX					 Integer32( 1 .. 3 )
		MAX-ACCESS			 read-only
		STATUS					 current
		DESCRIPTION			 " -- "
		::=  { processorCoreEntry  9 }


	procSoftCoreStatus		 OBJECT-TYPE
		SYNTAX					 INTEGER{ normal(0),midLoad(1),highLoad(2),overLoad(3)  }
		MAX-ACCESS			 read-only
		STATUS					 current
		DESCRIPTION			 " -- "
		::=  { processorCoreEntry  11 }


	procSoftCoreLoad		 OBJECT-TYPE
		SYNTAX					 Unsigned32( 0 .. 100 )
		MAX-ACCESS			 read-only
		STATUS					 current
		DESCRIPTION			 " -- "
		::=  { processorCoreEntry  12 }


	cdl		 OBJECT IDENTIFIER
		::=  { debug  4 }


	cdlSwitch		 OBJECT-TYPE
		SYNTAX					 INTEGER{ off(0),on(1)  }
		MAX-ACCESS			 read-write
		STATUS					 current
		DESCRIPTION			 " -- "
		::=  { cdl  1 }


	cdlServerInetAddrType		 OBJECT-TYPE
		SYNTAX					 InetAddressType
		MAX-ACCESS			 read-write
		STATUS					 current
		DESCRIPTION			 " -- "
		::=  { cdl  2 }


	cdlServerInetAddr		 OBJECT-TYPE
		SYNTAX					 InetAddress
		MAX-ACCESS			 read-write
		STATUS					 current
		DESCRIPTION			 " -- "
		::=  { cdl  3 }


	cdlFileDirectory		 OBJECT-TYPE
		SYNTAX					 DisplayString( SIZE ( 1 .. 199 ) )
		MAX-ACCESS			 read-write
		STATUS					 current
		DESCRIPTION			 " -- "
		::=  { cdl  4 }


	cdlFtpServerLoginName		 OBJECT-TYPE
		SYNTAX					 DisplayString( SIZE ( 1 .. 255 ) )
		MAX-ACCESS			 read-write
		STATUS					 current
		DESCRIPTION			 " -- "
		::=  { cdl  5 }


	cdlFtpServerPassword		 OBJECT-TYPE
		SYNTAX					 DisplayString( SIZE ( 1 .. 255 ) )
		MAX-ACCESS			 read-write
		STATUS					 current
		DESCRIPTION			 " -- "
		::=  { cdl  6 }


	cdlFileSize		 OBJECT-TYPE
		SYNTAX					 Unsigned32( 1 .. 10 )
		MAX-ACCESS			 read-write
		STATUS					 current
		DESCRIPTION			 " -- "
		::=  { cdl  7 }


	cdlFileInterval		 OBJECT-TYPE
		SYNTAX					 Unsigned32( 10 .. 30 )
		MAX-ACCESS			 read-only
		STATUS					 current
		DESCRIPTION			 " -- "
		::=  { cdl  8 }


	cdlUploadTrigger		 OBJECT-TYPE
		SYNTAX					 INTEGER{ off(0),on(1)  }
		MAX-ACCESS			 read-write
		STATUS					 current
		DESCRIPTION			 " -- "
		::=  { cdl  9 }


	cdlServiceFileDirectory		 OBJECT-TYPE
		SYNTAX					 DisplayString( SIZE ( 1 .. 199 ) )
		MAX-ACCESS			 read-write
		STATUS					 current
		DESCRIPTION			 " -- "
		::=  { cdl  10 }


	cdlServiceFileSize		 OBJECT-TYPE
		SYNTAX					 Unsigned32( 1 .. 8 )
		MAX-ACCESS			 read-write
		STATUS					 current
		DESCRIPTION			 " -- "
		::=  { cdl  11 }


	cdlResourceStatusUpdateMsgTrigger		 OBJECT-TYPE
		SYNTAX					 INTEGER{ off(0),on(1)  }
		MAX-ACCESS			 read-write
		STATUS					 current
		DESCRIPTION			 " -- "
		::=  { cdl  12 }


	cdlFaultSwitch		 OBJECT-TYPE
		SYNTAX					 INTEGER{ off(0),on(1)  }
		MAX-ACCESS			 read-write
		STATUS					 current
		DESCRIPTION			 " -- "
		::=  { cdl  13 }


	measurementReport		 OBJECT IDENTIFIER
		::=  { debug  5 }


	mrServerInetAddrType		 OBJECT-TYPE
		SYNTAX					 InetAddressType
		MAX-ACCESS			 read-write
		STATUS					 current
		DESCRIPTION			 " -- "
		::=  { measurementReport  1 }


	mrServerInetAddr		 OBJECT-TYPE
		SYNTAX					 InetAddress
		MAX-ACCESS			 read-write
		STATUS					 current
		DESCRIPTION			 " -- "
		::=  { measurementReport  2 }


	mrFileDirectory		 OBJECT-TYPE
		SYNTAX					 DisplayString( SIZE ( 1 .. 199 ) )
		MAX-ACCESS			 read-write
		STATUS					 current
		DESCRIPTION			 " -- "
		::=  { measurementReport  3 }


	mrFtpServerLoginName		 OBJECT-TYPE
		SYNTAX					 DisplayString( SIZE ( 1 .. 255 ) )
		MAX-ACCESS			 read-write
		STATUS					 current
		DESCRIPTION			 " -- "
		::=  { measurementReport  4 }


	mrFtpServerPassword		 OBJECT-TYPE
		SYNTAX					 DisplayString( SIZE ( 1 .. 255 ) )
		MAX-ACCESS			 read-write
		STATUS					 current
		DESCRIPTION			 " -- "
		::=  { measurementReport  5 }


	mrFileSize		 OBJECT-TYPE
		SYNTAX					 Unsigned32( 1 .. 5 )
		MAX-ACCESS			 read-only
		STATUS					 current
		DESCRIPTION			 " -- "
		::=  { measurementReport  6 }


	mrTaskSwitch		 OBJECT-TYPE
		SYNTAX					 INTEGER{ off(0),on(1)  }
		MAX-ACCESS			 read-write
		STATUS					 current
		DESCRIPTION			 " -- "
		::=  { measurementReport  8 }


	mrStartDate		 OBJECT-TYPE
		SYNTAX					 DateAndTime
		MAX-ACCESS			 read-write
		STATUS					 current
		DESCRIPTION			 " -- "
		::=  { measurementReport  9 }


	mrEndDate		 OBJECT-TYPE
		SYNTAX					 DateAndTime
		MAX-ACCESS			 read-write
		STATUS					 current
		DESCRIPTION			 " -- "
		::=  { measurementReport  10 }


	mrTmValidNum		 OBJECT-TYPE
		SYNTAX					 Unsigned32( 0 .. 2 )
		MAX-ACCESS			 read-write
		STATUS					 current
		DESCRIPTION			 " -- "
		::=  { measurementReport  11 }


	mrStartTime1		 OBJECT-TYPE
		SYNTAX					 Unsigned32( 0 .. 23 )
		MAX-ACCESS			 read-write
		STATUS					 current
		DESCRIPTION			 " -- "
		::=  { measurementReport  12 }


	mrEndTime1		 OBJECT-TYPE
		SYNTAX					 Unsigned32( 0 .. 23 )
		MAX-ACCESS			 read-write
		STATUS					 current
		DESCRIPTION			 " -- "
		::=  { measurementReport  13 }


	mrStartTime2		 OBJECT-TYPE
		SYNTAX					 Unsigned32( 0 .. 23 )
		MAX-ACCESS			 read-write
		STATUS					 current
		DESCRIPTION			 " -- "
		::=  { measurementReport  14 }


	mrEndTime2		 OBJECT-TYPE
		SYNTAX					 Unsigned32( 0 .. 23 )
		MAX-ACCESS			 read-write
		STATUS					 current
		DESCRIPTION			 " -- "
		::=  { measurementReport  15 }


	mrMroSamplingPeriod		 OBJECT-TYPE
		SYNTAX					 INTEGER{ ms120(0),ms240(1),ms480(2),ms640(3),ms1024(4),ms2048(5),ms5120(6),ms10240(7),min1(8),min6(9),min12(10),min30(11),min60(12)  }
		MAX-ACCESS			 read-write
		STATUS					 current
		DESCRIPTION			 " -- "
		::=  { measurementReport  16 }


	mrMrsPeriod		 OBJECT-TYPE
		SYNTAX					 INTEGER{ min15(0),min30(1),min60(3)  }
		MAX-ACCESS			 read-write
		STATUS					 current
		DESCRIPTION			 " -- "
		::=  { measurementReport  17 }


	mrDim2MrsBitMap		 OBJECT-TYPE
		SYNTAX					 BITS{ tadvRsrp(0),tadvAoa(1),rsrpRsrq(2),ripRsrp(3),ripRsrq(4),plrULQci1SinrUL(5),plrDLQciRsrq(6),plrDLQciRsrp(7),plrULQc1Rip(8),sinrULRip(9),puschPRBNumPhr(10),pdschPRBNumRsrq(11)  }
		MAX-ACCESS			 read-write
		STATUS					 current
		DESCRIPTION			 " -- "
		::=  { measurementReport  18 }


	mrDim1MrsBitMap		 OBJECT-TYPE
		SYNTAX					 BITS{ rsrp(0),rsrq(1),tadv(2),powerHeadRoom(3),receivedIPower(4),aoa(5),packetLossRateULQci(6),packetLossRateDLQci(7),sinrUL(8),prbreceivedIPower(9),puschPRBNum(10),pdschPRBNum(11),eNBRxTxTimeDiff(12)  }
		MAX-ACCESS			 read-write
		STATUS					 current
		DESCRIPTION			 " -- "
		::=  { measurementReport  19 }


	mrUeMrCfgRatio		 OBJECT-TYPE
		SYNTAX					 Integer32( 0 .. 100 )
		MAX-ACCESS			 read-write
		STATUS					 current
		DESCRIPTION			 " -- "
		::=  { measurementReport  20 }


	mrCellListBitMap		 OBJECT-TYPE
		SYNTAX					 BITS{ localCell0(0),localCell1(1),localCell2(2),localCell3(3),localCell4(4),localCell5(5),localCell6(6),localCell7(7),localCell8(8),localCell9(9),localCell10(10),localCell11(11),localCell12(12),localCell13(13),localCell14(14),localCell15(15),localCell16(16),localCell17(17),localCell18(18),localCell19(19),localCell20(20),localCell21(21),localCell22(22),localCell23(23)  }
		MAX-ACCESS			 read-write
		STATUS					 current
		DESCRIPTION			 " -- "
		::=  { measurementReport  21 }


	mrPrbRptType		 OBJECT-TYPE
		SYNTAX					 INTEGER{ allRpt(0),partRpt(1)  }
		MAX-ACCESS			 read-write
		STATUS					 current
		DESCRIPTION			 " -- "
		::=  { measurementReport  22 }


	mrPrbStartPosition		 OBJECT-TYPE
		SYNTAX					 Integer32( 0 .. 90 )
		MAX-ACCESS			 read-write
		STATUS					 current
		DESCRIPTION			 " -- "
		::=  { measurementReport  23 }


	mrRsrpAdd		 OBJECT-TYPE
		SYNTAX					 Integer32( -7 .. 7 )
		MAX-ACCESS			 read-write
		STATUS					 current
		DESCRIPTION			 " -- "
		::=  { measurementReport  25 }


	mrRsrpDropThreshold		 OBJECT-TYPE
		SYNTAX					 Integer32( 0 .. 60 )
		MAX-ACCESS			 read-write
		STATUS					 current
		DESCRIPTION			 " -- "
		::=  { measurementReport  26 }


	mrRsrpDropRatio		 OBJECT-TYPE
		SYNTAX					 Integer32( 0 .. 100 )
		MAX-ACCESS			 read-write
		STATUS					 current
		DESCRIPTION			 " -- "
		::=  { measurementReport  27 }


	mrPacketLossRate		 OBJECT-TYPE
		SYNTAX					 Integer32( 0 .. 100 )
		MAX-ACCESS			 read-write
		STATUS					 current
		DESCRIPTION			 " -- "
		::=  { measurementReport  28 }


	mrPHRReportMod		 OBJECT-TYPE
		SYNTAX					 INTEGER{ rightnow(0),max(1)  }
		MAX-ACCESS			 read-write
		STATUS					 current
		DESCRIPTION			 " -- "
		::=  { measurementReport  30 }


	mrPHRReportRatio		 OBJECT-TYPE
		SYNTAX					 Integer32( 0 .. 100 )
		MAX-ACCESS			 read-write
		STATUS					 current
		DESCRIPTION			 " -- "
		::=  { measurementReport  31 }


	mrPHRReportDelta		 OBJECT-TYPE
		SYNTAX					 Integer32( 0 .. 20 )
		MAX-ACCESS			 read-write
		STATUS					 current
		DESCRIPTION			 " -- "
		::=  { measurementReport  32 }


	mrMeasCtrlGeranSwitch		 OBJECT-TYPE
		SYNTAX					 INTEGER{ off(0),on(1)  }
		MAX-ACCESS			 read-write
		STATUS					 current
		DESCRIPTION			 " -- "
		::=  { measurementReport  33 }


	mrMeasCtrlUtraSwitch		 OBJECT-TYPE
		SYNTAX					 INTEGER{ off(0),on(1)  }
		MAX-ACCESS			 read-write
		STATUS					 current
		DESCRIPTION			 " -- "
		::=  { measurementReport  34 }


	mrMeasCtrlEutraDifFreSwitch		 OBJECT-TYPE
		SYNTAX					 INTEGER{ off(0),on(1)  }
		MAX-ACCESS			 read-write
		STATUS					 current
		DESCRIPTION			 " -- "
		::=  { measurementReport  35 }


	mrMeasCtrlCdma2000Switch		 OBJECT-TYPE
		SYNTAX					 INTEGER{ off(0),on(1)  }
		MAX-ACCESS			 read-write
		STATUS					 current
		DESCRIPTION			 " -- "
		::=  { measurementReport  36 }


	mrStartDifFreqSysMeasSwitch		 OBJECT-TYPE
		SYNTAX					 INTEGER{ off(0),on(1)  }
		MAX-ACCESS			 read-write
		STATUS					 current
		DESCRIPTION			 " -- "
		::=  { measurementReport  37 }


	mrDocRptMROSwitch		 OBJECT-TYPE
		SYNTAX					 INTEGER{ off(0),on(1)  }
		MAX-ACCESS			 read-write
		STATUS					 current
		DESCRIPTION			 " -- "
		::=  { measurementReport  38 }


	mrDocRptMRESwitch		 OBJECT-TYPE
		SYNTAX					 INTEGER{ off(0),on(1)  }
		MAX-ACCESS			 read-write
		STATUS					 current
		DESCRIPTION			 " -- "
		::=  { measurementReport  39 }


	mrDocRptMRSSwitch		 OBJECT-TYPE
		SYNTAX					 INTEGER{ off(0),on(1)  }
		MAX-ACCESS			 read-write
		STATUS					 current
		DESCRIPTION			 " -- "
		::=  { measurementReport  40 }


	mrUeRxTxTimeDiff		 OBJECT-TYPE
		SYNTAX					 INTEGER{ off(0),on(1)  }
		MAX-ACCESS			 read-write
		STATUS					 current
		DESCRIPTION			 " -- "
		::=  { measurementReport  41 }


	mrLteNcMroOptSwitch		 OBJECT-TYPE
		SYNTAX					 INTEGER{ off(0),on(1)  }
		MAX-ACCESS			 read-write
		STATUS					 current
		DESCRIPTION			 " -- "
		::=  { measurementReport  42 }


	mrPLRULThreshold		 OBJECT-TYPE
		SYNTAX					 Integer32( 0 .. 65535 )
		MAX-ACCESS			 read-write
		STATUS					 current
		DESCRIPTION			 " -- "
		::=  { measurementReport  43 }


	mrPLRULCorrection		 OBJECT-TYPE
		SYNTAX					 Integer32( 0 .. 100 )
		MAX-ACCESS			 read-write
		STATUS					 current
		DESCRIPTION			 " -- "
		::=  { measurementReport  44 }


	mrQCI1PLRULThreshold		 OBJECT-TYPE
		SYNTAX					 Integer32( 0 .. 65535 )
		MAX-ACCESS			 read-write
		STATUS					 current
		DESCRIPTION			 " -- "
		::=  { measurementReport  45 }


	mrQCI1PLRULCorrection		 OBJECT-TYPE
		SYNTAX					 Integer32( 0 .. 100 )
		MAX-ACCESS			 read-write
		STATUS					 current
		DESCRIPTION			 " -- "
		::=  { measurementReport  46 }


	mrQCI5PLRULThreshold		 OBJECT-TYPE
		SYNTAX					 Integer32( 0 .. 65535 )
		MAX-ACCESS			 read-write
		STATUS					 current
		DESCRIPTION			 " -- "
		::=  { measurementReport  47 }


	mrQCI5PLRULCorrection		 OBJECT-TYPE
		SYNTAX					 Integer32( 0 .. 100 )
		MAX-ACCESS			 read-write
		STATUS					 current
		DESCRIPTION			 " -- "
		::=  { measurementReport  48 }


	mrQCI9PLRDLThreshold		 OBJECT-TYPE
		SYNTAX					 Integer32( 0 .. 65535 )
		MAX-ACCESS			 read-write
		STATUS					 current
		DESCRIPTION			 " -- "
		::=  { measurementReport  49 }


	mrQCI9PLRDLCorrection		 OBJECT-TYPE
		SYNTAX					 Integer32( 0 .. 100 )
		MAX-ACCESS			 read-write
		STATUS					 current
		DESCRIPTION			 " -- "
		::=  { measurementReport  50 }


	mrQCI1PLRDLThreshold		 OBJECT-TYPE
		SYNTAX					 Integer32( 0 .. 65535 )
		MAX-ACCESS			 read-write
		STATUS					 current
		DESCRIPTION			 " -- "
		::=  { measurementReport  51 }


	mrQCI1PLRDLCorrection		 OBJECT-TYPE
		SYNTAX					 Integer32( 0 .. 100 )
		MAX-ACCESS			 read-write
		STATUS					 current
		DESCRIPTION			 " -- "
		::=  { measurementReport  52 }


	mrQCI5PLRDLThreshold		 OBJECT-TYPE
		SYNTAX					 Integer32( 0 .. 65535 )
		MAX-ACCESS			 read-write
		STATUS					 current
		DESCRIPTION			 " -- "
		::=  { measurementReport  53 }


	mrQCI5PLRDLCorrection		 OBJECT-TYPE
		SYNTAX					 Integer32( 0 .. 100 )
		MAX-ACCESS			 read-write
		STATUS					 current
		DESCRIPTION			 " -- "
		::=  { measurementReport  54 }


	mrUeCellCompIdRptSwitch		 OBJECT-TYPE
		SYNTAX					 INTEGER{ off(0),on(1)  }
		MAX-ACCESS			 read-write
		STATUS					 current
		DESCRIPTION			 " -- "
		::=  { measurementReport  55 }


	mrImsiRptSwitch		 OBJECT-TYPE
		SYNTAX					 INTEGER{ off(0),on(1)  }
		MAX-ACCESS			 read-write
		STATUS					 current
		DESCRIPTION			 " -- "
		::=  { measurementReport  56 }


	mrUeCellCompIdRptDirectory		 OBJECT-TYPE
		SYNTAX					 DisplayString( SIZE ( 1 .. 199 ) )
		MAX-ACCESS			 read-write
		STATUS					 current
		DESCRIPTION			 " -- "
		::=  { measurementReport  58 }


	mrNcRsrpSwitch		 OBJECT-TYPE
		SYNTAX					 INTEGER{ off(0),on(1)  }
		MAX-ACCESS			 read-write
		STATUS					 current
		DESCRIPTION			 " -- "
		::=  { measurementReport  59 }


	mrNcRsrpOffset		 OBJECT-TYPE
		SYNTAX					 Integer32( 0 .. 20 )
		MAX-ACCESS			 read-write
		STATUS					 current
		DESCRIPTION			 " -- "
		::=  { measurementReport  60 }


	alarmActUpload		 OBJECT IDENTIFIER
		::=  { debug  6 }


	almActUploadRegInfoTable		 OBJECT-TYPE
		SYNTAX					 SEQUENCE  OF	 AlmActUploadRegInfoEntry
		MAX-ACCESS			 not-accessible
		STATUS					 current
		DESCRIPTION			 " -- "
		::=  { alarmActUpload  1 }


	almActUploadRegInfoEntry		 OBJECT-TYPE
		SYNTAX					 AlmActUploadRegInfoEntry
		MAX-ACCESS			 not-accessible
		STATUS					 current
		DESCRIPTION			 " -- "
		INDEX						{ almActUploadAlarmNo,almActUploadLogIdx }
		::=  { almActUploadRegInfoTable  1 }


	AlmActUploadRegInfoEntry		 ::=  SEQUENCE {
		almActUploadAlarmNo					Integer32,
		almActUploadLogIdx					Integer32,
		almActUploadRowStatus					RowStatus,
		almActUploadBoardType					INTEGER,
		almActUploadProcNo					Unsigned32,
		almActUploadLogType					DisplayString
		}


	almActUploadAlarmNo		 OBJECT-TYPE
		SYNTAX					 Integer32( 0 .. 2147483647 )
		MAX-ACCESS			 not-accessible
		STATUS					 current
		DESCRIPTION			 " -- "
		::=  { almActUploadRegInfoEntry  1 }


	almActUploadLogIdx		 OBJECT-TYPE
		SYNTAX					 Integer32( 1 .. 15 )
		MAX-ACCESS			 not-accessible
		STATUS					 current
		DESCRIPTION			 " -- "
		::=  { almActUploadRegInfoEntry  2 }


	almActUploadRowStatus		 OBJECT-TYPE
		SYNTAX					 RowStatus
		MAX-ACCESS			 read-create
		STATUS					 current
		DESCRIPTION			 " -- "
		::=  { almActUploadRegInfoEntry  3 }


	almActUploadBoardType		 OBJECT-TYPE
		SYNTAX					 INTEGER{ unknown(0),scta(97),bpia(98),bpoa(99),bpoe(109),bpof(128),sctc(130),sctd(141),bpog(143),bpoh(177),scte(178),mmbc(224),sctf(240),bpoi(241)  }
		MAX-ACCESS			 read-create
		STATUS					 current
		DESCRIPTION			 " -- "
		::=  { almActUploadRegInfoEntry  4 }


	almActUploadProcNo		 OBJECT-TYPE
		SYNTAX					 Unsigned32( 0 .. 4294967295 )
		MAX-ACCESS			 read-create
		STATUS					 current
		DESCRIPTION			 " -- "
		::=  { almActUploadRegInfoEntry  5 }


	almActUploadLogType		 OBJECT-TYPE
		SYNTAX					 DisplayString( SIZE ( 1 .. 255 ) )
		MAX-ACCESS			 read-create
		STATUS					 current
		DESCRIPTION			 " -- "
		::=  { almActUploadRegInfoEntry  6 }


	almActUploadCfg		 OBJECT IDENTIFIER
		::=  { alarmActUpload  2 }


	almActUploadInetAddrType		 OBJECT-TYPE
		SYNTAX					 InetAddressType
		MAX-ACCESS			 read-write
		STATUS					 current
		DESCRIPTION			 " -- "
		::=  { almActUploadCfg  1 }


	almActUploadInetAddr		 OBJECT-TYPE
		SYNTAX					 InetAddress
		MAX-ACCESS			 read-write
		STATUS					 current
		DESCRIPTION			 " -- "
		::=  { almActUploadCfg  2 }


	almActUploadftpServerLoginName		 OBJECT-TYPE
		SYNTAX					 DisplayString( SIZE ( 1 .. 255 ) )
		MAX-ACCESS			 read-write
		STATUS					 current
		DESCRIPTION			 " -- "
		::=  { almActUploadCfg  3 }


	almActUploadftpServerPassword		 OBJECT-TYPE
		SYNTAX					 DisplayString( SIZE ( 1 .. 255 ) )
		MAX-ACCESS			 read-write
		STATUS					 current
		DESCRIPTION			 " -- "
		::=  { almActUploadCfg  4 }


	almActUploadFTPDirectory		 OBJECT-TYPE
		SYNTAX					 DisplayString( SIZE ( 1 .. 199 ) )
		MAX-ACCESS			 read-write
		STATUS					 current
		DESCRIPTION			 " -- "
		::=  { almActUploadCfg  5 }


	almActUploadSwitch		 OBJECT-TYPE
		SYNTAX					 INTEGER{ off(0),on(1)  }
		MAX-ACCESS			 read-write
		STATUS					 current
		DESCRIPTION			 " -- "
		::=  { almActUploadCfg  6 }


	omTestInfo		 OBJECT IDENTIFIER
		::=  { debug  7 }


	omTestDspTskFltSwitch		 OBJECT-TYPE
		SYNTAX					 INTEGER{ off(0),on(1)  }
		MAX-ACCESS			 read-write
		STATUS					 current
		DESCRIPTION			 " -- "
		::=  { omTestInfo  1 }


	omTestPpcTskFltSwitch		 OBJECT-TYPE
		SYNTAX					 INTEGER{ off(0),on(1)  }
		MAX-ACCESS			 read-write
		STATUS					 current
		DESCRIPTION			 " -- "
		::=  { omTestInfo  2 }


	omTestProcPerformanceAdjFaoctor		 OBJECT-TYPE
		SYNTAX					 Integer32( 1 .. 100 )
		MAX-ACCESS			 read-write
		STATUS					 current
		DESCRIPTION			 " -- "
		::=  { omTestInfo  3 }


	omTestMrStaggerDelayTime		 OBJECT-TYPE
		SYNTAX					 Integer32( 1 .. 10 )
		MAX-ACCESS			 read-write
		STATUS					 current
		DESCRIPTION			 " -- "
		::=  { omTestInfo  4 }


	omTestCdlStaggerDelayTime		 OBJECT-TYPE
		SYNTAX					 Integer32( 2 .. 15 )
		MAX-ACCESS			 read-write
		STATUS					 current
		DESCRIPTION			 " -- "
		::=  { omTestInfo  5 }


	omTestLogSwitch		 OBJECT-TYPE
		SYNTAX					 INTEGER{ off(0),on(1)  }
		MAX-ACCESS			 read-write
		STATUS					 current
		DESCRIPTION			 " -- "
		::=  { omTestInfo  6 }


	omTestCdlRandomGroupTime		 OBJECT-TYPE
		SYNTAX					 Integer32( 0 .. 60 )
		MAX-ACCESS			 read-write
		STATUS					 current
		DESCRIPTION			 " -- "
		::=  { omTestInfo  7 }


	omTestAlarmRpsSwitch		 OBJECT-TYPE
		SYNTAX					 INTEGER{ off(0),on(1)  }
		MAX-ACCESS			 read-write
		STATUS					 current
		DESCRIPTION			 " -- "
		::=  { omTestInfo  8 }


	omTestAlarmRptStats		 OBJECT-TYPE
		SYNTAX					 INTEGER{ notRPT(0),rPT(1)  }
		MAX-ACCESS			 read-only
		STATUS					 current
		DESCRIPTION			 " -- "
		::=  { omTestInfo  9 }


	omTestHeartbeatSwitch		 OBJECT-TYPE
		SYNTAX					 INTEGER{ off(0),on(1)  }
		MAX-ACCESS			 read-write
		STATUS					 current
		DESCRIPTION			 " -- "
		::=  { omTestInfo  10 }


	omTestHeartbeatPeriod		 OBJECT-TYPE
		SYNTAX					 Unsigned32( 1 .. 255 )
		MAX-ACCESS			 read-write
		STATUS					 current
		DESCRIPTION			 " -- "
		::=  { omTestInfo  11 }


	omTestRruResetRruTimer		 OBJECT-TYPE
		SYNTAX					 Integer32( 15 .. 120|0 )
		MAX-ACCESS			 read-write
		STATUS					 current
		DESCRIPTION			 " -- "
		::=  { omTestInfo  12 }


	omTestAlmPersisSwitch		 OBJECT-TYPE
		SYNTAX					 INTEGER{ off(0),on(1)  }
		MAX-ACCESS			 read-write
		STATUS					 current
		DESCRIPTION			 " -- "
		::=  { omTestInfo  13 }


	omTestS1DelayRecSwitch		 OBJECT-TYPE
		SYNTAX					 INTEGER{ off(0),on(1)  }
		MAX-ACCESS			 read-write
		STATUS					 current
		DESCRIPTION			 " -- "
		::=  { omTestInfo  14 }


	nodeBCtrlPolicy		 OBJECT IDENTIFIER
		::=  { eNB  3 }


	alarmCtrlDSPRecoverSwitch		 OBJECT-TYPE
		SYNTAX					 INTEGER{ off(0),on(1)  }
		MAX-ACCESS			 read-write
		STATUS					 current
		DESCRIPTION			 " -- "
		::=  { nodeBCtrlPolicy  1 }


	alarmCtrlRRUVSWRRptSwitch		 OBJECT-TYPE
		SYNTAX					 INTEGER{ off(0),on(1)  }
		MAX-ACCESS			 read-write
		STATUS					 current
		DESCRIPTION			 " -- "
		::=  { nodeBCtrlPolicy  2 }


	rruCtrlVSWRMonitorSwitch		 OBJECT-TYPE
		SYNTAX					 INTEGER{ off(0),on(1)  }
		MAX-ACCESS			 read-write
		STATUS					 current
		DESCRIPTION			 " -- "
		::=  { nodeBCtrlPolicy  3 }


	antennaArrayFaultDealSwitch		 OBJECT-TYPE
		SYNTAX					 INTEGER{ off(0),on(1)  }
		MAX-ACCESS			 read-write
		STATUS					 current
		DESCRIPTION			 " -- "
		::=  { nodeBCtrlPolicy  4 }


	s1FaultResetNBSwitch		 OBJECT-TYPE
		SYNTAX					 INTEGER{ off(0),on(1)  }
		MAX-ACCESS			 read-write
		STATUS					 current
		DESCRIPTION			 " -- "
		::=  { nodeBCtrlPolicy  5 }


	s1FaultResetNBTime		 OBJECT-TYPE
		SYNTAX					 Integer32( 15 .. 1440 )
		MAX-ACCESS			 read-write
		STATUS					 current
		DESCRIPTION			 " -- "
		::=  { nodeBCtrlPolicy  6 }


	selftTestSwitch		 OBJECT-TYPE
		SYNTAX					 INTEGER{ off(0),on(1)  }
		MAX-ACCESS			 read-write
		STATUS					 current
		DESCRIPTION			 " -- "
		::=  { nodeBCtrlPolicy  8 }


	ofpSelfAdaptiveCtrlSwitch		 OBJECT-TYPE
		SYNTAX					 INTEGER{ off(0),on(1)  }
		MAX-ACCESS			 read-write
		STATUS					 current
		DESCRIPTION			 " -- "
		::=  { nodeBCtrlPolicy  9 }


	ofpSelfAdaptiveCtrlTime		 OBJECT-TYPE
		SYNTAX					 Integer32( 5 .. 3600 )
		MAX-ACCESS			 read-write
		STATUS					 current
		DESCRIPTION			 " -- "
		::=  { nodeBCtrlPolicy  10 }


	rruSlaveOfpFaultDealSwitch		 OBJECT-TYPE
		SYNTAX					 INTEGER{ off(0),on(1)  }
		MAX-ACCESS			 read-write
		STATUS					 current
		DESCRIPTION			 " -- "
		::=  { nodeBCtrlPolicy  11 }


	rruFddiRecClkMonSwitch		 OBJECT-TYPE
		SYNTAX					 INTEGER{ off(0),on(1)  }
		MAX-ACCESS			 read-write
		STATUS					 current
		DESCRIPTION			 " -- "
		::=  { nodeBCtrlPolicy  12 }


	curCfgFileSavePeriodSwitch		 OBJECT-TYPE
		SYNTAX					 INTEGER{ off(0),on(1)  }
		MAX-ACCESS			 read-write
		STATUS					 current
		DESCRIPTION			 " -- "
		::=  { nodeBCtrlPolicy  13 }


	curCfgFileSavePeriodTime		 OBJECT-TYPE
		SYNTAX					 Integer32( 15 .. 1440 )
		MAX-ACCESS			 read-write
		STATUS					 current
		DESCRIPTION			 " -- "
		::=  { nodeBCtrlPolicy  14 }


	cfgFileAmalgamTrigger		 OBJECT-TYPE
		SYNTAX					 INTEGER{ off(0),on(1)  }
		MAX-ACCESS			 read-write
		STATUS					 current
		DESCRIPTION			 " -- "
		::=  { nodeBCtrlPolicy  15 }


	rollBackSwitch		 OBJECT-TYPE
		SYNTAX					 INTEGER{ off(0),on(1)  }
		MAX-ACCESS			 read-write
		STATUS					 current
		DESCRIPTION			 " -- "
		::=  { nodeBCtrlPolicy  16 }


	rtIotEventLogSwitch		 OBJECT-TYPE
		SYNTAX					 INTEGER{ off(0),on(1)  }
		MAX-ACCESS			 read-write
		STATUS					 current
		DESCRIPTION			 " -- "
		::=  { nodeBCtrlPolicy  17 }


	s1FaultSnapshotSwitch		 OBJECT-TYPE
		SYNTAX					 INTEGER{ off(0),on(1)  }
		MAX-ACCESS			 read-write
		STATUS					 current
		DESCRIPTION			 " -- "
		::=  { nodeBCtrlPolicy  18 }


	tranRealCapPacketSwitch		 OBJECT-TYPE
		SYNTAX					 INTEGER{ off(0),on(1)  }
		MAX-ACCESS			 read-write
		STATUS					 current
		DESCRIPTION			 " -- "
		::=  { nodeBCtrlPolicy  19 }


	brdIrFrameSelfAdaptSwitch		 OBJECT-TYPE
		SYNTAX					 INTEGER{ off(0),on(1)  }
		MAX-ACCESS			 read-write
		STATUS					 current
		DESCRIPTION			 " -- "
		::=  { nodeBCtrlPolicy  20 }


	protocolStackCapPacketSwitch		 OBJECT-TYPE
		SYNTAX					 INTEGER{ off(0),on(1)  }
		MAX-ACCESS			 read-write
		STATUS					 current
		DESCRIPTION			 " -- "
		::=  { nodeBCtrlPolicy  21 }


	sysUpShiftSwitch		 OBJECT-TYPE
		SYNTAX					 INTEGER{ off(0),on(1)  }
		MAX-ACCESS			 read-write
		STATUS					 current
		DESCRIPTION			 " -- "
		::=  { nodeBCtrlPolicy  22 }


	s1FaultPolicy		 OBJECT-TYPE
		SYNTAX					 INTEGER{ releaseusr(1),redirectusr(2)  }
		MAX-ACCESS			 read-write
		STATUS					 current
		DESCRIPTION			 " -- "
		::=  { nodeBCtrlPolicy  23 }


	selfTransX2SetupSwitch		 OBJECT-TYPE
		SYNTAX					 INTEGER{ off(0),on(1)  }
		MAX-ACCESS			 read-write
		STATUS					 current
		DESCRIPTION			 " -- "
		::=  { nodeBCtrlPolicy  24 }


	freqChangeSwitch		 OBJECT-TYPE
		SYNTAX					 INTEGER{ off(0),on(1)  }
		MAX-ACCESS			 read-write
		STATUS					 current
		DESCRIPTION			 " -- "
		::=  { nodeBCtrlPolicy  25 }


	hlProcMaxNum		 OBJECT-TYPE
		SYNTAX					 Integer32( 1 .. 9 )
		MAX-ACCESS			 read-write
		STATUS					 current
		DESCRIPTION			 " -- "
		::=  { nodeBCtrlPolicy  26 }


	sipCapPacketSwitch		 OBJECT-TYPE
		SYNTAX					 INTEGER{ off(0),on(1)  }
		MAX-ACCESS			 read-write
		STATUS					 current
		DESCRIPTION			 " -- "
		::=  { nodeBCtrlPolicy  28 }


	pcapFilterRule		 OBJECT-TYPE
		SYNTAX					 INTEGER{ noRule(0),ipRule(1),dscpRule(2),cmdRule(3)  }
		MAX-ACCESS			 read-write
		STATUS					 current
		DESCRIPTION			 " -- "
		::=  { nodeBCtrlPolicy  29 }


	pcapFilterIpType		 OBJECT-TYPE
		SYNTAX					 INTEGER{ unknown(0),ipv4(1),ipv6(2)  }
		MAX-ACCESS			 read-write
		STATUS					 current
		DESCRIPTION			 " -- "
		::=  { nodeBCtrlPolicy  30 }


	pcapFilterIpaddress1		 OBJECT-TYPE
		SYNTAX					 InetAddress
		MAX-ACCESS			 read-write
		STATUS					 current
		DESCRIPTION			 " -- "
		::=  { nodeBCtrlPolicy  31 }


	pcapFilterIpaddress2		 OBJECT-TYPE
		SYNTAX					 InetAddress
		MAX-ACCESS			 read-write
		STATUS					 current
		DESCRIPTION			 " -- "
		::=  { nodeBCtrlPolicy  32 }


	pcapFilterIpaddress3		 OBJECT-TYPE
		SYNTAX					 InetAddress
		MAX-ACCESS			 read-write
		STATUS					 current
		DESCRIPTION			 " -- "
		::=  { nodeBCtrlPolicy  33 }


	pcapFilterDscp		 OBJECT-TYPE
		SYNTAX					 Integer32( 0 .. 63|-1 )
		MAX-ACCESS			 read-write
		STATUS					 current
		DESCRIPTION			 " -- "
		::=  { nodeBCtrlPolicy  34 }


	backupVersionTrigger		 OBJECT-TYPE
		SYNTAX					 INTEGER{ off(0),on(1)  }
		MAX-ACCESS			 read-write
		STATUS					 current
		DESCRIPTION			 " -- "
		::=  { nodeBCtrlPolicy  35 }


	backupCopyResult		 OBJECT-TYPE
		SYNTAX					 INTEGER{ invalid(0),fail(1),success(2),backloading(3)  }
		MAX-ACCESS			 read-only
		STATUS					 current
		DESCRIPTION			 " -- "
		::=  { nodeBCtrlPolicy  36 }


	rapidIOSwitch		 OBJECT-TYPE
		SYNTAX					 INTEGER{ off(0),on(1)  }
		MAX-ACCESS			 read-write
		STATUS					 current
		DESCRIPTION			 " -- "
		::=  { nodeBCtrlPolicy  37 }


	enbSgwLinkPerformanceSwitch		 OBJECT-TYPE
		SYNTAX					 INTEGER{ off(0),on(1)  }
		MAX-ACCESS			 read-write
		STATUS					 current
		DESCRIPTION			 " -- "
		::=  { nodeBCtrlPolicy  38 }


	gtpcCheckSwitch		 OBJECT-TYPE
		SYNTAX					 INTEGER{ off(0),on(1)  }
		MAX-ACCESS			 read-write
		STATUS					 current
		DESCRIPTION			 " -- "
		::=  { nodeBCtrlPolicy  40 }


	baseBoardSWCfgEnableSwitch		 OBJECT-TYPE
		SYNTAX					 INTEGER{ off(0),on(1)  }
		MAX-ACCESS			 read-write
		STATUS					 current
		DESCRIPTION			 " -- "
		::=  { nodeBCtrlPolicy  41 }


	rruPortSelfAdaptiveCtrlSwitch		 OBJECT-TYPE
		SYNTAX					 INTEGER{ off(0),on(1)  }
		MAX-ACCESS			 read-write
		STATUS					 current
		DESCRIPTION			 " -- "
		::=  { nodeBCtrlPolicy  42 }


	verProtectSwitch		 OBJECT-TYPE
		SYNTAX					 INTEGER{ off(0),on(1)  }
		MAX-ACCESS			 read-write
		STATUS					 current
		DESCRIPTION			 " -- "
		::=  { nodeBCtrlPolicy  43 }


	reservedCmdString		 OBJECT-TYPE
		SYNTAX					 DisplayString( SIZE ( 1 .. 255 ) )
		MAX-ACCESS			 read-write
		STATUS					 current
		DESCRIPTION			 " -- "
		::=  { nodeBCtrlPolicy  44 }


	omLinkFaultSwitchTime		 OBJECT-TYPE
		SYNTAX					 Integer32( 60 .. 600 )
		MAX-ACCESS			 read-write
		STATUS					 current
		DESCRIPTION			 " -- "
		::=  { nodeBCtrlPolicy  45 }


	tdExitCmdSwitch		 OBJECT-TYPE
		SYNTAX					 INTEGER{ off(0),on(1)  }
		MAX-ACCESS			 read-write
		STATUS					 current
		DESCRIPTION			 " -- "
		::=  { nodeBCtrlPolicy  46 }


	tdExitStatus		 OBJECT-TYPE
		SYNTAX					 INTEGER{ noExit(0),onExit(1),sucExit(2),failExit(3)  }
		MAX-ACCESS			 read-write
		STATUS					 current
		DESCRIPTION			 " -- "
		::=  { nodeBCtrlPolicy  47 }


	eNBConfig		 OBJECT IDENTIFIER
		::=  { eNB  4 }


	transport		 OBJECT IDENTIFIER
		::=  { eNBConfig  1 }


	eNb		 OBJECT IDENTIFIER
		::=  { transport  1 }


	ipPhysicalPort		 OBJECT IDENTIFIER
		::=  { eNb  2 }


	ethernetPortTable		 OBJECT-TYPE
		SYNTAX					 SEQUENCE  OF	 EthernetPortEntry
		MAX-ACCESS			 not-accessible
		STATUS					 current
		DESCRIPTION			 " -- "
		::=  { ipPhysicalPort  1 }


	ethernetPortEntry		 OBJECT-TYPE
		SYNTAX					 EthernetPortEntry
		MAX-ACCESS			 not-accessible
		STATUS					 current
		DESCRIPTION			 " -- "
		INDEX						{ ethRackNo,ethShelfNo,ethSlotNo,ethPhyPortId }
		::=  { ethernetPortTable  1 }


	EthernetPortEntry		 ::=  SEQUENCE {
		ethRackNo					Integer32,
		ethShelfNo					Integer32,
		ethSlotNo					Integer32,
		ethPhyPortId					Integer32,
		ethRowStatus					RowStatus,
		ethCfgPortMode					INTEGER,
		ethRealPortMode					INTEGER,
		ethLogicBandwidth					Unsigned32,
		ethDuplexMode					INTEGER,
		ethLocalMacAddress					MacAddress,
		ethPortBlockSwitch					INTEGER,
		ethPortStatus					INTEGER,
		ethPortUlRate					Unsigned32,
		ethPortDlRate					Unsigned32,
		ethPortUlByte					Unsigned32,
		ethPortDlByte					Unsigned32,
		ethCongestThreshold					Unsigned32,
		ethPortUpUseRatio					Unsigned32,
		ethPortDownUseRatio					Unsigned32,
		ethPortGigabitSwitch					INTEGER,
		ethPortActuralBitRate					Integer32
		}


	ethRackNo		 OBJECT-TYPE
		SYNTAX					 Integer32( 0 .. 0 )
		MAX-ACCESS			 not-accessible
		STATUS					 current
		DESCRIPTION			 " -- "
		::=  { ethernetPortEntry  1 }


	ethShelfNo		 OBJECT-TYPE
		SYNTAX					 Integer32( 0 .. 0 )
		MAX-ACCESS			 not-accessible
		STATUS					 current
		DESCRIPTION			 " -- "
		::=  { ethernetPortEntry  2 }


	ethSlotNo		 OBJECT-TYPE
		SYNTAX					 Integer32( 0 .. 16 )
		MAX-ACCESS			 not-accessible
		STATUS					 current
		DESCRIPTION			 " -- "
		::=  { ethernetPortEntry  3 }


	ethPhyPortId		 OBJECT-TYPE
		SYNTAX					 Integer32( 0 .. 1 )
		MAX-ACCESS			 not-accessible
		STATUS					 current
		DESCRIPTION			 " -- "
		::=  { ethernetPortEntry  4 }


	ethRowStatus		 OBJECT-TYPE
		SYNTAX					 RowStatus
		MAX-ACCESS			 read-only
		STATUS					 current
		DESCRIPTION			 " -- "
		::=  { ethernetPortEntry  5 }


	ethCfgPortMode		 OBJECT-TYPE
		SYNTAX					 INTEGER{ auto(0),t10M(1),t100M(2),t1000M(3),t10000M(4)  }
		MAX-ACCESS			 read-only
		STATUS					 current
		DESCRIPTION			 " -- "
		::=  { ethernetPortEntry  6 }


	ethRealPortMode		 OBJECT-TYPE
		SYNTAX					 INTEGER{ unknown(0),t10M(1),t100M(2),t1000M(3),t10000M(4)  }
		MAX-ACCESS			 read-only
		STATUS					 current
		DESCRIPTION			 " -- "
		::=  { ethernetPortEntry  7 }


	ethLogicBandwidth		 OBJECT-TYPE
		SYNTAX					 Unsigned32( 0 .. 4294967295 )
		MAX-ACCESS			 read-write
		STATUS					 current
		DESCRIPTION			 " -- "
		::=  { ethernetPortEntry  8 }


	ethDuplexMode		 OBJECT-TYPE
		SYNTAX					 INTEGER{ fullDuplex(0),halfDuplex(1)  }
		MAX-ACCESS			 read-only
		STATUS					 current
		DESCRIPTION			 " -- "
		::=  { ethernetPortEntry  9 }


	ethLocalMacAddress		 OBJECT-TYPE
		SYNTAX					 MacAddress
		MAX-ACCESS			 read-write
		STATUS					 current
		DESCRIPTION			 " -- "
		::=  { ethernetPortEntry  11 }


	ethPortBlockSwitch		 OBJECT-TYPE
		SYNTAX					 INTEGER{ block(0),unblock(1)  }
		MAX-ACCESS			 read-write
		STATUS					 current
		DESCRIPTION			 " -- "
		::=  { ethernetPortEntry  12 }


	ethPortStatus		 OBJECT-TYPE
		SYNTAX					 INTEGER{ up(0),down(1)  }
		MAX-ACCESS			 read-only
		STATUS					 current
		DESCRIPTION			 " -- "
		::=  { ethernetPortEntry  13 }


	ethPortUlRate		 OBJECT-TYPE
		SYNTAX					 Unsigned32( 0 .. 4294967295 )
		MAX-ACCESS			 read-only
		STATUS					 current
		DESCRIPTION			 " -- "
		::=  { ethernetPortEntry  14 }


	ethPortDlRate		 OBJECT-TYPE
		SYNTAX					 Unsigned32( 0 .. 4294967295 )
		MAX-ACCESS			 read-only
		STATUS					 current
		DESCRIPTION			 " -- "
		::=  { ethernetPortEntry  15 }


	ethPortUlByte		 OBJECT-TYPE
		SYNTAX					 Unsigned32( 0 .. 4294967295 )
		MAX-ACCESS			 read-only
		STATUS					 current
		DESCRIPTION			 " -- "
		::=  { ethernetPortEntry  16 }


	ethPortDlByte		 OBJECT-TYPE
		SYNTAX					 Unsigned32( 0 .. 4294967295 )
		MAX-ACCESS			 read-only
		STATUS					 current
		DESCRIPTION			 " -- "
		::=  { ethernetPortEntry  17 }


	ethCongestThreshold		 OBJECT-TYPE
		SYNTAX					 Unsigned32( 0 .. 4294967295 )
		MAX-ACCESS			 read-write
		STATUS					 current
		DESCRIPTION			 " -- "
		::=  { ethernetPortEntry  18 }


	ethPortUpUseRatio		 OBJECT-TYPE
		SYNTAX					 Unsigned32( 0 .. 4294967295 )
		MAX-ACCESS			 read-only
		STATUS					 current
		DESCRIPTION			 " -- "
		::=  { ethernetPortEntry  19 }


	ethPortDownUseRatio		 OBJECT-TYPE
		SYNTAX					 Unsigned32( 0 .. 4294967295 )
		MAX-ACCESS			 read-only
		STATUS					 current
		DESCRIPTION			 " -- "
		::=  { ethernetPortEntry  20 }


	ethPortGigabitSwitch		 OBJECT-TYPE
		SYNTAX					 INTEGER{ close(0),open(1)  }
		MAX-ACCESS			 read-write
		STATUS					 current
		DESCRIPTION			 " -- "
		::=  { ethernetPortEntry  21 }


	ethPortActuralBitRate		 OBJECT-TYPE
		SYNTAX					 Integer32( -2147483648 .. 2147483647 )
		MAX-ACCESS			 read-only
		STATUS					 current
		DESCRIPTION			 " -- "
		::=  { ethernetPortEntry  24 }


	nodeBHW		 OBJECT IDENTIFIER
		::=  { eNBConfig  2 }


	clock		 OBJECT IDENTIFIER
		::=  { nodeBHW  1 }


	clockCommon		 OBJECT IDENTIFIER
		::=  { clock  1 }


	clkCommUsableState		 OBJECT-TYPE
		SYNTAX					 INTEGER{ disabled(0),enabled(1)  }
		MAX-ACCESS			 read-only
		STATUS					 current
		DESCRIPTION			 " -- "
		::=  { clockCommon  1 }


	clkCommRunState		 OBJECT-TYPE
		SYNTAX					 INTEGER{ start(0),warmup(1),lock(2),holdover(3),holdoveralert(4),holdovertimeout(5),abnormal(6)  }
		MAX-ACCESS			 read-only
		STATUS					 current
		DESCRIPTION			 " -- "
		::=  { clockCommon  2 }


	clkCommHoldoverTime		 OBJECT-TYPE
		SYNTAX					 Integer32( 0 .. 86400 )
		MAX-ACCESS			 read-only
		STATUS					 current
		DESCRIPTION			 " -- "
		::=  { clockCommon  3 }


	clkCommClkSupplySrc		 OBJECT-TYPE
		SYNTAX					 INTEGER{ unknown(0),gps(1),cnss(2),series(3),ptp1588(4),romteClk(5),cmSync(6),interSeries(7),opSeries(8),ocuSeries(9)  }
		MAX-ACCESS			 read-write
		STATUS					 current
		DESCRIPTION			 " -- "
		::=  { clockCommon  4 }


	clkCommPLLDelayAdjustThreshold		 OBJECT-TYPE
		SYNTAX					 Integer32( 6 .. 300 )
		MAX-ACCESS			 read-write
		STATUS					 current
		DESCRIPTION			 " -- "
		::=  { clockCommon  5 }


	clockSourceTable		 OBJECT-TYPE
		SYNTAX					 SEQUENCE  OF	 ClockSourceEntry
		MAX-ACCESS			 not-accessible
		STATUS					 current
		DESCRIPTION			 " -- "
		::=  { clock  2 }


	clockSourceEntry		 OBJECT-TYPE
		SYNTAX					 ClockSourceEntry
		MAX-ACCESS			 not-accessible
		STATUS					 current
		DESCRIPTION			 " -- "
		INDEX						{ clkSrcIndex }
		::=  { clockSourceTable  1 }


	ClockSourceEntry		 ::=  SEQUENCE {
		clkSrcIndex					Integer32,
		clkSrcRowStatus					RowStatus,
		clkSrcType					INTEGER,
		clkSrcStatus					INTEGER,
		clkSrcDelayValue					Integer32
		}


	clkSrcIndex		 OBJECT-TYPE
		SYNTAX					 Integer32( 1 .. 9 )
		MAX-ACCESS			 not-accessible
		STATUS					 current
		DESCRIPTION			 " -- "
		::=  { clockSourceEntry  1 }


	clkSrcRowStatus		 OBJECT-TYPE
		SYNTAX					 RowStatus
		MAX-ACCESS			 read-only
		STATUS					 current
		DESCRIPTION			 " -- "
		::=  { clockSourceEntry  2 }


	clkSrcType		 OBJECT-TYPE
		SYNTAX					 INTEGER{ unknown(0),gps(1),cnss(2),series(3),ptp1588(4),romteClk(5),cmSync(6),interSeries(7),opSeries(8),ocuSeries(9)  }
		MAX-ACCESS			 read-only
		STATUS					 current
		DESCRIPTION			 " -- "
		::=  { clockSourceEntry  3 }


	clkSrcStatus		 OBJECT-TYPE
		SYNTAX					 INTEGER{ active(0),standby(1),unusable(2)  }
		MAX-ACCESS			 read-only
		STATUS					 current
		DESCRIPTION			 " -- "
		::=  { clockSourceEntry  4 }


	clkSrcDelayValue		 OBJECT-TYPE
		SYNTAX					 Integer32( -1000000 .. 1000000 )
		MAX-ACCESS			 read-write
		STATUS					 current
		DESCRIPTION			 " -- "
		::=  { clockSourceEntry  5 }


	gpsDevice		 OBJECT IDENTIFIER
		::=  { clock  3 }


	gpsTable		 OBJECT-TYPE
		SYNTAX					 SEQUENCE  OF	 GpsEntry
		MAX-ACCESS			 not-accessible
		STATUS					 current
		DESCRIPTION			 " -- "
		::=  { gpsDevice  1 }


	gpsEntry		 OBJECT-TYPE
		SYNTAX					 GpsEntry
		MAX-ACCESS			 not-accessible
		STATUS					 current
		DESCRIPTION			 " -- "
		INDEX						{ gpsRackNo,gpsShelfNo,gpsSlotNo,gpsIndexOnBoard }
		::=  { gpsTable  1 }


	GpsEntry		 ::=  SEQUENCE {
		gpsRackNo					Integer32,
		gpsShelfNo					Integer32,
		gpsSlotNo					Integer32,
		gpsIndexOnBoard					Integer32,
		gpsRowStatus					RowStatus,
		gpsDevType					INTEGER,
		gpsLongitude					DisplayString,
		gpsLatitude					DisplayString,
		gpsElevation					DisplayString,
		gpsUnlockReason					BITS,
		gpsInfoLockSateNum					Integer32,
		gpsInfoSignalValue					DisplayString,
		gpsReceiverSoftWareVer					DisplayString,
		gpsReceiverAntennaDelay					Integer32,
		gpsReceiverResetTrigger					INTEGER
		}


	gpsRackNo		 OBJECT-TYPE
		SYNTAX					 Integer32( 0 .. 0 )
		MAX-ACCESS			 not-accessible
		STATUS					 current
		DESCRIPTION			 " -- "
		::=  { gpsEntry  1 }


	gpsShelfNo		 OBJECT-TYPE
		SYNTAX					 Integer32( 0 .. 0 )
		MAX-ACCESS			 not-accessible
		STATUS					 current
		DESCRIPTION			 " -- "
		::=  { gpsEntry  2 }


	gpsSlotNo		 OBJECT-TYPE
		SYNTAX					 Integer32( 0 .. 16 )
		MAX-ACCESS			 not-accessible
		STATUS					 current
		DESCRIPTION			 " -- "
		::=  { gpsEntry  3 }


	gpsIndexOnBoard		 OBJECT-TYPE
		SYNTAX					 Integer32( 0 .. 1 )
		MAX-ACCESS			 not-accessible
		STATUS					 current
		DESCRIPTION			 " -- "
		::=  { gpsEntry  4 }


	gpsRowStatus		 OBJECT-TYPE
		SYNTAX					 RowStatus
		MAX-ACCESS			 read-only
		STATUS					 current
		DESCRIPTION			 " -- "
		::=  { gpsEntry  5 }


	gpsDevType		 OBJECT-TYPE
		SYNTAX					 INTEGER{ unknown(0),gps(1),cnss(2),romteGps(3)  }
		MAX-ACCESS			 read-only
		STATUS					 current
		DESCRIPTION			 " -- "
		::=  { gpsEntry  6 }


	gpsLongitude		 OBJECT-TYPE
		SYNTAX					 DisplayString( SIZE ( 1 .. 255 ) )
		MAX-ACCESS			 read-only
		STATUS					 current
		DESCRIPTION			 " -- "
		::=  { gpsEntry  7 }


	gpsLatitude		 OBJECT-TYPE
		SYNTAX					 DisplayString( SIZE ( 1 .. 255 ) )
		MAX-ACCESS			 read-only
		STATUS					 current
		DESCRIPTION			 " -- "
		::=  { gpsEntry  8 }


	gpsElevation		 OBJECT-TYPE
		SYNTAX					 DisplayString( SIZE ( 1 .. 255 ) )
		MAX-ACCESS			 read-only
		STATUS					 current
		DESCRIPTION			 " -- "
		::=  { gpsEntry  9 }


	gpsUnlockReason		 OBJECT-TYPE
		SYNTAX					 BITS{ noUse0(0),antOpen(1),antSht(2),notTrk(3),noUse4(4),svyIn(5),noPos(6),lpsecPend(7),testMd(8),posIvd(9),noUse10(10),ancWit(11),ppsGen(12)  }
		MAX-ACCESS			 read-only
		STATUS					 current
		DESCRIPTION			 " -- "
		::=  { gpsEntry  10 }


	gpsInfoLockSateNum		 OBJECT-TYPE
		SYNTAX					 Integer32( 0 .. 255 )
		MAX-ACCESS			 read-only
		STATUS					 current
		DESCRIPTION			 " -- "
		::=  { gpsEntry  11 }


	gpsInfoSignalValue		 OBJECT-TYPE
		SYNTAX					 DisplayString( SIZE ( 1 .. 255 ) )
		MAX-ACCESS			 read-only
		STATUS					 current
		DESCRIPTION			 " -- "
		::=  { gpsEntry  12 }


	gpsReceiverSoftWareVer		 OBJECT-TYPE
		SYNTAX					 DisplayString( SIZE ( 1 .. 255 ) )
		MAX-ACCESS			 read-only
		STATUS					 current
		DESCRIPTION			 " -- "
		::=  { gpsEntry  13 }


	gpsReceiverAntennaDelay		 OBJECT-TYPE
		SYNTAX					 Integer32( 0 .. 2048 )
		MAX-ACCESS			 read-write
		STATUS					 current
		DESCRIPTION			 " -- "
		::=  { gpsEntry  14 }


	gpsReceiverResetTrigger		 OBJECT-TYPE
		SYNTAX					 INTEGER{ off(0),on(1)  }
		MAX-ACCESS			 read-write
		STATUS					 current
		DESCRIPTION			 " -- "
		::=  { gpsEntry  15 }


	remoteClockModule		 OBJECT IDENTIFIER
		::=  { clock  4 }


	remoteClockModuleTable		 OBJECT-TYPE
		SYNTAX					 SEQUENCE  OF	 RemoteClockModuleEntry
		MAX-ACCESS			 not-accessible
		STATUS					 current
		DESCRIPTION			 " -- "
		::=  { remoteClockModule  1 }


	remoteClockModuleEntry		 OBJECT-TYPE
		SYNTAX					 RemoteClockModuleEntry
		MAX-ACCESS			 not-accessible
		STATUS					 current
		DESCRIPTION			 " -- "
		INDEX						{ remoteClkModuleIndex }
		::=  { remoteClockModuleTable  1 }


	RemoteClockModuleEntry		 ::=  SEQUENCE {
		remoteClkModuleIndex					Integer32,
		remoteClkModuleRowStatus					RowStatus,
		remoteClkModuleManufacturer					DisplayString,
		remoteClkModuleAntennaDelay					Integer32,
		remoteClkModuleTemperature					Integer32,
		remoteClkModuleSoftwareVersion					DisplayString,
		remoteClkModuleFirmwareVersion					DisplayString,
		remoteClkModuleHardwareVersion					DisplayString,
		remoteClkModuleSerialNumber					DisplayString,
		remoteClkOpticalModuleRxPower					Integer32,
		remoteClkOpticalModuleTxPower					Integer32,
		remoteClkOpticalModuleManufacturer					DisplayString,
		remoteClkOpticalModuleBitRate					Integer32,
		remoteClkOpticalModuleTemperature					Integer32,
		remoteClkOpticalModuleVoltage					Integer32,
		remoteClkOpticalModuleCurrent					Integer32,
		remoteClkModuleResetTrigger					INTEGER,
		remoteClkModuleLoopBackTrigger					INTEGER,
		remoteClkModuleLockSateNum					Integer32,
		remoteClkModuleSignalValue					DisplayString
		}


	remoteClkModuleIndex		 OBJECT-TYPE
		SYNTAX					 Integer32( 0 .. 1 )
		MAX-ACCESS			 not-accessible
		STATUS					 current
		DESCRIPTION			 " -- "
		::=  { remoteClockModuleEntry  1 }


	remoteClkModuleRowStatus		 OBJECT-TYPE
		SYNTAX					 RowStatus
		MAX-ACCESS			 read-only
		STATUS					 current
		DESCRIPTION			 " -- "
		::=  { remoteClockModuleEntry  2 }


	remoteClkModuleManufacturer		 OBJECT-TYPE
		SYNTAX					 DisplayString( SIZE ( 1 .. 255 ) )
		MAX-ACCESS			 read-only
		STATUS					 current
		DESCRIPTION			 " -- "
		::=  { remoteClockModuleEntry  3 }


	remoteClkModuleAntennaDelay		 OBJECT-TYPE
		SYNTAX					 Integer32( 0 .. 2048 )
		MAX-ACCESS			 read-write
		STATUS					 current
		DESCRIPTION			 " -- "
		::=  { remoteClockModuleEntry  4 }


	remoteClkModuleTemperature		 OBJECT-TYPE
		SYNTAX					 Integer32( -2147483648 .. 2147483647 )
		MAX-ACCESS			 read-only
		STATUS					 current
		DESCRIPTION			 " -- "
		::=  { remoteClockModuleEntry  5 }


	remoteClkModuleSoftwareVersion		 OBJECT-TYPE
		SYNTAX					 DisplayString( SIZE ( 1 .. 255 ) )
		MAX-ACCESS			 read-only
		STATUS					 current
		DESCRIPTION			 " -- "
		::=  { remoteClockModuleEntry  6 }


	remoteClkModuleFirmwareVersion		 OBJECT-TYPE
		SYNTAX					 DisplayString( SIZE ( 1 .. 255 ) )
		MAX-ACCESS			 read-only
		STATUS					 current
		DESCRIPTION			 " -- "
		::=  { remoteClockModuleEntry  7 }


	remoteClkModuleHardwareVersion		 OBJECT-TYPE
		SYNTAX					 DisplayString( SIZE ( 1 .. 255 ) )
		MAX-ACCESS			 read-only
		STATUS					 current
		DESCRIPTION			 " -- "
		::=  { remoteClockModuleEntry  8 }


	remoteClkModuleSerialNumber		 OBJECT-TYPE
		SYNTAX					 DisplayString( SIZE ( 1 .. 255 ) )
		MAX-ACCESS			 read-only
		STATUS					 current
		DESCRIPTION			 " -- "
		::=  { remoteClockModuleEntry  9 }


	remoteClkOpticalModuleRxPower		 OBJECT-TYPE
		SYNTAX					 Integer32( -2147483648 .. 2147483647 )
		MAX-ACCESS			 read-only
		STATUS					 current
		DESCRIPTION			 " -- "
		::=  { remoteClockModuleEntry  10 }


	remoteClkOpticalModuleTxPower		 OBJECT-TYPE
		SYNTAX					 Integer32( -2147483648 .. 2147483647 )
		MAX-ACCESS			 read-only
		STATUS					 current
		DESCRIPTION			 " -- "
		::=  { remoteClockModuleEntry  11 }


	remoteClkOpticalModuleManufacturer		 OBJECT-TYPE
		SYNTAX					 DisplayString( SIZE ( 1 .. 255 ) )
		MAX-ACCESS			 read-only
		STATUS					 current
		DESCRIPTION			 " -- "
		::=  { remoteClockModuleEntry  12 }


	remoteClkOpticalModuleBitRate		 OBJECT-TYPE
		SYNTAX					 Integer32( -2147483648 .. 2147483647 )
		MAX-ACCESS			 read-only
		STATUS					 current
		DESCRIPTION			 " -- "
		::=  { remoteClockModuleEntry  13 }


	remoteClkOpticalModuleTemperature		 OBJECT-TYPE
		SYNTAX					 Integer32( -2147483648 .. 2147483647 )
		MAX-ACCESS			 read-only
		STATUS					 current
		DESCRIPTION			 " -- "
		::=  { remoteClockModuleEntry  14 }


	remoteClkOpticalModuleVoltage		 OBJECT-TYPE
		SYNTAX					 Integer32( -2147483648 .. 2147483647 )
		MAX-ACCESS			 read-only
		STATUS					 current
		DESCRIPTION			 " -- "
		::=  { remoteClockModuleEntry  15 }


	remoteClkOpticalModuleCurrent		 OBJECT-TYPE
		SYNTAX					 Integer32( -2147483648 .. 2147483647 )
		MAX-ACCESS			 read-only
		STATUS					 current
		DESCRIPTION			 " -- "
		::=  { remoteClockModuleEntry  16 }


	remoteClkModuleResetTrigger		 OBJECT-TYPE
		SYNTAX					 INTEGER{ off(0),on(1)  }
		MAX-ACCESS			 read-write
		STATUS					 current
		DESCRIPTION			 " -- "
		::=  { remoteClockModuleEntry  17 }


	remoteClkModuleLoopBackTrigger		 OBJECT-TYPE
		SYNTAX					 INTEGER{ off(0),on(1)  }
		MAX-ACCESS			 read-write
		STATUS					 current
		DESCRIPTION			 " -- "
		::=  { remoteClockModuleEntry  18 }


	remoteClkModuleLockSateNum		 OBJECT-TYPE
		SYNTAX					 Integer32( 0 .. 255 )
		MAX-ACCESS			 read-only
		STATUS					 current
		DESCRIPTION			 " -- "
		::=  { remoteClockModuleEntry  19 }


	remoteClkModuleSignalValue		 OBJECT-TYPE
		SYNTAX					 DisplayString( SIZE ( 1 .. 255 ) )
		MAX-ACCESS			 read-only
		STATUS					 current
		DESCRIPTION			 " -- "
		::=  { remoteClockModuleEntry  20 }


	ofpPortInfo		 OBJECT IDENTIFIER
		::=  { nodeBHW  2 }


	ofpPortTable		 OBJECT-TYPE
		SYNTAX					 SEQUENCE  OF	 OfpPortEntry
		MAX-ACCESS			 not-accessible
		STATUS					 current
		DESCRIPTION			 " -- "
		::=  { ofpPortInfo  1 }


	ofpPortEntry		 OBJECT-TYPE
		SYNTAX					 OfpPortEntry
		MAX-ACCESS			 not-accessible
		STATUS					 current
		DESCRIPTION			 " -- "
		INDEX						{ ofpPortRackNo,ofpPortShelfNo,ofpPortSlotNo,ofpPortIndexOnBoard }
		::=  { ofpPortTable  1 }


	OfpPortEntry		 ::=  SEQUENCE {
		ofpPortRackNo					Integer32,
		ofpPortShelfNo					Integer32,
		ofpPortSlotNo					Integer32,
		ofpPortIndexOnBoard					Integer32,
		ofpPortRowStatus					RowStatus,
		ofpPortType					INTEGER,
		ofpPortFpgaStatus					INTEGER,
		ofpPortModuleStandStatus					INTEGER,
		ofpPortModuleTemperature					Integer32,
		ofpPortModuleVcc					Integer32,
		ofpPortModuleBias					Integer32,
		ofpPortModuleTxPower					Integer32,
		ofpPortModuleRxPower					Integer32,
		ofpPortModuleLossStatus					INTEGER,
		ofpPortModuleVendorName					DisplayString,
		ofpPortModuleS9umKmLen					Integer32,
		ofpPortModuleS9um100MLen					Integer32,
		ofpPortModuleM50um10MLen					Integer32,
		ofpPortModuleM625um10MLen					Integer32,
		ofpPortModuleBitRate					Integer32,
		ofpPortLoopBackTrigger					INTEGER,
		ofpPortLoopCheckPeriod					Unsigned32,
		ofpPortMatchStatus					INTEGER,
		ofpPortLinkStatus					INTEGER,
		ofpPortModuleActualBitRate					Integer32,
		ofpPortFPGARate					INTEGER,
		ofpPortResetOfpTrigger					INTEGER,
		ofpPortOperationStatus					INTEGER,
		ofpPortBitErrorRate					Unsigned32,
		ofpPortFpgaOpenState					INTEGER,
		ofpPortGsmSetFlag					INTEGER
		}


	ofpPortRackNo		 OBJECT-TYPE
		SYNTAX					 Integer32( 0 .. 0 )
		MAX-ACCESS			 not-accessible
		STATUS					 current
		DESCRIPTION			 " -- "
		::=  { ofpPortEntry  1 }


	ofpPortShelfNo		 OBJECT-TYPE
		SYNTAX					 Integer32( 0 .. 0 )
		MAX-ACCESS			 not-accessible
		STATUS					 current
		DESCRIPTION			 " -- "
		::=  { ofpPortEntry  2 }


	ofpPortSlotNo		 OBJECT-TYPE
		SYNTAX					 Integer32( 0 .. 16 )
		MAX-ACCESS			 not-accessible
		STATUS					 current
		DESCRIPTION			 " -- "
		::=  { ofpPortEntry  3 }


	ofpPortIndexOnBoard		 OBJECT-TYPE
		SYNTAX					 Integer32( 0 .. 5 )
		MAX-ACCESS			 not-accessible
		STATUS					 current
		DESCRIPTION			 " -- "
		::=  { ofpPortEntry  4 }


	ofpPortRowStatus		 OBJECT-TYPE
		SYNTAX					 RowStatus
		MAX-ACCESS			 read-only
		STATUS					 current
		DESCRIPTION			 " -- "
		::=  { ofpPortEntry  5 }


	ofpPortType		 OBJECT-TYPE
		SYNTAX					 INTEGER{ unknown(0),eth(1),stm(2),ir(3),remoteClk(4)  }
		MAX-ACCESS			 read-only
		STATUS					 current
		DESCRIPTION			 " -- "
		::=  { ofpPortEntry  6 }


	ofpPortFpgaStatus		 OBJECT-TYPE
		SYNTAX					 INTEGER{ unknown(-1),syn(0),asyn(1)  }
		MAX-ACCESS			 read-only
		STATUS					 current
		DESCRIPTION			 " -- "
		::=  { ofpPortEntry  7 }


	ofpPortModuleStandStatus		 OBJECT-TYPE
		SYNTAX					 INTEGER{ notExisted(0),existed(1)  }
		MAX-ACCESS			 read-only
		STATUS					 current
		DESCRIPTION			 " -- "
		::=  { ofpPortEntry  8 }


	ofpPortModuleTemperature		 OBJECT-TYPE
		SYNTAX					 Integer32( -128 .. 127 )
		MAX-ACCESS			 read-only
		STATUS					 current
		DESCRIPTION			 " -- "
		::=  { ofpPortEntry  9 }


	ofpPortModuleVcc		 OBJECT-TYPE
		SYNTAX					 Integer32( 0 .. 65535 )
		MAX-ACCESS			 read-only
		STATUS					 current
		DESCRIPTION			 " -- "
		::=  { ofpPortEntry  10 }


	ofpPortModuleBias		 OBJECT-TYPE
		SYNTAX					 Integer32( 0 .. 65535 )
		MAX-ACCESS			 read-only
		STATUS					 current
		DESCRIPTION			 " -- "
		::=  { ofpPortEntry  11 }


	ofpPortModuleTxPower		 OBJECT-TYPE
		SYNTAX					 Integer32( -2147483648 .. 2147483647 )
		MAX-ACCESS			 read-only
		STATUS					 current
		DESCRIPTION			 " -- "
		::=  { ofpPortEntry  12 }


	ofpPortModuleRxPower		 OBJECT-TYPE
		SYNTAX					 Integer32( -2147483648 .. 2147483647 )
		MAX-ACCESS			 read-only
		STATUS					 current
		DESCRIPTION			 " -- "
		::=  { ofpPortEntry  13 }


	ofpPortModuleLossStatus		 OBJECT-TYPE
		SYNTAX					 INTEGER{ noLosss(0),loss(1)  }
		MAX-ACCESS			 read-only
		STATUS					 current
		DESCRIPTION			 " -- "
		::=  { ofpPortEntry  14 }


	ofpPortModuleVendorName		 OBJECT-TYPE
		SYNTAX					 DisplayString( SIZE ( 1 .. 255 ) )
		MAX-ACCESS			 read-only
		STATUS					 current
		DESCRIPTION			 " -- "
		::=  { ofpPortEntry  15 }


	ofpPortModuleS9umKmLen		 OBJECT-TYPE
		SYNTAX					 Integer32( 0|1 .. 255 )
		MAX-ACCESS			 read-only
		STATUS					 current
		DESCRIPTION			 " -- "
		::=  { ofpPortEntry  16 }


	ofpPortModuleS9um100MLen		 OBJECT-TYPE
		SYNTAX					 Integer32( 0|1 .. 255 )
		MAX-ACCESS			 read-only
		STATUS					 current
		DESCRIPTION			 " -- "
		::=  { ofpPortEntry  17 }


	ofpPortModuleM50um10MLen		 OBJECT-TYPE
		SYNTAX					 Integer32( 0|1 .. 255 )
		MAX-ACCESS			 read-only
		STATUS					 current
		DESCRIPTION			 " -- "
		::=  { ofpPortEntry  18 }


	ofpPortModuleM625um10MLen		 OBJECT-TYPE
		SYNTAX					 Integer32( 0|1 .. 255 )
		MAX-ACCESS			 read-only
		STATUS					 current
		DESCRIPTION			 " -- "
		::=  { ofpPortEntry  19 }


	ofpPortModuleBitRate		 OBJECT-TYPE
		SYNTAX					 Integer32( -2147483648 .. 2147483647 )
		MAX-ACCESS			 read-only
		STATUS					 current
		DESCRIPTION			 " -- "
		::=  { ofpPortEntry  20 }


	ofpPortLoopBackTrigger		 OBJECT-TYPE
		SYNTAX					 INTEGER{ zeroLoop(0),firstLoop(1),secondLoop(2),thirdLoop(3),fourthLoop(4),fifthLoop(5)  }
		MAX-ACCESS			 read-write
		STATUS					 current
		DESCRIPTION			 " -- "
		::=  { ofpPortEntry  21 }


	ofpPortLoopCheckPeriod		 OBJECT-TYPE
		SYNTAX					 Unsigned32( 0 .. 65535 )
		MAX-ACCESS			 read-write
		STATUS					 current
		DESCRIPTION			 " -- "
		::=  { ofpPortEntry  22 }


	ofpPortMatchStatus		 OBJECT-TYPE
		SYNTAX					 INTEGER{ unknown(0),match(1),notmatch(2)  }
		MAX-ACCESS			 read-only
		STATUS					 current
		DESCRIPTION			 " -- "
		::=  { ofpPortEntry  23 }


	ofpPortLinkStatus		 OBJECT-TYPE
		SYNTAX					 INTEGER{ up(0),down(1)  }
		MAX-ACCESS			 read-only
		STATUS					 current
		DESCRIPTION			 " -- "
		::=  { ofpPortEntry  24 }


	ofpPortModuleActualBitRate		 OBJECT-TYPE
		SYNTAX					 Integer32( -2147483648 .. 2147483647 )
		MAX-ACCESS			 read-only
		STATUS					 current
		DESCRIPTION			 " -- "
		::=  { ofpPortEntry  25 }


	ofpPortFPGARate		 OBJECT-TYPE
		SYNTAX					 INTEGER{ invalid(-1),rate25G(0),rate5G(1),rate10G(3)  }
		MAX-ACCESS			 read-write
		STATUS					 current
		DESCRIPTION			 " -- "
		::=  { ofpPortEntry  26 }


	ofpPortResetOfpTrigger		 OBJECT-TYPE
		SYNTAX					 INTEGER{ off(0),on(1)  }
		MAX-ACCESS			 read-write
		STATUS					 current
		DESCRIPTION			 " -- "
		::=  { ofpPortEntry  27 }


	ofpPortOperationStatus		 OBJECT-TYPE
		SYNTAX					 INTEGER{ enabled(0),disabled(1),invalid(2)  }
		MAX-ACCESS			 read-only
		STATUS					 current
		DESCRIPTION			 " -- "
		::=  { ofpPortEntry  28 }


	ofpPortBitErrorRate		 OBJECT-TYPE
		SYNTAX					 Unsigned32( 0 .. 4294967295 )
		MAX-ACCESS			 read-only
		STATUS					 current
		DESCRIPTION			 " -- "
		::=  { ofpPortEntry  29 }


	ofpPortFpgaOpenState		 OBJECT-TYPE
		SYNTAX					 INTEGER{ off(0),on(1)  }
		MAX-ACCESS			 read-write
		STATUS					 current
		DESCRIPTION			 " -- "
		::=  { ofpPortEntry  30 }


	ofpPortGsmSetFlag		 OBJECT-TYPE
		SYNTAX					 INTEGER{ off(0),on(1)  }
		MAX-ACCESS			 read-only
		STATUS					 current
		DESCRIPTION			 " -- "
		::=  { ofpPortEntry  31 }


	ofpPortCommInfo		 OBJECT IDENTIFIER
		::=  { ofpPortInfo  2 }


	ofpPortRxPowerThreshold		 OBJECT-TYPE
		SYNTAX					 Integer32( -300 .. -100 )
		MAX-ACCESS			 read-write
		STATUS					 current
		DESCRIPTION			 " -- "
		::=  { ofpPortCommInfo  1 }


	environmentMonitor		 OBJECT IDENTIFIER
		::=  { nodeBHW  3 }


	rootNode		 OBJECT IDENTIFIER
		::=  { environmentMonitor  1 }


	outerAlarmBoxTable		 OBJECT-TYPE
		SYNTAX					 SEQUENCE  OF	 OuterAlarmBoxEntry
		MAX-ACCESS			 not-accessible
		STATUS					 current
		DESCRIPTION			 " -- "
		::=  { rootNode  1 }


	outerAlarmBoxEntry		 OBJECT-TYPE
		SYNTAX					 OuterAlarmBoxEntry
		MAX-ACCESS			 not-accessible
		STATUS					 current
		DESCRIPTION			 " -- "
		INDEX						{ oabIndex }
		::=  { outerAlarmBoxTable  1 }


	OuterAlarmBoxEntry		 ::=  SEQUENCE {
		oabIndex					Integer32,
		oabRowStatus					RowStatus,
		oabResetTrigger					INTEGER,
		oabPathReverseStatus					Unsigned32
		}


	oabIndex		 OBJECT-TYPE
		SYNTAX					 Integer32( 0 .. 0 )
		MAX-ACCESS			 not-accessible
		STATUS					 current
		DESCRIPTION			 " -- "
		::=  { outerAlarmBoxEntry  1 }


	oabRowStatus		 OBJECT-TYPE
		SYNTAX					 RowStatus
		MAX-ACCESS			 read-only
		STATUS					 current
		DESCRIPTION			 " -- "
		::=  { outerAlarmBoxEntry  2 }


	oabResetTrigger		 OBJECT-TYPE
		SYNTAX					 INTEGER{ off(0),on(1)  }
		MAX-ACCESS			 read-write
		STATUS					 current
		DESCRIPTION			 " -- "
		::=  { outerAlarmBoxEntry  3 }


	oabPathReverseStatus		 OBJECT-TYPE
		SYNTAX					 Unsigned32( 0 .. 4294967295 )
		MAX-ACCESS			 read-write
		STATUS					 current
		DESCRIPTION			 " -- "
		::=  { outerAlarmBoxEntry  4 }


	dryContactTable		 OBJECT-TYPE
		SYNTAX					 SEQUENCE  OF	 DryContactEntry
		MAX-ACCESS			 not-accessible
		STATUS					 current
		DESCRIPTION			 " -- "
		::=  { rootNode  2 }


	dryContactEntry		 OBJECT-TYPE
		SYNTAX					 DryContactEntry
		MAX-ACCESS			 not-accessible
		STATUS					 current
		DESCRIPTION			 " -- "
		INDEX						{ dryContactNo }
		::=  { dryContactTable  1 }


	DryContactEntry		 ::=  SEQUENCE {
		dryContactNo					Integer32,
		dryContactRowStatus					RowStatus,
		dryContactAlarmNo					Integer32,
		dryContactAlarmState					INTEGER
		}


	dryContactNo		 OBJECT-TYPE
		SYNTAX					 Integer32( 1 .. 32 )
		MAX-ACCESS			 not-accessible
		STATUS					 current
		DESCRIPTION			 " -- "
		::=  { dryContactEntry  1 }


	dryContactRowStatus		 OBJECT-TYPE
		SYNTAX					 RowStatus
		MAX-ACCESS			 read-create
		STATUS					 current
		DESCRIPTION			 " -- "
		::=  { dryContactEntry  2 }


	dryContactAlarmNo		 OBJECT-TYPE
		SYNTAX					 Integer32( 0|1219 .. 1234 )
		MAX-ACCESS			 read-create
		STATUS					 current
		DESCRIPTION			 " -- "
		::=  { dryContactEntry  3 }


	dryContactAlarmState		 OBJECT-TYPE
		SYNTAX					 INTEGER{ on(0),off(1)  }
		MAX-ACCESS			 read-create
		STATUS					 current
		DESCRIPTION			 " -- "
		::=  { dryContactEntry  4 }


	supervisionEquipment		 OBJECT IDENTIFIER
		::=  { environmentMonitor  2 }


	emEquipmentTable		 OBJECT-TYPE
		SYNTAX					 SEQUENCE  OF	 EmEquipmentEntry
		MAX-ACCESS			 not-accessible
		STATUS					 current
		DESCRIPTION			 " -- "
		::=  { supervisionEquipment  1 }


	emEquipmentEntry		 OBJECT-TYPE
		SYNTAX					 EmEquipmentEntry
		MAX-ACCESS			 not-accessible
		STATUS					 current
		DESCRIPTION			 " -- "
		INDEX						{ emEquipmentIndex }
		::=  { emEquipmentTable  1 }


	EmEquipmentEntry		 ::=  SEQUENCE {
		emEquipmentIndex					Integer32,
		emEquipmentRowStatus					RowStatus,
		emEquipmentLocation					DisplayString,
		emEquipmentManufacturer					DisplayString,
		emEquipmentModel					DisplayString,
		emEquipmentProtocolVersion					INTEGER,
		emEquipmentSoftwareVersion					DisplayString,
		emEquipmentOperationState					INTEGER
		}


	emEquipmentIndex		 OBJECT-TYPE
		SYNTAX					 Integer32( 0 .. 0 )
		MAX-ACCESS			 not-accessible
		STATUS					 current
		DESCRIPTION			 " -- "
		::=  { emEquipmentEntry  1 }


	emEquipmentRowStatus		 OBJECT-TYPE
		SYNTAX					 RowStatus
		MAX-ACCESS			 read-only
		STATUS					 current
		DESCRIPTION			 " -- "
		::=  { emEquipmentEntry  2 }


	emEquipmentLocation		 OBJECT-TYPE
		SYNTAX					 DisplayString( SIZE ( 1 .. 255 ) )
		MAX-ACCESS			 read-write
		STATUS					 current
		DESCRIPTION			 " -- "
		::=  { emEquipmentEntry  3 }


	emEquipmentManufacturer		 OBJECT-TYPE
		SYNTAX					 DisplayString( SIZE ( 1 .. 255 ) )
		MAX-ACCESS			 read-only
		STATUS					 current
		DESCRIPTION			 " -- "
		::=  { emEquipmentEntry  4 }


	emEquipmentModel		 OBJECT-TYPE
		SYNTAX					 DisplayString( SIZE ( 1 .. 255 ) )
		MAX-ACCESS			 read-only
		STATUS					 current
		DESCRIPTION			 " -- "
		::=  { emEquipmentEntry  5 }


	emEquipmentProtocolVersion		 OBJECT-TYPE
		SYNTAX					 INTEGER{ unknown(0),ver20(1)  }
		MAX-ACCESS			 read-only
		STATUS					 current
		DESCRIPTION			 " -- "
		::=  { emEquipmentEntry  6 }


	emEquipmentSoftwareVersion		 OBJECT-TYPE
		SYNTAX					 DisplayString( SIZE ( 1 .. 255 ) )
		MAX-ACCESS			 read-only
		STATUS					 current
		DESCRIPTION			 " -- "
		::=  { emEquipmentEntry  7 }


	emEquipmentOperationState		 OBJECT-TYPE
		SYNTAX					 INTEGER{ disabled(0),enabled(1)  }
		MAX-ACCESS			 read-only
		STATUS					 current
		DESCRIPTION			 " -- "
		::=  { emEquipmentEntry  8 }


	emTemperatureTable		 OBJECT-TYPE
		SYNTAX					 SEQUENCE  OF	 EmTemperatureEntry
		MAX-ACCESS			 not-accessible
		STATUS					 current
		DESCRIPTION			 " -- "
		::=  { supervisionEquipment  2 }


	emTemperatureEntry		 OBJECT-TYPE
		SYNTAX					 EmTemperatureEntry
		MAX-ACCESS			 not-accessible
		STATUS					 current
		DESCRIPTION			 " -- "
		INDEX						{ emTemperatureIndex }
		::=  { emTemperatureTable  1 }


	EmTemperatureEntry		 ::=  SEQUENCE {
		emTemperatureIndex					Integer32,
		emTemperatureRowStatus					RowStatus,
		emTemperatureLocation					DisplayString,
		emTemperature					Integer32,
		emTemperatureUpperLimit					Integer32,
		emTemperatureLowerLimit					Integer32
		}


	emTemperatureIndex		 OBJECT-TYPE
		SYNTAX					 Integer32( 0 .. 2 )
		MAX-ACCESS			 not-accessible
		STATUS					 current
		DESCRIPTION			 " -- "
		::=  { emTemperatureEntry  1 }


	emTemperatureRowStatus		 OBJECT-TYPE
		SYNTAX					 RowStatus
		MAX-ACCESS			 read-only
		STATUS					 current
		DESCRIPTION			 " -- "
		::=  { emTemperatureEntry  2 }


	emTemperatureLocation		 OBJECT-TYPE
		SYNTAX					 DisplayString( SIZE ( 1 .. 255 ) )
		MAX-ACCESS			 read-write
		STATUS					 current
		DESCRIPTION			 " -- "
		::=  { emTemperatureEntry  3 }


	emTemperature		 OBJECT-TYPE
		SYNTAX					 Integer32( -9999 .. 10000|65535 )
		MAX-ACCESS			 read-only
		STATUS					 current
		DESCRIPTION			 " -- "
		::=  { emTemperatureEntry  4 }


	emTemperatureUpperLimit		 OBJECT-TYPE
		SYNTAX					 Integer32( 3000 .. 6000 )
		MAX-ACCESS			 read-write
		STATUS					 current
		DESCRIPTION			 " -- "
		::=  { emTemperatureEntry  5 }


	emTemperatureLowerLimit		 OBJECT-TYPE
		SYNTAX					 Integer32( -1500 .. 1000 )
		MAX-ACCESS			 read-write
		STATUS					 current
		DESCRIPTION			 " -- "
		::=  { emTemperatureEntry  6 }


	emHumidityTable		 OBJECT-TYPE
		SYNTAX					 SEQUENCE  OF	 EmHumidityEntry
		MAX-ACCESS			 not-accessible
		STATUS					 current
		DESCRIPTION			 " -- "
		::=  { supervisionEquipment  3 }


	emHumidityEntry		 OBJECT-TYPE
		SYNTAX					 EmHumidityEntry
		MAX-ACCESS			 not-accessible
		STATUS					 current
		DESCRIPTION			 " -- "
		INDEX						{ emHumidityIndex }
		::=  { emHumidityTable  1 }


	EmHumidityEntry		 ::=  SEQUENCE {
		emHumidityIndex					Integer32,
		emHumidityRowStatus					RowStatus,
		emHumidityLocation					DisplayString,
		emHumidity					Integer32,
		emHumidityUpperLimit					Integer32,
		emHumidityLowerLimit					Integer32
		}


	emHumidityIndex		 OBJECT-TYPE
		SYNTAX					 Integer32( 0 .. 0 )
		MAX-ACCESS			 not-accessible
		STATUS					 current
		DESCRIPTION			 " -- "
		::=  { emHumidityEntry  1 }


	emHumidityRowStatus		 OBJECT-TYPE
		SYNTAX					 RowStatus
		MAX-ACCESS			 read-only
		STATUS					 current
		DESCRIPTION			 " -- "
		::=  { emHumidityEntry  2 }


	emHumidityLocation		 OBJECT-TYPE
		SYNTAX					 DisplayString( SIZE ( 1 .. 255 ) )
		MAX-ACCESS			 read-write
		STATUS					 current
		DESCRIPTION			 " -- "
		::=  { emHumidityEntry  3 }


	emHumidity		 OBJECT-TYPE
		SYNTAX					 Integer32( 0 .. 10000|65535 )
		MAX-ACCESS			 read-only
		STATUS					 current
		DESCRIPTION			 " -- "
		::=  { emHumidityEntry  4 }


	emHumidityUpperLimit		 OBJECT-TYPE
		SYNTAX					 Integer32( 7000 .. 9000 )
		MAX-ACCESS			 read-write
		STATUS					 current
		DESCRIPTION			 " -- "
		::=  { emHumidityEntry  5 }


	emHumidityLowerLimit		 OBJECT-TYPE
		SYNTAX					 Integer32( 2000 .. 4000 )
		MAX-ACCESS			 read-write
		STATUS					 current
		DESCRIPTION			 " -- "
		::=  { emHumidityEntry  6 }


	emSmokeTable		 OBJECT-TYPE
		SYNTAX					 SEQUENCE  OF	 EmSmokeEntry
		MAX-ACCESS			 not-accessible
		STATUS					 current
		DESCRIPTION			 " -- "
		::=  { supervisionEquipment  4 }


	emSmokeEntry		 OBJECT-TYPE
		SYNTAX					 EmSmokeEntry
		MAX-ACCESS			 not-accessible
		STATUS					 current
		DESCRIPTION			 " -- "
		INDEX						{ emSmokeIndex }
		::=  { emSmokeTable  1 }


	EmSmokeEntry		 ::=  SEQUENCE {
		emSmokeIndex					Integer32,
		emSmokeRowStatus					RowStatus,
		emSmokeLocation					DisplayString
		}


	emSmokeIndex		 OBJECT-TYPE
		SYNTAX					 Integer32( 0 .. 0 )
		MAX-ACCESS			 not-accessible
		STATUS					 current
		DESCRIPTION			 " -- "
		::=  { emSmokeEntry  1 }


	emSmokeRowStatus		 OBJECT-TYPE
		SYNTAX					 RowStatus
		MAX-ACCESS			 read-only
		STATUS					 current
		DESCRIPTION			 " -- "
		::=  { emSmokeEntry  2 }


	emSmokeLocation		 OBJECT-TYPE
		SYNTAX					 DisplayString( SIZE ( 1 .. 255 ) )
		MAX-ACCESS			 read-write
		STATUS					 current
		DESCRIPTION			 " -- "
		::=  { emSmokeEntry  3 }


	emWaterTable		 OBJECT-TYPE
		SYNTAX					 SEQUENCE  OF	 EmWaterEntry
		MAX-ACCESS			 not-accessible
		STATUS					 current
		DESCRIPTION			 " -- "
		::=  { supervisionEquipment  5 }


	emWaterEntry		 OBJECT-TYPE
		SYNTAX					 EmWaterEntry
		MAX-ACCESS			 not-accessible
		STATUS					 current
		DESCRIPTION			 " -- "
		INDEX						{ emWaterIndex }
		::=  { emWaterTable  1 }


	EmWaterEntry		 ::=  SEQUENCE {
		emWaterIndex					Integer32,
		emWaterRowStatus					RowStatus,
		emWaterLocation					DisplayString
		}


	emWaterIndex		 OBJECT-TYPE
		SYNTAX					 Integer32( 0 .. 0 )
		MAX-ACCESS			 not-accessible
		STATUS					 current
		DESCRIPTION			 " -- "
		::=  { emWaterEntry  1 }


	emWaterRowStatus		 OBJECT-TYPE
		SYNTAX					 RowStatus
		MAX-ACCESS			 read-only
		STATUS					 current
		DESCRIPTION			 " -- "
		::=  { emWaterEntry  2 }


	emWaterLocation		 OBJECT-TYPE
		SYNTAX					 DisplayString( SIZE ( 1 .. 255 ) )
		MAX-ACCESS			 read-write
		STATUS					 current
		DESCRIPTION			 " -- "
		::=  { emWaterEntry  3 }


	emTheftTable		 OBJECT-TYPE
		SYNTAX					 SEQUENCE  OF	 EmTheftEntry
		MAX-ACCESS			 not-accessible
		STATUS					 current
		DESCRIPTION			 " -- "
		::=  { supervisionEquipment  6 }


	emTheftEntry		 OBJECT-TYPE
		SYNTAX					 EmTheftEntry
		MAX-ACCESS			 not-accessible
		STATUS					 current
		DESCRIPTION			 " -- "
		INDEX						{ emTheftIndex }
		::=  { emTheftTable  1 }


	EmTheftEntry		 ::=  SEQUENCE {
		emTheftIndex					Integer32,
		emTheftRowStatus					RowStatus,
		emTheftLocation					DisplayString
		}


	emTheftIndex		 OBJECT-TYPE
		SYNTAX					 Integer32( 0 .. 2 )
		MAX-ACCESS			 not-accessible
		STATUS					 current
		DESCRIPTION			 " -- "
		::=  { emTheftEntry  1 }


	emTheftRowStatus		 OBJECT-TYPE
		SYNTAX					 RowStatus
		MAX-ACCESS			 read-only
		STATUS					 current
		DESCRIPTION			 " -- "
		::=  { emTheftEntry  2 }


	emTheftLocation		 OBJECT-TYPE
		SYNTAX					 DisplayString( SIZE ( 1 .. 255 ) )
		MAX-ACCESS			 read-write
		STATUS					 current
		DESCRIPTION			 " -- "
		::=  { emTheftEntry  3 }


	emThunderboltTable		 OBJECT-TYPE
		SYNTAX					 SEQUENCE  OF	 EmThunderboltEntry
		MAX-ACCESS			 not-accessible
		STATUS					 current
		DESCRIPTION			 " -- "
		::=  { supervisionEquipment  7 }


	emThunderboltEntry		 OBJECT-TYPE
		SYNTAX					 EmThunderboltEntry
		MAX-ACCESS			 not-accessible
		STATUS					 current
		DESCRIPTION			 " -- "
		INDEX						{ emThunderboltIndex }
		::=  { emThunderboltTable  1 }


	EmThunderboltEntry		 ::=  SEQUENCE {
		emThunderboltIndex					Integer32,
		emThunderboltRowStatus					RowStatus,
		emThunderboltLocation					DisplayString,
		emThunderboltAlarmSwitchReportState					INTEGER
		}


	emThunderboltIndex		 OBJECT-TYPE
		SYNTAX					 Integer32( 0 .. 6 )
		MAX-ACCESS			 not-accessible
		STATUS					 current
		DESCRIPTION			 " -- "
		::=  { emThunderboltEntry  1 }


	emThunderboltRowStatus		 OBJECT-TYPE
		SYNTAX					 RowStatus
		MAX-ACCESS			 read-only
		STATUS					 current
		DESCRIPTION			 " -- "
		::=  { emThunderboltEntry  2 }


	emThunderboltLocation		 OBJECT-TYPE
		SYNTAX					 DisplayString( SIZE ( 1 .. 255 ) )
		MAX-ACCESS			 read-write
		STATUS					 current
		DESCRIPTION			 " -- "
		::=  { emThunderboltEntry  3 }


	emThunderboltAlarmSwitchReportState		 OBJECT-TYPE
		SYNTAX					 INTEGER{ unknown(0),high(3),lower(4)  }
		MAX-ACCESS			 read-write
		STATUS					 current
		DESCRIPTION			 " -- "
		::=  { emThunderboltEntry  4 }


	peripheralEquipment		 OBJECT IDENTIFIER
		::=  { environmentMonitor  3 }


	airConditioner		 OBJECT IDENTIFIER
		::=  { peripheralEquipment  1 }


	airConditionerTable		 OBJECT-TYPE
		SYNTAX					 SEQUENCE  OF	 AirConditionerEntry
		MAX-ACCESS			 not-accessible
		STATUS					 current
		DESCRIPTION			 " -- "
		::=  { airConditioner  1 }


	airConditionerEntry		 OBJECT-TYPE
		SYNTAX					 AirConditionerEntry
		MAX-ACCESS			 not-accessible
		STATUS					 current
		DESCRIPTION			 " -- "
		INDEX						{ airConditionerIndex }
		::=  { airConditionerTable  1 }


	AirConditionerEntry		 ::=  SEQUENCE {
		airConditionerIndex					Integer32,
		airConditionerRowStatus					RowStatus,
		airCondLocation					DisplayString,
		airCondManufacturer					DisplayString,
		airCondModel					DisplayString,
		airCondProtocolVersion					INTEGER,
		airCondRunningSwitch					INTEGER,
		airCondRunningState					INTEGER,
		airCondVentilationState					INTEGER,
		airCondCoolingState					INTEGER,
		airCondHeatingState					INTEGER,
		airCondCoolingStopTemperature					Integer32,
		airCondCoolingSensitivity					Integer32,
		airCondWarmingStartTemperature					Integer32,
		airCondWarmingSensitivity					Integer32,
		airCondOverTemperatureLimit					Integer32,
		airCondUnderTemperatureLimit					Integer32,
		airCondVoltage					Integer32,
		airCondSupplyAirTemperature					Integer32,
		airCondReturnAirTemperature					Integer32,
		airCondSupplyAirHumidity					Integer32,
		airCondReturnAirHumidity					Integer32,
		airCondOverVoltageAlarmState					INTEGER,
		airCondUnderVoltageAlarmState					INTEGER,
		airCondOverTemperatureAlarmState					INTEGER,
		airCondUnderTemperatureAlarmState					INTEGER,
		airCondInnerFanAlarmState					INTEGER,
		airCondOuterFanAlarmState					INTEGER,
		airCondReturnAirTempSensorAlarmState					INTEGER,
		airCondReturnAirHumiditySensorAlarmState					INTEGER,
		airCondCompressorOverVoltageAlarmState					INTEGER,
		airCondCompressorUnderVoltageAlarmState					INTEGER,
		airCondFilterLoggedAlarmState					INTEGER,
		airCondOperationState					INTEGER
		}


	airConditionerIndex		 OBJECT-TYPE
		SYNTAX					 Integer32( 0 .. 0 )
		MAX-ACCESS			 not-accessible
		STATUS					 current
		DESCRIPTION			 " -- "
		::=  { airConditionerEntry  1 }


	airConditionerRowStatus		 OBJECT-TYPE
		SYNTAX					 RowStatus
		MAX-ACCESS			 read-only
		STATUS					 current
		DESCRIPTION			 " -- "
		::=  { airConditionerEntry  2 }


	airCondLocation		 OBJECT-TYPE
		SYNTAX					 DisplayString( SIZE ( 1 .. 255 ) )
		MAX-ACCESS			 read-write
		STATUS					 current
		DESCRIPTION			 " -- "
		::=  { airConditionerEntry  3 }


	airCondManufacturer		 OBJECT-TYPE
		SYNTAX					 DisplayString( SIZE ( 1 .. 255 ) )
		MAX-ACCESS			 read-only
		STATUS					 current
		DESCRIPTION			 " -- "
		::=  { airConditionerEntry  4 }


	airCondModel		 OBJECT-TYPE
		SYNTAX					 DisplayString( SIZE ( 1 .. 255 ) )
		MAX-ACCESS			 read-only
		STATUS					 current
		DESCRIPTION			 " -- "
		::=  { airConditionerEntry  5 }


	airCondProtocolVersion		 OBJECT-TYPE
		SYNTAX					 INTEGER{ unknown(0),ver20(1)  }
		MAX-ACCESS			 read-only
		STATUS					 current
		DESCRIPTION			 " -- "
		::=  { airConditionerEntry  6 }


	airCondRunningSwitch		 OBJECT-TYPE
		SYNTAX					 INTEGER{ off(0),on(1)  }
		MAX-ACCESS			 read-write
		STATUS					 current
		DESCRIPTION			 " -- "
		::=  { airConditionerEntry  7 }


	airCondRunningState		 OBJECT-TYPE
		SYNTAX					 INTEGER{ off(0),on(1)  }
		MAX-ACCESS			 read-only
		STATUS					 current
		DESCRIPTION			 " -- "
		::=  { airConditionerEntry  8 }


	airCondVentilationState		 OBJECT-TYPE
		SYNTAX					 INTEGER{ off(0),on(1)  }
		MAX-ACCESS			 read-only
		STATUS					 current
		DESCRIPTION			 " -- "
		::=  { airConditionerEntry  9 }


	airCondCoolingState		 OBJECT-TYPE
		SYNTAX					 INTEGER{ off(0),on(1)  }
		MAX-ACCESS			 read-only
		STATUS					 current
		DESCRIPTION			 " -- "
		::=  { airConditionerEntry  10 }


	airCondHeatingState		 OBJECT-TYPE
		SYNTAX					 INTEGER{ off(0),on(1)  }
		MAX-ACCESS			 read-only
		STATUS					 current
		DESCRIPTION			 " -- "
		::=  { airConditionerEntry  11 }


	airCondCoolingStopTemperature		 OBJECT-TYPE
		SYNTAX					 Integer32( 2000 .. 4000 )
		MAX-ACCESS			 read-write
		STATUS					 current
		DESCRIPTION			 " -- "
		::=  { airConditionerEntry  12 }


	airCondCoolingSensitivity		 OBJECT-TYPE
		SYNTAX					 Integer32( 100 .. 1500 )
		MAX-ACCESS			 read-write
		STATUS					 current
		DESCRIPTION			 " -- "
		::=  { airConditionerEntry  13 }


	airCondWarmingStartTemperature		 OBJECT-TYPE
		SYNTAX					 Integer32( -1000 .. 1500 )
		MAX-ACCESS			 read-write
		STATUS					 current
		DESCRIPTION			 " -- "
		::=  { airConditionerEntry  14 }


	airCondWarmingSensitivity		 OBJECT-TYPE
		SYNTAX					 Integer32( 100 .. 1000 )
		MAX-ACCESS			 read-write
		STATUS					 current
		DESCRIPTION			 " -- "
		::=  { airConditionerEntry  15 }


	airCondOverTemperatureLimit		 OBJECT-TYPE
		SYNTAX					 Integer32( 3000 .. 6000 )
		MAX-ACCESS			 read-write
		STATUS					 current
		DESCRIPTION			 " -- "
		::=  { airConditionerEntry  16 }


	airCondUnderTemperatureLimit		 OBJECT-TYPE
		SYNTAX					 Integer32( -1500 .. 1000 )
		MAX-ACCESS			 read-write
		STATUS					 current
		DESCRIPTION			 " -- "
		::=  { airConditionerEntry  17 }


	airCondVoltage		 OBJECT-TYPE
		SYNTAX					 Integer32( -2147483648 .. 2147483647 )
		MAX-ACCESS			 read-only
		STATUS					 current
		DESCRIPTION			 " -- "
		::=  { airConditionerEntry  18 }


	airCondSupplyAirTemperature		 OBJECT-TYPE
		SYNTAX					 Integer32( -2147483648 .. 2147483647 )
		MAX-ACCESS			 read-only
		STATUS					 current
		DESCRIPTION			 " -- "
		::=  { airConditionerEntry  19 }


	airCondReturnAirTemperature		 OBJECT-TYPE
		SYNTAX					 Integer32( -2147483648 .. 2147483647 )
		MAX-ACCESS			 read-only
		STATUS					 current
		DESCRIPTION			 " -- "
		::=  { airConditionerEntry  20 }


	airCondSupplyAirHumidity		 OBJECT-TYPE
		SYNTAX					 Integer32( -2147483648 .. 2147483647 )
		MAX-ACCESS			 read-only
		STATUS					 current
		DESCRIPTION			 " -- "
		::=  { airConditionerEntry  21 }


	airCondReturnAirHumidity		 OBJECT-TYPE
		SYNTAX					 Integer32( -2147483648 .. 2147483647 )
		MAX-ACCESS			 read-only
		STATUS					 current
		DESCRIPTION			 " -- "
		::=  { airConditionerEntry  22 }


	airCondOverVoltageAlarmState		 OBJECT-TYPE
		SYNTAX					 INTEGER{ notExisted(0),existed(1)  }
		MAX-ACCESS			 read-only
		STATUS					 current
		DESCRIPTION			 " -- "
		::=  { airConditionerEntry  23 }


	airCondUnderVoltageAlarmState		 OBJECT-TYPE
		SYNTAX					 INTEGER{ notExisted(0),existed(1)  }
		MAX-ACCESS			 read-only
		STATUS					 current
		DESCRIPTION			 " -- "
		::=  { airConditionerEntry  24 }


	airCondOverTemperatureAlarmState		 OBJECT-TYPE
		SYNTAX					 INTEGER{ notExisted(0),existed(1)  }
		MAX-ACCESS			 read-only
		STATUS					 current
		DESCRIPTION			 " -- "
		::=  { airConditionerEntry  25 }


	airCondUnderTemperatureAlarmState		 OBJECT-TYPE
		SYNTAX					 INTEGER{ notExisted(0),existed(1)  }
		MAX-ACCESS			 read-only
		STATUS					 current
		DESCRIPTION			 " -- "
		::=  { airConditionerEntry  26 }


	airCondInnerFanAlarmState		 OBJECT-TYPE
		SYNTAX					 INTEGER{ notExisted(0),existed(1)  }
		MAX-ACCESS			 read-only
		STATUS					 current
		DESCRIPTION			 " -- "
		::=  { airConditionerEntry  27 }


	airCondOuterFanAlarmState		 OBJECT-TYPE
		SYNTAX					 INTEGER{ notExisted(0),existed(1)  }
		MAX-ACCESS			 read-only
		STATUS					 current
		DESCRIPTION			 " -- "
		::=  { airConditionerEntry  28 }


	airCondReturnAirTempSensorAlarmState		 OBJECT-TYPE
		SYNTAX					 INTEGER{ notExisted(0),existed(1)  }
		MAX-ACCESS			 read-only
		STATUS					 current
		DESCRIPTION			 " -- "
		::=  { airConditionerEntry  29 }


	airCondReturnAirHumiditySensorAlarmState		 OBJECT-TYPE
		SYNTAX					 INTEGER{ notExisted(0),existed(1)  }
		MAX-ACCESS			 read-only
		STATUS					 current
		DESCRIPTION			 " -- "
		::=  { airConditionerEntry  30 }


	airCondCompressorOverVoltageAlarmState		 OBJECT-TYPE
		SYNTAX					 INTEGER{ notExisted(0),existed(1)  }
		MAX-ACCESS			 read-only
		STATUS					 current
		DESCRIPTION			 " -- "
		::=  { airConditionerEntry  31 }


	airCondCompressorUnderVoltageAlarmState		 OBJECT-TYPE
		SYNTAX					 INTEGER{ notExisted(0),existed(1)  }
		MAX-ACCESS			 read-only
		STATUS					 current
		DESCRIPTION			 " -- "
		::=  { airConditionerEntry  32 }


	airCondFilterLoggedAlarmState		 OBJECT-TYPE
		SYNTAX					 INTEGER{ notExisted(0),existed(1)  }
		MAX-ACCESS			 read-only
		STATUS					 current
		DESCRIPTION			 " -- "
		::=  { airConditionerEntry  33 }


	airCondOperationState		 OBJECT-TYPE
		SYNTAX					 INTEGER{ disabled(0),enabled(1)  }
		MAX-ACCESS			 read-only
		STATUS					 current
		DESCRIPTION			 " -- "
		::=  { airConditionerEntry  34 }


	ioc		 OBJECT IDENTIFIER
		::=  { peripheralEquipment  2 }


	iocTable		 OBJECT-TYPE
		SYNTAX					 SEQUENCE  OF	 IocEntry
		MAX-ACCESS			 not-accessible
		STATUS					 current
		DESCRIPTION			 " -- "
		::=  { ioc  1 }


	iocEntry		 OBJECT-TYPE
		SYNTAX					 IocEntry
		MAX-ACCESS			 not-accessible
		STATUS					 current
		DESCRIPTION			 " -- "
		INDEX						{ iocIndex }
		::=  { iocTable  1 }


	IocEntry		 ::=  SEQUENCE {
		iocIndex					Integer32,
		iocRowStatus					RowStatus,
		iocDescription					DisplayString
		}


	iocIndex		 OBJECT-TYPE
		SYNTAX					 Integer32( 0 .. 0 )
		MAX-ACCESS			 not-accessible
		STATUS					 current
		DESCRIPTION			 " -- "
		::=  { iocEntry  1 }


	iocRowStatus		 OBJECT-TYPE
		SYNTAX					 RowStatus
		MAX-ACCESS			 read-create
		STATUS					 current
		DESCRIPTION			 " -- "
		::=  { iocEntry  2 }


	iocDescription		 OBJECT-TYPE
		SYNTAX					 DisplayString( SIZE ( 1 .. 255 ) )
		MAX-ACCESS			 read-create
		STATUS					 current
		DESCRIPTION			 " -- "
		::=  { iocEntry  3 }


	heatExchangerTable		 OBJECT-TYPE
		SYNTAX					 SEQUENCE  OF	 HeatExchangerEntry
		MAX-ACCESS			 not-accessible
		STATUS					 current
		DESCRIPTION			 " -- "
		::=  { ioc  2 }


	heatExchangerEntry		 OBJECT-TYPE
		SYNTAX					 HeatExchangerEntry
		MAX-ACCESS			 not-accessible
		STATUS					 current
		DESCRIPTION			 " -- "
		INDEX						{ heatExIndex }
		::=  { heatExchangerTable  1 }


	HeatExchangerEntry		 ::=  SEQUENCE {
		heatExIndex					Integer32,
		heatExRowStatus					RowStatus,
		heatExLocation					DisplayString,
		heatExManufacturer					DisplayString,
		heatExModel					DisplayString,
		heatExProtocolVersion					DisplayString,
		heatExRunningState					INTEGER,
		heatExInnerFanState					INTEGER,
		heatExOuterFanState					INTEGER,
		heatExOuterFanRunTemperature					Integer32,
		heatExOuterFanTempOffset					Integer32,
		heatExOverTemperatureLimit					Integer32,
		heatExUnderTemperatureLimit					Integer32,
		heatExVoltageDC					Integer32,
		heatExReturnAirTemperature					Integer32
		}


	heatExIndex		 OBJECT-TYPE
		SYNTAX					 Integer32( 0 .. 0 )
		MAX-ACCESS			 not-accessible
		STATUS					 current
		DESCRIPTION			 " -- "
		::=  { heatExchangerEntry  1 }


	heatExRowStatus		 OBJECT-TYPE
		SYNTAX					 RowStatus
		MAX-ACCESS			 read-only
		STATUS					 current
		DESCRIPTION			 " -- "
		::=  { heatExchangerEntry  2 }


	heatExLocation		 OBJECT-TYPE
		SYNTAX					 DisplayString( SIZE ( 1 .. 255 ) )
		MAX-ACCESS			 read-write
		STATUS					 current
		DESCRIPTION			 " -- "
		::=  { heatExchangerEntry  3 }


	heatExManufacturer		 OBJECT-TYPE
		SYNTAX					 DisplayString( SIZE ( 1 .. 255 ) )
		MAX-ACCESS			 read-only
		STATUS					 current
		DESCRIPTION			 " -- "
		::=  { heatExchangerEntry  4 }


	heatExModel		 OBJECT-TYPE
		SYNTAX					 DisplayString( SIZE ( 1 .. 255 ) )
		MAX-ACCESS			 read-only
		STATUS					 current
		DESCRIPTION			 " -- "
		::=  { heatExchangerEntry  5 }


	heatExProtocolVersion		 OBJECT-TYPE
		SYNTAX					 DisplayString( SIZE ( 1 .. 255 ) )
		MAX-ACCESS			 read-only
		STATUS					 current
		DESCRIPTION			 " -- "
		::=  { heatExchangerEntry  6 }


	heatExRunningState		 OBJECT-TYPE
		SYNTAX					 INTEGER{ off(0),on(1)  }
		MAX-ACCESS			 read-only
		STATUS					 current
		DESCRIPTION			 " -- "
		::=  { heatExchangerEntry  7 }


	heatExInnerFanState		 OBJECT-TYPE
		SYNTAX					 INTEGER{ off(0),on(1)  }
		MAX-ACCESS			 read-only
		STATUS					 current
		DESCRIPTION			 " -- "
		::=  { heatExchangerEntry  8 }


	heatExOuterFanState		 OBJECT-TYPE
		SYNTAX					 INTEGER{ off(0),on(1)  }
		MAX-ACCESS			 read-only
		STATUS					 current
		DESCRIPTION			 " -- "
		::=  { heatExchangerEntry  9 }


	heatExOuterFanRunTemperature		 OBJECT-TYPE
		SYNTAX					 Integer32( 2000 .. 4000 )
		MAX-ACCESS			 read-write
		STATUS					 current
		DESCRIPTION			 " -- "
		::=  { heatExchangerEntry  10 }


	heatExOuterFanTempOffset		 OBJECT-TYPE
		SYNTAX					 Integer32( 500 .. 4500 )
		MAX-ACCESS			 read-write
		STATUS					 current
		DESCRIPTION			 " -- "
		::=  { heatExchangerEntry  11 }


	heatExOverTemperatureLimit		 OBJECT-TYPE
		SYNTAX					 Integer32( 3000 .. 8600 )
		MAX-ACCESS			 read-write
		STATUS					 current
		DESCRIPTION			 " -- "
		::=  { heatExchangerEntry  12 }


	heatExUnderTemperatureLimit		 OBJECT-TYPE
		SYNTAX					 Integer32( -1500 .. 1500 )
		MAX-ACCESS			 read-write
		STATUS					 current
		DESCRIPTION			 " -- "
		::=  { heatExchangerEntry  13 }


	heatExVoltageDC		 OBJECT-TYPE
		SYNTAX					 Integer32( -2147483648 .. 2147483647 )
		MAX-ACCESS			 read-only
		STATUS					 current
		DESCRIPTION			 " -- "
		::=  { heatExchangerEntry  14 }


	heatExReturnAirTemperature		 OBJECT-TYPE
		SYNTAX					 Integer32( -2147483648 .. 2147483647 )
		MAX-ACCESS			 read-only
		STATUS					 current
		DESCRIPTION			 " -- "
		::=  { heatExchangerEntry  15 }


	coolingFan		 OBJECT IDENTIFIER
		::=  { nodeBHW  4 }


	coolingCommon		 OBJECT IDENTIFIER
		::=  { coolingFan  1 }


	coolingPolicy		 OBJECT-TYPE
		SYNTAX					 INTEGER{ stablePWM(0),stagePWM(1),callBackPWM(2),intelligentPWM(3)  }
		MAX-ACCESS			 read-write
		STATUS					 current
		DESCRIPTION			 " -- "
		::=  { coolingCommon  1 }


	coolingFanStablePWM		 OBJECT-TYPE
		SYNTAX					 Integer32( 50 .. 250 )
		MAX-ACCESS			 read-write
		STATUS					 current
		DESCRIPTION			 " -- "
		::=  { coolingCommon  2 }


	coolingNormalMaxTemperature		 OBJECT-TYPE
		SYNTAX					 Integer32( 50 .. 80 )
		MAX-ACCESS			 read-write
		STATUS					 current
		DESCRIPTION			 " -- "
		::=  { coolingCommon  3 }


	coolingNormalMinTemperature		 OBJECT-TYPE
		SYNTAX					 Integer32( -5 .. 25 )
		MAX-ACCESS			 read-write
		STATUS					 current
		DESCRIPTION			 " -- "
		::=  { coolingCommon  4 }


	coolingTargetTemperature		 OBJECT-TYPE
		SYNTAX					 Integer32( 25 .. 50 )
		MAX-ACCESS			 read-write
		STATUS					 current
		DESCRIPTION			 " -- "
		::=  { coolingCommon  5 }


	coolingTemperatureSensitivity		 OBJECT-TYPE
		SYNTAX					 Integer32( 1 .. 4 )
		MAX-ACCESS			 read-write
		STATUS					 current
		DESCRIPTION			 " -- "
		::=  { coolingCommon  6 }


	coolingFanAdjustPWMStep		 OBJECT-TYPE
		SYNTAX					 Integer32( 1 .. 5 )
		MAX-ACCESS			 read-write
		STATUS					 current
		DESCRIPTION			 " -- "
		::=  { coolingCommon  7 }


	coolingAdjustTempThreshold		 OBJECT-TYPE
		SYNTAX					 Integer32( 1 .. 5 )
		MAX-ACCESS			 read-write
		STATUS					 current
		DESCRIPTION			 " -- "
		::=  { coolingCommon  8 }


	coolingFanLoadAdjustUpperLimit		 OBJECT-TYPE
		SYNTAX					 Integer32( 50 .. 100 )
		MAX-ACCESS			 read-write
		STATUS					 current
		DESCRIPTION			 " -- "
		::=  { coolingCommon  9 }


	coolingFanLoadAdjustLowerLimit		 OBJECT-TYPE
		SYNTAX					 Integer32( 0 .. 49 )
		MAX-ACCESS			 read-write
		STATUS					 current
		DESCRIPTION			 " -- "
		::=  { coolingCommon  10 }


	coolingFanHighSpeedThreshold		 OBJECT-TYPE
		SYNTAX					 Integer32( 50 .. 250 )
		MAX-ACCESS			 read-write
		STATUS					 current
		DESCRIPTION			 " -- "
		::=  { coolingCommon  11 }


	coolingFanHighSpeedDetectPeriod		 OBJECT-TYPE
		SYNTAX					 Integer32( 1 .. 96 )
		MAX-ACCESS			 read-write
		STATUS					 current
		DESCRIPTION			 " -- "
		::=  { coolingCommon  12 }


	coolingFanTable		 OBJECT-TYPE
		SYNTAX					 SEQUENCE  OF	 CoolingFanEntry
		MAX-ACCESS			 not-accessible
		STATUS					 current
		DESCRIPTION			 " -- "
		::=  { coolingFan  2 }


	coolingFanEntry		 OBJECT-TYPE
		SYNTAX					 CoolingFanEntry
		MAX-ACCESS			 not-accessible
		STATUS					 current
		DESCRIPTION			 " -- "
		INDEX						{ coolingFanShelfNo,coolingFanIndex }
		::=  { coolingFanTable  1 }


	CoolingFanEntry		 ::=  SEQUENCE {
		coolingFanShelfNo					Integer32,
		coolingFanIndex					Integer32,
		coolingFanRowStatus					RowStatus,
		coolingFanSpeed					Integer32,
		coolingFanPWM					Integer32
		}


	coolingFanShelfNo		 OBJECT-TYPE
		SYNTAX					 Integer32( 0 .. 0 )
		MAX-ACCESS			 not-accessible
		STATUS					 current
		DESCRIPTION			 " -- "
		::=  { coolingFanEntry  1 }


	coolingFanIndex		 OBJECT-TYPE
		SYNTAX					 Integer32( 0 .. 2 )
		MAX-ACCESS			 not-accessible
		STATUS					 current
		DESCRIPTION			 " -- "
		::=  { coolingFanEntry  2 }


	coolingFanRowStatus		 OBJECT-TYPE
		SYNTAX					 RowStatus
		MAX-ACCESS			 read-only
		STATUS					 current
		DESCRIPTION			 " -- "
		::=  { coolingFanEntry  3 }


	coolingFanSpeed		 OBJECT-TYPE
		SYNTAX					 Integer32( 0 .. 65535 )
		MAX-ACCESS			 read-only
		STATUS					 current
		DESCRIPTION			 " -- "
		::=  { coolingFanEntry  4 }


	coolingFanPWM		 OBJECT-TYPE
		SYNTAX					 Integer32( 0 .. 255 )
		MAX-ACCESS			 read-only
		STATUS					 current
		DESCRIPTION			 " -- "
		::=  { coolingFanEntry  5 }


	calibration		 OBJECT IDENTIFIER
		::=  { eNBConfig  5 }


	initCalibrationTable		 OBJECT-TYPE
		SYNTAX					 SEQUENCE  OF	 InitCalibrationEntry
		MAX-ACCESS			 not-accessible
		STATUS					 current
		DESCRIPTION			 " -- "
		::=  { calibration  3 }


	initCalibrationEntry		 OBJECT-TYPE
		SYNTAX					 InitCalibrationEntry
		MAX-ACCESS			 not-accessible
		STATUS					 current
		DESCRIPTION			 " -- "
		INDEX						{ initCalibrationRRUNo }
		::=  { initCalibrationTable  1 }


	InitCalibrationEntry		 ::=  SEQUENCE {
		initCalibrationRRUNo					Integer32,
		initCalibrationRowStatus					RowStatus,
		initCalibrationAnt1TxStatus					INTEGER,
		initCalibrationAnt1RxStatus					INTEGER,
		initCalibrationAnt2TxStatus					INTEGER,
		initCalibrationAnt2RxStatus					INTEGER,
		initCalibrationAnt3TxStatus					INTEGER,
		initCalibrationAnt3RxStatus					INTEGER,
		initCalibrationAnt4TxStatus					INTEGER,
		initCalibrationAnt4RxStatus					INTEGER,
		initCalibrationAnt5TxStatus					INTEGER,
		initCalibrationAnt5RxStatus					INTEGER,
		initCalibrationAnt6TxStatus					INTEGER,
		initCalibrationAnt6RxStatus					INTEGER,
		initCalibrationAnt7TxStatus					INTEGER,
		initCalibrationAnt7RxStatus					INTEGER,
		initCalibrationAnt8TxStatus					INTEGER,
		initCalibrationAnt8RxStatus					INTEGER
		}


	initCalibrationRRUNo		 OBJECT-TYPE
		SYNTAX					 Integer32( 0 .. 191 )
		MAX-ACCESS			 not-accessible
		STATUS					 current
		DESCRIPTION			 " -- "
		::=  { initCalibrationEntry  1 }


	initCalibrationRowStatus		 OBJECT-TYPE
		SYNTAX					 RowStatus
		MAX-ACCESS			 read-only
		STATUS					 current
		DESCRIPTION			 " -- "
		::=  { initCalibrationEntry  2 }


	initCalibrationAnt1TxStatus		 OBJECT-TYPE
		SYNTAX					 INTEGER{ unknown(-1),running(0),failure(1)  }
		MAX-ACCESS			 read-only
		STATUS					 current
		DESCRIPTION			 " -- "
		::=  { initCalibrationEntry  3 }


	initCalibrationAnt1RxStatus		 OBJECT-TYPE
		SYNTAX					 INTEGER{ unknown(-1),running(0),failure(1)  }
		MAX-ACCESS			 read-only
		STATUS					 current
		DESCRIPTION			 " -- "
		::=  { initCalibrationEntry  4 }


	initCalibrationAnt2TxStatus		 OBJECT-TYPE
		SYNTAX					 INTEGER{ unknown(-1),running(0),failure(1)  }
		MAX-ACCESS			 read-only
		STATUS					 current
		DESCRIPTION			 " -- "
		::=  { initCalibrationEntry  5 }


	initCalibrationAnt2RxStatus		 OBJECT-TYPE
		SYNTAX					 INTEGER{ unknown(-1),running(0),failure(1)  }
		MAX-ACCESS			 read-only
		STATUS					 current
		DESCRIPTION			 " -- "
		::=  { initCalibrationEntry  6 }


	initCalibrationAnt3TxStatus		 OBJECT-TYPE
		SYNTAX					 INTEGER{ unknown(-1),running(0),failure(1)  }
		MAX-ACCESS			 read-only
		STATUS					 current
		DESCRIPTION			 " -- "
		::=  { initCalibrationEntry  7 }


	initCalibrationAnt3RxStatus		 OBJECT-TYPE
		SYNTAX					 INTEGER{ unknown(-1),running(0),failure(1)  }
		MAX-ACCESS			 read-only
		STATUS					 current
		DESCRIPTION			 " -- "
		::=  { initCalibrationEntry  8 }


	initCalibrationAnt4TxStatus		 OBJECT-TYPE
		SYNTAX					 INTEGER{ unknown(-1),running(0),failure(1)  }
		MAX-ACCESS			 read-only
		STATUS					 current
		DESCRIPTION			 " -- "
		::=  { initCalibrationEntry  9 }


	initCalibrationAnt4RxStatus		 OBJECT-TYPE
		SYNTAX					 INTEGER{ unknown(-1),running(0),failure(1)  }
		MAX-ACCESS			 read-only
		STATUS					 current
		DESCRIPTION			 " -- "
		::=  { initCalibrationEntry  10 }


	initCalibrationAnt5TxStatus		 OBJECT-TYPE
		SYNTAX					 INTEGER{ unknown(-1),running(0),failure(1)  }
		MAX-ACCESS			 read-only
		STATUS					 current
		DESCRIPTION			 " -- "
		::=  { initCalibrationEntry  11 }


	initCalibrationAnt5RxStatus		 OBJECT-TYPE
		SYNTAX					 INTEGER{ unknown(-1),running(0),failure(1)  }
		MAX-ACCESS			 read-only
		STATUS					 current
		DESCRIPTION			 " -- "
		::=  { initCalibrationEntry  12 }


	initCalibrationAnt6TxStatus		 OBJECT-TYPE
		SYNTAX					 INTEGER{ unknown(-1),running(0),failure(1)  }
		MAX-ACCESS			 read-only
		STATUS					 current
		DESCRIPTION			 " -- "
		::=  { initCalibrationEntry  13 }


	initCalibrationAnt6RxStatus		 OBJECT-TYPE
		SYNTAX					 INTEGER{ unknown(-1),running(0),failure(1)  }
		MAX-ACCESS			 read-only
		STATUS					 current
		DESCRIPTION			 " -- "
		::=  { initCalibrationEntry  14 }


	initCalibrationAnt7TxStatus		 OBJECT-TYPE
		SYNTAX					 INTEGER{ unknown(-1),running(0),failure(1)  }
		MAX-ACCESS			 read-only
		STATUS					 current
		DESCRIPTION			 " -- "
		::=  { initCalibrationEntry  15 }


	initCalibrationAnt7RxStatus		 OBJECT-TYPE
		SYNTAX					 INTEGER{ unknown(-1),running(0),failure(1)  }
		MAX-ACCESS			 read-only
		STATUS					 current
		DESCRIPTION			 " -- "
		::=  { initCalibrationEntry  16 }


	initCalibrationAnt8TxStatus		 OBJECT-TYPE
		SYNTAX					 INTEGER{ unknown(-1),running(0),failure(1)  }
		MAX-ACCESS			 read-only
		STATUS					 current
		DESCRIPTION			 " -- "
		::=  { initCalibrationEntry  17 }


	initCalibrationAnt8RxStatus		 OBJECT-TYPE
		SYNTAX					 INTEGER{ unknown(-1),running(0),failure(1)  }
		MAX-ACCESS			 read-only
		STATUS					 current
		DESCRIPTION			 " -- "
		::=  { initCalibrationEntry  18 }


	remoteRadioUnit		 OBJECT IDENTIFIER
		::=  { eNBConfig  6 }


	topologyRRUTable		 OBJECT-TYPE
		SYNTAX					 SEQUENCE  OF	 TopologyRRUEntry
		MAX-ACCESS			 not-accessible
		STATUS					 current
		DESCRIPTION			 " -- "
		::=  { remoteRadioUnit  1 }


	topologyRRUEntry		 OBJECT-TYPE
		SYNTAX					 TopologyRRUEntry
		MAX-ACCESS			 not-accessible
		STATUS					 current
		DESCRIPTION			 " -- "
		INDEX						{ topoRRUNo }
		::=  { topologyRRUTable  1 }


	TopologyRRUEntry		 ::=  SEQUENCE {
		topoRRUNo					Integer32,
		topoRRURowStatus					RowStatus,
		topoRRUTypeName					DisplayString,
		topoRRULocation					DisplayString,
		topoRRUMacAddr					DisplayString,
		topoRRUAccessRackNo					Integer32,
		topoRRUAccessShelfNo					Integer32,
		topoRRUAccessSlotNo					Integer32,
		topoRRUAccessBoardType					INTEGER,
		topoRRUOfp1AccessOfpPortNo					Integer32,
		topoRRUOfp1AccessLinePosition					Integer32,
		topoRRUOfp2AccessOfpPortNo					Integer32,
		topoRRUOfp2AccessLinePosition					Integer32,
		topoRRUMainOfpNo					Integer32,
		topoRRUAccessUlTimeDelay					Unsigned32,
		topoRRUAccessDlTimeDelay					Unsigned32,
		topoRRUIsNetMatched					INTEGER,
		topoRRUMaxAntPathNum					Integer32,
		topoRRUMaxTxPower					Integer32,
		topoRRUBandWidth					Unsigned32,
		topoRRUBandScope					INTEGER,
		topoRRUMaxTimeDelayCompensation					Unsigned32,
		topoRRUHardwareType					DisplayString,
		topoRRUHardwareVersion					DisplayString,
		topoRRUSoftwareVersion					DisplayString,
		topoRRUFirmwareVersion					DisplayString,
		topoRRUOperationMode					INTEGER,
		topoRRURunningStatus					INTEGER,
		topoRRUAccessPhase					INTEGER,
		topoRRUOperationalState					INTEGER,
		topoRRULocalOscillationFreq					Unsigned32,
		topoRRULocalOscillationState					INTEGER,
		topoRRUClockState					INTEGER,
		topoRRUTemperatureUpperLimit					Integer32,
		topoRRUTemperatureLowerLimit					Integer32,
		topoRRUStateMachine					INTEGER,
		topoRRUResetTrigger					INTEGER,
		topoRRUNextResetTimer					Unsigned32,
		topoRRUProgramDownloadTrigger					INTEGER,
		topoRRUProgramActivateTrigger					INTEGER,
		topoRRUSystemContact					DisplayString,
		topoRRUSystemTime					DateAndTime,
		topoRRUOfpWorkMode					INTEGER,
		topoRRUCheckActiveAlarmTrigger					INTEGER,
		topoRRUCheckActiveAlarmNo					Unsigned32,
		topoRRUCheckActiveAlarmValue					Unsigned32,
		topoRRULogDestination					DisplayString,
		topoRRULogFileType					INTEGER,
		topoRRURemoteResetNextRruTrigger					INTEGER,
		topoRRURemoteResetNextRruTimer					Unsigned32,
		topoRRUFaultStatus					INTEGER,
		topoRRUUnavaiableReason					BITS,
		topoRRUUUpTime					DateAndTime,
		topoRRUAccessSlaveUlTimeDelay					Unsigned32,
		topoRRUAccessSlaveDlTimeDelay					Unsigned32,
		topoRRUAccessMasterFiberLength					Unsigned32,
		topoRRUAccessSlaveFiberLength					Unsigned32,
		topoRRUFiberFaultReason					BITS,
		topoRRUSupportTdCarrierNum					Integer32,
		topoRRUDLMaxTimeDelayCompensation					Unsigned32,
		topoRRUULMaxTimeDelayCompensation					Unsigned32,
		topoRRUSupportCellWorkMode					BITS,
		topoRRUSupportSingleAntCal					INTEGER,
		topoRRUMainSendAntCalPortNo					Integer32,
		topoRRUSlaveSendAntCalPortNo					Integer32,
		topoRRUMainRecvAntCalPortNo					Integer32,
		topoRRUSlaveRecvAntCalPortNo					Integer32,
		topoRRULocalOscillationFreq2					Unsigned32,
		topoRRULocalOscillationState2					INTEGER,
		topoRRULocalOscillationFreq3					Unsigned32,
		topoRRULocalOscillationState3					INTEGER,
		topoRRUCPUCheckInterval					Integer32,
		topoRRUCPUOccupation					Integer32,
		topoRRUVSWRThreshold					Unsigned32,
		topoRRUTemperature					Integer32,
		topoRRUTxConstSwitch					INTEGER,
		topoRRUTxConstFlag					INTEGER,
		topoRRUACPowerOffsetRx					Integer32,
		topoRRUACPowerOffsetTx					Integer32,
		topoRRUBspMainStatus					INTEGER,
		topoRRUBspBackupStatus					INTEGER,
		topoRRUMainBrdCurrentValue					Integer32,
		topoRRUTRxConstSwitch					INTEGER,
		topoRRUTRxConstType					INTEGER,
		topoRRUSetTRxMode					INTEGER,
		topoRRUTRxConstPower					Integer32,
		topoRRUTempCompensationPeriod					Unsigned32,
		topoRRUSlaveBootUpgradeSwitch					INTEGER,
		topoRRURunningCellWorkMode					BITS,
		topoRRUJamCounter					Unsigned32,
		topoRRUBootMainStatus					INTEGER,
		topoRRUBootSlaveStatus					INTEGER,
		topoRRUBearedCarrierNum					Integer32,
		topoRRUVSWR2ndThreshold					Unsigned32,
		topoRRUIrE1AccessIrENo					Integer32,
		topoRRUTopoType					INTEGER,
		topoRRUAccessRHUBNo					Integer32,
		topoRRUIrE2AccessIrENo					Integer32,
		topoRRUHubMainEthNo					Integer32,
		topoRRUChannelGain					Unsigned32,
		topoRRUSignalTxRxSwitch					INTEGER,
		topoRRUAntCombinGrpNo					Integer32,
		topoRRUAntGrpAcessSequenceNo					Integer32,
		topoRRUJamResistantRange					Unsigned32
		}


	topoRRUNo		 OBJECT-TYPE
		SYNTAX					 Integer32( 0 .. 191 )
		MAX-ACCESS			 not-accessible
		STATUS					 current
		DESCRIPTION			 " -- "
		::=  { topologyRRUEntry  1 }


	topoRRURowStatus		 OBJECT-TYPE
		SYNTAX					 RowStatus
		MAX-ACCESS			 read-only
		STATUS					 current
		DESCRIPTION			 " -- "
		::=  { topologyRRUEntry  2 }


	topoRRUTypeName		 OBJECT-TYPE
		SYNTAX					 DisplayString( SIZE ( 1 .. 255 ) )
		MAX-ACCESS			 read-only
		STATUS					 current
		DESCRIPTION			 " -- "
		::=  { topologyRRUEntry  3 }


	topoRRULocation		 OBJECT-TYPE
		SYNTAX					 DisplayString( SIZE ( 1 .. 255 ) )
		MAX-ACCESS			 read-only
		STATUS					 current
		DESCRIPTION			 " -- "
		::=  { topologyRRUEntry  4 }


	topoRRUMacAddr		 OBJECT-TYPE
		SYNTAX					 DisplayString( SIZE ( 12 .. 12 ) )
		MAX-ACCESS			 read-only
		STATUS					 current
		DESCRIPTION			 " -- "
		::=  { topologyRRUEntry  5 }


	topoRRUAccessRackNo		 OBJECT-TYPE
		SYNTAX					 Integer32( 0 .. 0|-1 )
		MAX-ACCESS			 read-only
		STATUS					 current
		DESCRIPTION			 " -- "
		::=  { topologyRRUEntry  6 }


	topoRRUAccessShelfNo		 OBJECT-TYPE
		SYNTAX					 Integer32( 0 .. 0|-1 )
		MAX-ACCESS			 read-only
		STATUS					 current
		DESCRIPTION			 " -- "
		::=  { topologyRRUEntry  7 }


	topoRRUAccessSlotNo		 OBJECT-TYPE
		SYNTAX					 Integer32( 1 .. 7|-1 )
		MAX-ACCESS			 read-only
		STATUS					 current
		DESCRIPTION			 " -- "
		::=  { topologyRRUEntry  8 }


	topoRRUAccessBoardType		 OBJECT-TYPE
		SYNTAX					 INTEGER{ unknown(0),ccu(54),ceu(56),bbu(58),iiu(66),bcu(67),biu(68),accu(70),abbut(71),abbuf(72),eiuDof(75),scta(97),bpia(98),bpoa(99),bpoe(109),tdru311B(113),tdru312(114),bpof(128),sctd(141),mmba(142),bpog(143),bpoh(177),scte(178),mmbc(224),sctf(240),bpoi(241)  }
		MAX-ACCESS			 read-only
		STATUS					 current
		DESCRIPTION			 " -- "
		::=  { topologyRRUEntry  9 }


	topoRRUOfp1AccessOfpPortNo		 OBJECT-TYPE
		SYNTAX					 Integer32( 0 .. 5|-1 )
		MAX-ACCESS			 read-only
		STATUS					 current
		DESCRIPTION			 " -- "
		::=  { topologyRRUEntry  10 }


	topoRRUOfp1AccessLinePosition		 OBJECT-TYPE
		SYNTAX					 Integer32( 1 .. 6|-1 )
		MAX-ACCESS			 read-only
		STATUS					 current
		DESCRIPTION			 " -- "
		::=  { topologyRRUEntry  11 }


	topoRRUOfp2AccessOfpPortNo		 OBJECT-TYPE
		SYNTAX					 Integer32( 0 .. 5|-1 )
		MAX-ACCESS			 read-only
		STATUS					 current
		DESCRIPTION			 " -- "
		::=  { topologyRRUEntry  12 }


	topoRRUOfp2AccessLinePosition		 OBJECT-TYPE
		SYNTAX					 Integer32( 1 .. 6|-1 )
		MAX-ACCESS			 read-only
		STATUS					 current
		DESCRIPTION			 " -- "
		::=  { topologyRRUEntry  13 }


	topoRRUMainOfpNo		 OBJECT-TYPE
		SYNTAX					 Integer32( 0 .. 5|-1 )
		MAX-ACCESS			 read-only
		STATUS					 current
		DESCRIPTION			 " -- "
		::=  { topologyRRUEntry  14 }


	topoRRUAccessUlTimeDelay		 OBJECT-TYPE
		SYNTAX					 Unsigned32( 0 .. 4294967295 )
		MAX-ACCESS			 read-only
		STATUS					 current
		DESCRIPTION			 " -- "
		::=  { topologyRRUEntry  15 }


	topoRRUAccessDlTimeDelay		 OBJECT-TYPE
		SYNTAX					 Unsigned32( 0 .. 4294967295 )
		MAX-ACCESS			 read-only
		STATUS					 current
		DESCRIPTION			 " -- "
		::=  { topologyRRUEntry  16 }


	topoRRUIsNetMatched		 OBJECT-TYPE
		SYNTAX					 INTEGER{ matched(0),unmatched(1)  }
		MAX-ACCESS			 read-only
		STATUS					 current
		DESCRIPTION			 " -- "
		::=  { topologyRRUEntry  17 }


	topoRRUMaxAntPathNum		 OBJECT-TYPE
		SYNTAX					 Integer32( 0|1 .. 8 )
		MAX-ACCESS			 read-only
		STATUS					 current
		DESCRIPTION			 " -- "
		::=  { topologyRRUEntry  18 }


	topoRRUMaxTxPower		 OBJECT-TYPE
		SYNTAX					 Integer32( -32768 .. 32767 )
		MAX-ACCESS			 read-only
		STATUS					 current
		DESCRIPTION			 " -- "
		::=  { topologyRRUEntry  19 }


	topoRRUBandWidth		 OBJECT-TYPE
		SYNTAX					 Unsigned32( 0 .. 255 )
		MAX-ACCESS			 read-only
		STATUS					 current
		DESCRIPTION			 " -- "
		::=  { topologyRRUEntry  20 }


	topoRRUBandScope		 OBJECT-TYPE
		SYNTAX					 INTEGER{ unknown(-1),v1880to1920(0),v2010to2025(1),v2300to2400(2),v2575to2615(3),v2545to2575(4),v1447to1467(6),v2620to2690(7),v1785to1805(8),v703to803(10),otherBand(254)  }
		MAX-ACCESS			 read-only
		STATUS					 current
		DESCRIPTION			 " -- "
		::=  { topologyRRUEntry  21 }


	topoRRUMaxTimeDelayCompensation		 OBJECT-TYPE
		SYNTAX					 Unsigned32( 0 .. 4294967295 )
		MAX-ACCESS			 read-only
		STATUS					 current
		DESCRIPTION			 " -- "
		::=  { topologyRRUEntry  22 }


	topoRRUHardwareType		 OBJECT-TYPE
		SYNTAX					 DisplayString( SIZE ( 32 .. 32 ) )
		MAX-ACCESS			 read-only
		STATUS					 current
		DESCRIPTION			 " -- "
		::=  { topologyRRUEntry  23 }


	topoRRUHardwareVersion		 OBJECT-TYPE
		SYNTAX					 DisplayString( SIZE ( 16 .. 16 ) )
		MAX-ACCESS			 read-only
		STATUS					 current
		DESCRIPTION			 " -- "
		::=  { topologyRRUEntry  24 }


	topoRRUSoftwareVersion		 OBJECT-TYPE
		SYNTAX					 DisplayString( SIZE ( 40 .. 40 ) )
		MAX-ACCESS			 read-only
		STATUS					 current
		DESCRIPTION			 " -- "
		::=  { topologyRRUEntry  25 }


	topoRRUFirmwareVersion		 OBJECT-TYPE
		SYNTAX					 DisplayString( SIZE ( 40 .. 40 ) )
		MAX-ACCESS			 read-only
		STATUS					 current
		DESCRIPTION			 " -- "
		::=  { topologyRRUEntry  26 }


	topoRRUOperationMode		 OBJECT-TYPE
		SYNTAX					 INTEGER{ normal(0),test(1),doubleNormal(2),doubleTest(3)  }
		MAX-ACCESS			 read-write
		STATUS					 current
		DESCRIPTION			 " -- "
		::=  { topologyRRUEntry  27 }


	topoRRURunningStatus		 OBJECT-TYPE
		SYNTAX					 INTEGER{ free(0),test(1),running(2)  }
		MAX-ACCESS			 read-only
		STATUS					 current
		DESCRIPTION			 " -- "
		::=  { topologyRRUEntry  28 }


	topoRRUAccessPhase		 OBJECT-TYPE
		SYNTAX					 INTEGER{ unknown(0),broadcastAccess(1),pathSetup(2),versionUpdate(3),timeDelayMeasure(4),antConfig(5),available(6)  }
		MAX-ACCESS			 read-only
		STATUS					 current
		DESCRIPTION			 " -- "
		::=  { topologyRRUEntry  29 }


	topoRRUOperationalState		 OBJECT-TYPE
		SYNTAX					 INTEGER{ enabled(0),disabled(1),invalid(2)  }
		MAX-ACCESS			 read-only
		STATUS					 current
		DESCRIPTION			 " -- "
		::=  { topologyRRUEntry  30 }


	topoRRULocalOscillationFreq		 OBJECT-TYPE
		SYNTAX					 Unsigned32( 0 .. 4294967295 )
		MAX-ACCESS			 read-only
		STATUS					 current
		DESCRIPTION			 " -- "
		::=  { topologyRRUEntry  31 }


	topoRRULocalOscillationState		 OBJECT-TYPE
		SYNTAX					 INTEGER{ unknown(-1),locked(0),unLocked(1)  }
		MAX-ACCESS			 read-only
		STATUS					 current
		DESCRIPTION			 " -- "
		::=  { topologyRRUEntry  32 }


	topoRRUClockState		 OBJECT-TYPE
		SYNTAX					 INTEGER{ unknown(-1),syn(0),asyn(1)  }
		MAX-ACCESS			 read-only
		STATUS					 current
		DESCRIPTION			 " -- "
		::=  { topologyRRUEntry  33 }


	topoRRUTemperatureUpperLimit		 OBJECT-TYPE
		SYNTAX					 Integer32( -2147483648 .. 2147483647 )
		MAX-ACCESS			 read-write
		STATUS					 current
		DESCRIPTION			 " -- "
		::=  { topologyRRUEntry  34 }


	topoRRUTemperatureLowerLimit		 OBJECT-TYPE
		SYNTAX					 Integer32( -2147483648 .. 2147483647 )
		MAX-ACCESS			 read-write
		STATUS					 current
		DESCRIPTION			 " -- "
		::=  { topologyRRUEntry  35 }


	topoRRUStateMachine		 OBJECT-TYPE
		SYNTAX					 INTEGER{ radioFrameSyn(0),superGroupSyn(1),synErr(2),statD(3),statE(4),statF(5),statG(6)  }
		MAX-ACCESS			 read-only
		STATUS					 current
		DESCRIPTION			 " -- "
		::=  { topologyRRUEntry  36 }


	topoRRUResetTrigger		 OBJECT-TYPE
		SYNTAX					 INTEGER{ notEffectNextRru(0),effectNextRru(1),bbuCmdCode(2),remoteResetRru(11)  }
		MAX-ACCESS			 read-write
		STATUS					 current
		DESCRIPTION			 " -- "
		::=  { topologyRRUEntry  37 }


	topoRRUNextResetTimer		 OBJECT-TYPE
		SYNTAX					 Unsigned32( 0 .. 65535 )
		MAX-ACCESS			 read-write
		STATUS					 current
		DESCRIPTION			 " -- "
		::=  { topologyRRUEntry  38 }


	topoRRUProgramDownloadTrigger		 OBJECT-TYPE
		SYNTAX					 INTEGER{ software(0),firmware(1)  }
		MAX-ACCESS			 read-write
		STATUS					 current
		DESCRIPTION			 " -- "
		::=  { topologyRRUEntry  39 }


	topoRRUProgramActivateTrigger		 OBJECT-TYPE
		SYNTAX					 INTEGER{ software(0),firmware(1),softwareAndFirmware(2)  }
		MAX-ACCESS			 read-write
		STATUS					 current
		DESCRIPTION			 " -- "
		::=  { topologyRRUEntry  40 }


	topoRRUSystemContact		 OBJECT-TYPE
		SYNTAX					 DisplayString( SIZE ( 1 .. 255 ) )
		MAX-ACCESS			 read-only
		STATUS					 current
		DESCRIPTION			 " -- "
		::=  { topologyRRUEntry  41 }


	topoRRUSystemTime		 OBJECT-TYPE
		SYNTAX					 DateAndTime
		MAX-ACCESS			 read-only
		STATUS					 current
		DESCRIPTION			 " -- "
		::=  { topologyRRUEntry  42 }


	topoRRUOfpWorkMode		 OBJECT-TYPE
		SYNTAX					 INTEGER{ unknown(-1),normal(1),lined(2),backup(3),shared(4)  }
		MAX-ACCESS			 read-only
		STATUS					 current
		DESCRIPTION			 " -- "
		::=  { topologyRRUEntry  43 }


	topoRRUCheckActiveAlarmTrigger		 OBJECT-TYPE
		SYNTAX					 INTEGER{ off(0),on(1)  }
		MAX-ACCESS			 read-write
		STATUS					 current
		DESCRIPTION			 " -- "
		::=  { topologyRRUEntry  44 }


	topoRRUCheckActiveAlarmNo		 OBJECT-TYPE
		SYNTAX					 Unsigned32( 0 .. 4294967295 )
		MAX-ACCESS			 read-write
		STATUS					 current
		DESCRIPTION			 " -- "
		::=  { topologyRRUEntry  45 }


	topoRRUCheckActiveAlarmValue		 OBJECT-TYPE
		SYNTAX					 Unsigned32( 0 .. 4294967295 )
		MAX-ACCESS			 read-write
		STATUS					 current
		DESCRIPTION			 " -- "
		::=  { topologyRRUEntry  46 }


	topoRRULogDestination		 OBJECT-TYPE
		SYNTAX					 DisplayString( SIZE ( 1 .. 150 ) )
		MAX-ACCESS			 read-write
		STATUS					 current
		DESCRIPTION			 " -- "
		::=  { topologyRRUEntry  47 }


	topoRRULogFileType		 OBJECT-TYPE
		SYNTAX					 INTEGER{ alarm(0),user(1),system(2),all(3),operate(4)  }
		MAX-ACCESS			 read-write
		STATUS					 current
		DESCRIPTION			 " -- "
		::=  { topologyRRUEntry  48 }


	topoRRURemoteResetNextRruTrigger		 OBJECT-TYPE
		SYNTAX					 INTEGER{ on(0)  }
		MAX-ACCESS			 read-write
		STATUS					 current
		DESCRIPTION			 " -- "
		::=  { topologyRRUEntry  49 }


	topoRRURemoteResetNextRruTimer		 OBJECT-TYPE
		SYNTAX					 Unsigned32( 500 .. 65535 )
		MAX-ACCESS			 read-write
		STATUS					 current
		DESCRIPTION			 " -- "
		::=  { topologyRRUEntry  50 }


	topoRRUFaultStatus		 OBJECT-TYPE
		SYNTAX					 INTEGER{ normal(0),fault(1)  }
		MAX-ACCESS			 read-only
		STATUS					 current
		DESCRIPTION			 " -- "
		::=  { topologyRRUEntry  51 }


	topoRRUUnavaiableReason		 OBJECT-TYPE
		SYNTAX					 BITS{ rruMasterOfpAbnormalBBU(0),rruSlaveOfpAbnormalBBU(1),rruLocalCrystaloidUnlock(2),rruSlaveOfpAbnormalRRU(3),rruOfpModuleMixedUse(4)  }
		MAX-ACCESS			 read-only
		STATUS					 current
		DESCRIPTION			 " -- "
		::=  { topologyRRUEntry  52 }


	topoRRUUUpTime		 OBJECT-TYPE
		SYNTAX					 DateAndTime
		MAX-ACCESS			 read-only
		STATUS					 current
		DESCRIPTION			 " -- "
		::=  { topologyRRUEntry  53 }


	topoRRUAccessSlaveUlTimeDelay		 OBJECT-TYPE
		SYNTAX					 Unsigned32( 0 .. 4294967295 )
		MAX-ACCESS			 read-only
		STATUS					 current
		DESCRIPTION			 " -- "
		::=  { topologyRRUEntry  54 }


	topoRRUAccessSlaveDlTimeDelay		 OBJECT-TYPE
		SYNTAX					 Unsigned32( 0 .. 4294967295 )
		MAX-ACCESS			 read-only
		STATUS					 current
		DESCRIPTION			 " -- "
		::=  { topologyRRUEntry  55 }


	topoRRUAccessMasterFiberLength		 OBJECT-TYPE
		SYNTAX					 Unsigned32( 0 .. 4294967295 )
		MAX-ACCESS			 read-only
		STATUS					 current
		DESCRIPTION			 " -- "
		::=  { topologyRRUEntry  56 }


	topoRRUAccessSlaveFiberLength		 OBJECT-TYPE
		SYNTAX					 Unsigned32( 0 .. 4294967295 )
		MAX-ACCESS			 read-only
		STATUS					 current
		DESCRIPTION			 " -- "
		::=  { topologyRRUEntry  57 }


	topoRRUFiberFaultReason		 OBJECT-TYPE
		SYNTAX					 BITS{ rruMasterOfpAbnormalBBU(0),rruSlaveOfpAbnormalBBU(1),rruSlaveOfpAbnormalRRU(2)  }
		MAX-ACCESS			 read-only
		STATUS					 current
		DESCRIPTION			 " -- "
		::=  { topologyRRUEntry  58 }


	topoRRUSupportTdCarrierNum		 OBJECT-TYPE
		SYNTAX					 Integer32( 0 .. 255 )
		MAX-ACCESS			 read-only
		STATUS					 current
		DESCRIPTION			 " -- "
		::=  { topologyRRUEntry  59 }


	topoRRUDLMaxTimeDelayCompensation		 OBJECT-TYPE
		SYNTAX					 Unsigned32( 0 .. 4294967295 )
		MAX-ACCESS			 read-only
		STATUS					 current
		DESCRIPTION			 " -- "
		::=  { topologyRRUEntry  60 }


	topoRRUULMaxTimeDelayCompensation		 OBJECT-TYPE
		SYNTAX					 Unsigned32( 0 .. 4294967295 )
		MAX-ACCESS			 read-only
		STATUS					 current
		DESCRIPTION			 " -- "
		::=  { topologyRRUEntry  61 }


	topoRRUSupportCellWorkMode		 OBJECT-TYPE
		SYNTAX					 BITS{ tddlte(0),tdscdma(1),fddlte(2)  }
		MAX-ACCESS			 read-only
		STATUS					 current
		DESCRIPTION			 " -- "
		::=  { topologyRRUEntry  62 }


	topoRRUSupportSingleAntCal		 OBJECT-TYPE
		SYNTAX					 INTEGER{ unsupportSingleCal(0),supportSingleCal(1)  }
		MAX-ACCESS			 read-only
		STATUS					 current
		DESCRIPTION			 " -- "
		::=  { topologyRRUEntry  63 }


	topoRRUMainSendAntCalPortNo		 OBJECT-TYPE
		SYNTAX					 Integer32( 0 .. 255 )
		MAX-ACCESS			 read-only
		STATUS					 current
		DESCRIPTION			 " -- "
		::=  { topologyRRUEntry  64 }


	topoRRUSlaveSendAntCalPortNo		 OBJECT-TYPE
		SYNTAX					 Integer32( 0 .. 255 )
		MAX-ACCESS			 read-only
		STATUS					 current
		DESCRIPTION			 " -- "
		::=  { topologyRRUEntry  65 }


	topoRRUMainRecvAntCalPortNo		 OBJECT-TYPE
		SYNTAX					 Integer32( 0 .. 255 )
		MAX-ACCESS			 read-only
		STATUS					 current
		DESCRIPTION			 " -- "
		::=  { topologyRRUEntry  66 }


	topoRRUSlaveRecvAntCalPortNo		 OBJECT-TYPE
		SYNTAX					 Integer32( 0 .. 255 )
		MAX-ACCESS			 read-only
		STATUS					 current
		DESCRIPTION			 " -- "
		::=  { topologyRRUEntry  67 }


	topoRRULocalOscillationFreq2		 OBJECT-TYPE
		SYNTAX					 Unsigned32( 0 .. 4294967295 )
		MAX-ACCESS			 read-only
		STATUS					 current
		DESCRIPTION			 " -- "
		::=  { topologyRRUEntry  68 }


	topoRRULocalOscillationState2		 OBJECT-TYPE
		SYNTAX					 INTEGER{ unknown(-1),locked(0),unLocked(1)  }
		MAX-ACCESS			 read-only
		STATUS					 current
		DESCRIPTION			 " -- "
		::=  { topologyRRUEntry  69 }


	topoRRULocalOscillationFreq3		 OBJECT-TYPE
		SYNTAX					 Unsigned32( 0 .. 4294967295 )
		MAX-ACCESS			 read-only
		STATUS					 current
		DESCRIPTION			 " -- "
		::=  { topologyRRUEntry  70 }


	topoRRULocalOscillationState3		 OBJECT-TYPE
		SYNTAX					 INTEGER{ unknown(-1),locked(0),unLocked(1)  }
		MAX-ACCESS			 read-only
		STATUS					 current
		DESCRIPTION			 " -- "
		::=  { topologyRRUEntry  71 }


	topoRRUCPUCheckInterval		 OBJECT-TYPE
		SYNTAX					 Integer32( 1 .. 60 )
		MAX-ACCESS			 read-write
		STATUS					 current
		DESCRIPTION			 " -- "
		::=  { topologyRRUEntry  72 }


	topoRRUCPUOccupation		 OBJECT-TYPE
		SYNTAX					 Integer32( 0 .. 100 )
		MAX-ACCESS			 read-only
		STATUS					 current
		DESCRIPTION			 " -- "
		::=  { topologyRRUEntry  73 }


	topoRRUVSWRThreshold		 OBJECT-TYPE
		SYNTAX					 Unsigned32( 15 .. 30 )
		MAX-ACCESS			 read-write
		STATUS					 current
		DESCRIPTION			 " -- "
		::=  { topologyRRUEntry  74 }


	topoRRUTemperature		 OBJECT-TYPE
		SYNTAX					 Integer32( -2147483648 .. 2147483647 )
		MAX-ACCESS			 read-only
		STATUS					 current
		DESCRIPTION			 " -- "
		::=  { topologyRRUEntry  75 }


	topoRRUTxConstSwitch		 OBJECT-TYPE
		SYNTAX					 INTEGER{ off(0),on(1)  }
		MAX-ACCESS			 read-write
		STATUS					 current
		DESCRIPTION			 " -- "
		::=  { topologyRRUEntry  76 }


	topoRRUTxConstFlag		 OBJECT-TYPE
		SYNTAX					 INTEGER{ fpga(0),intermediateFreq(1)  }
		MAX-ACCESS			 read-write
		STATUS					 current
		DESCRIPTION			 " -- "
		::=  { topologyRRUEntry  77 }


	topoRRUACPowerOffsetRx		 OBJECT-TYPE
		SYNTAX					 Integer32( 0 .. 5 )
		MAX-ACCESS			 read-write
		STATUS					 current
		DESCRIPTION			 " -- "
		::=  { topologyRRUEntry  78 }


	topoRRUACPowerOffsetTx		 OBJECT-TYPE
		SYNTAX					 Integer32( 0 .. 5 )
		MAX-ACCESS			 read-write
		STATUS					 current
		DESCRIPTION			 " -- "
		::=  { topologyRRUEntry  79 }


	topoRRUBspMainStatus		 OBJECT-TYPE
		SYNTAX					 INTEGER{ unknown(-1),unAvailable(0),available(1),unLoad(2)  }
		MAX-ACCESS			 read-only
		STATUS					 current
		DESCRIPTION			 " -- "
		::=  { topologyRRUEntry  80 }


	topoRRUBspBackupStatus		 OBJECT-TYPE
		SYNTAX					 INTEGER{ unknown(-1),unAvailable(0),available(1),unLoad(2)  }
		MAX-ACCESS			 read-only
		STATUS					 current
		DESCRIPTION			 " -- "
		::=  { topologyRRUEntry  81 }


	topoRRUMainBrdCurrentValue		 OBJECT-TYPE
		SYNTAX					 Integer32( -2147483648 .. 2147483647 )
		MAX-ACCESS			 read-only
		STATUS					 current
		DESCRIPTION			 " -- "
		::=  { topologyRRUEntry  82 }


	topoRRUTRxConstSwitch		 OBJECT-TYPE
		SYNTAX					 INTEGER{ off(0),on(1)  }
		MAX-ACCESS			 read-write
		STATUS					 current
		DESCRIPTION			 " -- "
		::=  { topologyRRUEntry  83 }


	topoRRUTRxConstType		 OBJECT-TYPE
		SYNTAX					 INTEGER{ invalid(-1),irSource(0),dacSource(1),tdsPathSource(2),tdlPathSourch(3)  }
		MAX-ACCESS			 read-write
		STATUS					 current
		DESCRIPTION			 " -- "
		::=  { topologyRRUEntry  84 }


	topoRRUSetTRxMode		 OBJECT-TYPE
		SYNTAX					 INTEGER{ invalid(-1),uplink(0),downlink(1)  }
		MAX-ACCESS			 read-write
		STATUS					 current
		DESCRIPTION			 " -- "
		::=  { topologyRRUEntry  86 }


	topoRRUTRxConstPower		 OBJECT-TYPE
		SYNTAX					 Integer32( -2147483648 .. 2147483647 )
		MAX-ACCESS			 read-write
		STATUS					 current
		DESCRIPTION			 " -- "
		::=  { topologyRRUEntry  87 }


	topoRRUTempCompensationPeriod		 OBJECT-TYPE
		SYNTAX					 Unsigned32( 60 .. 36000 )
		MAX-ACCESS			 read-write
		STATUS					 current
		DESCRIPTION			 " -- "
		::=  { topologyRRUEntry  91 }


	topoRRUSlaveBootUpgradeSwitch		 OBJECT-TYPE
		SYNTAX					 INTEGER{ standBy(0),upgrading(1)  }
		MAX-ACCESS			 read-write
		STATUS					 current
		DESCRIPTION			 " -- "
		::=  { topologyRRUEntry  92 }


	topoRRURunningCellWorkMode		 OBJECT-TYPE
		SYNTAX					 BITS{ tddlte(0),tdscdma(1),fddlte(2)  }
		MAX-ACCESS			 read-only
		STATUS					 current
		DESCRIPTION			 " -- "
		::=  { topologyRRUEntry  93 }


	topoRRUJamCounter		 OBJECT-TYPE
		SYNTAX					 Unsigned32( 0 .. 4294967295 )
		MAX-ACCESS			 read-only
		STATUS					 current
		DESCRIPTION			 " -- "
		::=  { topologyRRUEntry  94 }


	topoRRUBootMainStatus		 OBJECT-TYPE
		SYNTAX					 INTEGER{ unknown(-1),unAvailable(0),available(1),unLoad(2)  }
		MAX-ACCESS			 read-only
		STATUS					 current
		DESCRIPTION			 " -- "
		::=  { topologyRRUEntry  95 }


	topoRRUBootSlaveStatus		 OBJECT-TYPE
		SYNTAX					 INTEGER{ unknown(-1),unAvailable(0),available(1),unLoad(2)  }
		MAX-ACCESS			 read-only
		STATUS					 current
		DESCRIPTION			 " -- "
		::=  { topologyRRUEntry  96 }


	topoRRUBearedCarrierNum		 OBJECT-TYPE
		SYNTAX					 Integer32( -2147483648 .. 2147483647 )
		MAX-ACCESS			 read-only
		STATUS					 current
		DESCRIPTION			 " -- "
		::=  { topologyRRUEntry  97 }


	topoRRUVSWR2ndThreshold		 OBJECT-TYPE
		SYNTAX					 Unsigned32( 15 .. 30 )
		MAX-ACCESS			 read-write
		STATUS					 current
		DESCRIPTION			 " -- "
		::=  { topologyRRUEntry  98 }


	topoRRUIrE1AccessIrENo		 OBJECT-TYPE
		SYNTAX					 Integer32( 1 .. 8|-1 )
		MAX-ACCESS			 read-only
		STATUS					 current
		DESCRIPTION			 " -- "
		::=  { topologyRRUEntry  116 }


	topoRRUTopoType		 OBJECT-TYPE
		SYNTAX					 INTEGER{ normal(0),pico(1)  }
		MAX-ACCESS			 read-only
		STATUS					 current
		DESCRIPTION			 " -- "
		::=  { topologyRRUEntry  117 }


	topoRRUAccessRHUBNo		 OBJECT-TYPE
		SYNTAX					 Integer32( 200 .. 254 )
		MAX-ACCESS			 read-only
		STATUS					 current
		DESCRIPTION			 " -- "
		::=  { topologyRRUEntry  118 }


	topoRRUIrE2AccessIrENo		 OBJECT-TYPE
		SYNTAX					 Integer32( 1 .. 8|-1 )
		MAX-ACCESS			 read-only
		STATUS					 current
		DESCRIPTION			 " -- "
		::=  { topologyRRUEntry  119 }


	topoRRUHubMainEthNo		 OBJECT-TYPE
		SYNTAX					 Integer32( 1 .. 8|-1 )
		MAX-ACCESS			 read-only
		STATUS					 current
		DESCRIPTION			 " -- "
		::=  { topologyRRUEntry  120 }


	topoRRUChannelGain		 OBJECT-TYPE
		SYNTAX					 Unsigned32( 0 .. 450 )
		MAX-ACCESS			 read-only
		STATUS					 current
		DESCRIPTION			 " -- "
		::=  { topologyRRUEntry  123 }


	topoRRUSignalTxRxSwitch		 OBJECT-TYPE
		SYNTAX					 INTEGER{ off(0),on(1)  }
		MAX-ACCESS			 read-write
		STATUS					 current
		DESCRIPTION			 " -- "
		::=  { topologyRRUEntry  124 }


	topoRRUAntCombinGrpNo		 OBJECT-TYPE
		SYNTAX					 Integer32( 0 .. 65535 )
		MAX-ACCESS			 read-only
		STATUS					 current
		DESCRIPTION			 " -- "
		::=  { topologyRRUEntry  125 }


	topoRRUAntGrpAcessSequenceNo		 OBJECT-TYPE
		SYNTAX					 Integer32( 0 .. 3 )
		MAX-ACCESS			 read-only
		STATUS					 current
		DESCRIPTION			 " -- "
		::=  { topologyRRUEntry  126 }


	topoRRUJamResistantRange		 OBJECT-TYPE
		SYNTAX					 Unsigned32( 0 .. 4294967295 )
		MAX-ACCESS			 read-only
		STATUS					 current
		DESCRIPTION			 " -- "
		::=  { topologyRRUEntry  127 }


	topologyAntennaArrayTable		 OBJECT-TYPE
		SYNTAX					 SEQUENCE  OF	 TopologyAntennaArrayEntry
		MAX-ACCESS			 not-accessible
		STATUS					 current
		DESCRIPTION			 " -- "
		::=  { remoteRadioUnit  2 }


	topologyAntennaArrayEntry		 OBJECT-TYPE
		SYNTAX					 TopologyAntennaArrayEntry
		MAX-ACCESS			 not-accessible
		STATUS					 current
		DESCRIPTION			 " -- "
		INDEX						{ topoAntArrayNo }
		::=  { topologyAntennaArrayTable  1 }


	TopologyAntennaArrayEntry		 ::=  SEQUENCE {
		topoAntArrayNo					Integer32,
		topoAntArrayRowStatus					RowStatus,
		topoAntArrayPosition					Integer32,
		topoAntArrayLocation					DisplayString,
		topoAntArrayVendorIndex					Integer32,
		topoAntArrayTypeIndex					Integer32,
		topoAntArrayIsRet					INTEGER
		}


	topoAntArrayNo		 OBJECT-TYPE
		SYNTAX					 Integer32( 0 .. 191 )
		MAX-ACCESS			 not-accessible
		STATUS					 current
		DESCRIPTION			 " -- "
		::=  { topologyAntennaArrayEntry  1 }


	topoAntArrayRowStatus		 OBJECT-TYPE
		SYNTAX					 RowStatus
		MAX-ACCESS			 read-only
		STATUS					 current
		DESCRIPTION			 " -- "
		::=  { topologyAntennaArrayEntry  2 }


	topoAntArrayPosition		 OBJECT-TYPE
		SYNTAX					 Integer32( 0 .. 359 )
		MAX-ACCESS			 read-only
		STATUS					 current
		DESCRIPTION			 " -- "
		::=  { topologyAntennaArrayEntry  3 }


	topoAntArrayLocation		 OBJECT-TYPE
		SYNTAX					 DisplayString( SIZE ( 1 .. 255 ) )
		MAX-ACCESS			 read-only
		STATUS					 current
		DESCRIPTION			 " -- "
		::=  { topologyAntennaArrayEntry  4 }


	topoAntArrayVendorIndex		 OBJECT-TYPE
		SYNTAX					 Integer32( 0 .. 255 )
		MAX-ACCESS			 read-only
		STATUS					 current
		DESCRIPTION			 " -- "
		::=  { topologyAntennaArrayEntry  5 }


	topoAntArrayTypeIndex		 OBJECT-TYPE
		SYNTAX					 Integer32( 0 .. 47 )
		MAX-ACCESS			 read-only
		STATUS					 current
		DESCRIPTION			 " -- "
		::=  { topologyAntennaArrayEntry  6 }


	topoAntArrayIsRet		 OBJECT-TYPE
		SYNTAX					 INTEGER{ unsupport(0),support(1)  }
		MAX-ACCESS			 read-only
		STATUS					 current
		DESCRIPTION			 " -- "
		::=  { topologyAntennaArrayEntry  7 }


	topoRRUAntSettingTable		 OBJECT-TYPE
		SYNTAX					 SEQUENCE  OF	 TopoRRUAntSettingEntry
		MAX-ACCESS			 not-accessible
		STATUS					 current
		DESCRIPTION			 " -- "
		::=  { remoteRadioUnit  3 }


	topoRRUAntSettingEntry		 OBJECT-TYPE
		SYNTAX					 TopoRRUAntSettingEntry
		MAX-ACCESS			 not-accessible
		STATUS					 current
		DESCRIPTION			 " -- "
		INDEX						{ topoSetRRUNo,topoSetRRUPortNo }
		::=  { topoRRUAntSettingTable  1 }


	TopoRRUAntSettingEntry		 ::=  SEQUENCE {
		topoSetRRUNo					Integer32,
		topoSetRRUPortNo					Integer32,
		topoSetRRUPortWithAntennaRowStatus					RowStatus,
		topoSetRRUPortAntArrayNo					Integer32,
		topoSetRRUPortAntArrayPathNo					Integer32,
		topoSetRRUPortSubtoLocalCellId					Integer32,
		topoSetRRUPortSubtoAntGrpID					Integer32,
		topoSetRRURETAntSupport					INTEGER,
		topoSetRRURETAntRCUNo					Integer32,
		topoSetRRUPortPathNo					Integer32,
		topoSetRRUPortCarrierStart					Integer32,
		topoSetRRUPortCarrierEnd					Integer32,
		topoSetRRUPortMaxTxPower					Integer32,
		topoSetRRUPortSupportFreq					BITS,
		topoSetRRUPortSubtoLocalCellId2					Integer32,
		topoSetRRUPortSubtoLocalCellId3					Integer32,
		topoSetRRUPortSubtoLocalCellId4					Integer32,
		topoSetRRUPortSubtoAntGrpID2					Integer32,
		topoSetRRUPortSubtoAntGrpID3					Integer32,
		topoSetRRUPortSubtoAntGrpID4					Integer32,
		topoSetRRUPortTDCarrierStart					Integer32,
		topoSetRRUPortTDCarrierEnd					Integer32,
		topoSetRRUSendAndRecvAbility					INTEGER,
		topoSetRRUCalAIqTxNom					Integer32,
		topoSetRRUCalAIqRxNom					Integer32,
		topoSetRRUCalPoutTxNom					Integer32,
		topoSetRRUCalPinRxNom					Integer32,
		topoSetRRUPortSubtoTdsLocalCellId					Integer32,
		topoSetRRUTdsCalAIqTxNom					Integer32,
		topoSetRRUTdsCalAIqRxNom					Integer32,
		topoSetRRUTdsCalPoutTxNom					Integer32,
		topoSetRRUTdsCalPinRxNom					Integer32
		}


	topoSetRRUNo		 OBJECT-TYPE
		SYNTAX					 Integer32( 0 .. 191 )
		MAX-ACCESS			 not-accessible
		STATUS					 current
		DESCRIPTION			 " -- "
		::=  { topoRRUAntSettingEntry  1 }


	topoSetRRUPortNo		 OBJECT-TYPE
		SYNTAX					 Integer32( 1 .. 16 )
		MAX-ACCESS			 not-accessible
		STATUS					 current
		DESCRIPTION			 " -- "
		::=  { topoRRUAntSettingEntry  2 }


	topoSetRRUPortWithAntennaRowStatus		 OBJECT-TYPE
		SYNTAX					 RowStatus
		MAX-ACCESS			 read-only
		STATUS					 current
		DESCRIPTION			 " -- "
		::=  { topoRRUAntSettingEntry  3 }


	topoSetRRUPortAntArrayNo		 OBJECT-TYPE
		SYNTAX					 Integer32( 0 .. 191|-1 )
		MAX-ACCESS			 read-only
		STATUS					 current
		DESCRIPTION			 " -- "
		::=  { topoRRUAntSettingEntry  4 }


	topoSetRRUPortAntArrayPathNo		 OBJECT-TYPE
		SYNTAX					 Integer32( 1 .. 8|-1 )
		MAX-ACCESS			 read-only
		STATUS					 current
		DESCRIPTION			 " -- "
		::=  { topoRRUAntSettingEntry  5 }


	topoSetRRUPortSubtoLocalCellId		 OBJECT-TYPE
		SYNTAX					 Integer32( 0 .. 23|-1 )
		MAX-ACCESS			 read-only
		STATUS					 current
		DESCRIPTION			 " -- "
		::=  { topoRRUAntSettingEntry  6 }


	topoSetRRUPortSubtoAntGrpID		 OBJECT-TYPE
		SYNTAX					 Integer32( -1|1 .. 8 )
		MAX-ACCESS			 read-only
		STATUS					 current
		DESCRIPTION			 " -- "
		::=  { topoRRUAntSettingEntry  7 }


	topoSetRRURETAntSupport		 OBJECT-TYPE
		SYNTAX					 INTEGER{ unsupport(0),support(1)  }
		MAX-ACCESS			 read-only
		STATUS					 current
		DESCRIPTION			 " -- "
		::=  { topoRRUAntSettingEntry  8 }


	topoSetRRURETAntRCUNo		 OBJECT-TYPE
		SYNTAX					 Integer32( -1|1 .. 6 )
		MAX-ACCESS			 read-only
		STATUS					 current
		DESCRIPTION			 " -- "
		::=  { topoRRUAntSettingEntry  9 }


	topoSetRRUPortPathNo		 OBJECT-TYPE
		SYNTAX					 Integer32( 1 .. 8 )
		MAX-ACCESS			 read-only
		STATUS					 current
		DESCRIPTION			 " -- "
		::=  { topoRRUAntSettingEntry  10 }


	topoSetRRUPortCarrierStart		 OBJECT-TYPE
		SYNTAX					 Integer32( 0 .. 255 )
		MAX-ACCESS			 read-only
		STATUS					 current
		DESCRIPTION			 " -- "
		::=  { topoRRUAntSettingEntry  11 }


	topoSetRRUPortCarrierEnd		 OBJECT-TYPE
		SYNTAX					 Integer32( 0 .. 255 )
		MAX-ACCESS			 read-only
		STATUS					 current
		DESCRIPTION			 " -- "
		::=  { topoRRUAntSettingEntry  12 }


	topoSetRRUPortMaxTxPower		 OBJECT-TYPE
		SYNTAX					 Integer32( 0 .. 65535 )
		MAX-ACCESS			 read-only
		STATUS					 current
		DESCRIPTION			 " -- "
		::=  { topoRRUAntSettingEntry  13 }


	topoSetRRUPortSupportFreq		 OBJECT-TYPE
		SYNTAX					 BITS{ freqBand0(0),freqBand1(1),freqBand2(2),freqBand3(3),freqBand4(4),freqBand5(5),freqBand6(6),freqBand7(7),freqBand8(8),freqBand9(9),freqBand10(10),freqBand11(11),freqBand12(12),freqBand13(13),freqBand14(14),freqBand15(15)  }
		MAX-ACCESS			 read-only
		STATUS					 current
		DESCRIPTION			 " -- "
		::=  { topoRRUAntSettingEntry  14 }


	topoSetRRUPortSubtoLocalCellId2		 OBJECT-TYPE
		SYNTAX					 Integer32( 0 .. 23|-1 )
		MAX-ACCESS			 read-only
		STATUS					 current
		DESCRIPTION			 " -- "
		::=  { topoRRUAntSettingEntry  15 }


	topoSetRRUPortSubtoLocalCellId3		 OBJECT-TYPE
		SYNTAX					 Integer32( 0 .. 23|-1 )
		MAX-ACCESS			 read-only
		STATUS					 current
		DESCRIPTION			 " -- "
		::=  { topoRRUAntSettingEntry  16 }


	topoSetRRUPortSubtoLocalCellId4		 OBJECT-TYPE
		SYNTAX					 Integer32( 0 .. 23|-1 )
		MAX-ACCESS			 read-only
		STATUS					 current
		DESCRIPTION			 " -- "
		::=  { topoRRUAntSettingEntry  17 }


	topoSetRRUPortSubtoAntGrpID2		 OBJECT-TYPE
		SYNTAX					 Integer32( -1|1 .. 8 )
		MAX-ACCESS			 read-only
		STATUS					 current
		DESCRIPTION			 " -- "
		::=  { topoRRUAntSettingEntry  18 }


	topoSetRRUPortSubtoAntGrpID3		 OBJECT-TYPE
		SYNTAX					 Integer32( -1|1 .. 8 )
		MAX-ACCESS			 read-only
		STATUS					 current
		DESCRIPTION			 " -- "
		::=  { topoRRUAntSettingEntry  19 }


	topoSetRRUPortSubtoAntGrpID4		 OBJECT-TYPE
		SYNTAX					 Integer32( -1|1 .. 8 )
		MAX-ACCESS			 read-only
		STATUS					 current
		DESCRIPTION			 " -- "
		::=  { topoRRUAntSettingEntry  20 }


	topoSetRRUPortTDCarrierStart		 OBJECT-TYPE
		SYNTAX					 Integer32( 0 .. 255 )
		MAX-ACCESS			 read-only
		STATUS					 current
		DESCRIPTION			 " -- "
		::=  { topoRRUAntSettingEntry  21 }


	topoSetRRUPortTDCarrierEnd		 OBJECT-TYPE
		SYNTAX					 Integer32( 0 .. 255 )
		MAX-ACCESS			 read-only
		STATUS					 current
		DESCRIPTION			 " -- "
		::=  { topoRRUAntSettingEntry  22 }


	topoSetRRUSendAndRecvAbility		 OBJECT-TYPE
		SYNTAX					 INTEGER{ recv(1),send(2),recvAndSend(3)  }
		MAX-ACCESS			 read-only
		STATUS					 current
		DESCRIPTION			 " -- "
		::=  { topoRRUAntSettingEntry  23 }


	topoSetRRUCalAIqTxNom		 OBJECT-TYPE
		SYNTAX					 Integer32( -32768 .. 32767 )
		MAX-ACCESS			 read-only
		STATUS					 current
		DESCRIPTION			 " -- "
		::=  { topoRRUAntSettingEntry  24 }


	topoSetRRUCalAIqRxNom		 OBJECT-TYPE
		SYNTAX					 Integer32( -32768 .. 32767 )
		MAX-ACCESS			 read-only
		STATUS					 current
		DESCRIPTION			 " -- "
		::=  { topoRRUAntSettingEntry  25 }


	topoSetRRUCalPoutTxNom		 OBJECT-TYPE
		SYNTAX					 Integer32( -32768 .. 32767 )
		MAX-ACCESS			 read-only
		STATUS					 current
		DESCRIPTION			 " -- "
		::=  { topoRRUAntSettingEntry  26 }


	topoSetRRUCalPinRxNom		 OBJECT-TYPE
		SYNTAX					 Integer32( -32768 .. 32767 )
		MAX-ACCESS			 read-only
		STATUS					 current
		DESCRIPTION			 " -- "
		::=  { topoRRUAntSettingEntry  27 }


	topoSetRRUPortSubtoTdsLocalCellId		 OBJECT-TYPE
		SYNTAX					 Integer32( 0 .. 11|-1 )
		MAX-ACCESS			 read-only
		STATUS					 current
		DESCRIPTION			 " -- "
		::=  { topoRRUAntSettingEntry  28 }


	topoSetRRUTdsCalAIqTxNom		 OBJECT-TYPE
		SYNTAX					 Integer32( -32768 .. 32767 )
		MAX-ACCESS			 read-only
		STATUS					 current
		DESCRIPTION			 " -- "
		::=  { topoRRUAntSettingEntry  29 }


	topoSetRRUTdsCalAIqRxNom		 OBJECT-TYPE
		SYNTAX					 Integer32( -32768 .. 32767 )
		MAX-ACCESS			 read-only
		STATUS					 current
		DESCRIPTION			 " -- "
		::=  { topoRRUAntSettingEntry  30 }


	topoSetRRUTdsCalPoutTxNom		 OBJECT-TYPE
		SYNTAX					 Integer32( -32768 .. 32767 )
		MAX-ACCESS			 read-only
		STATUS					 current
		DESCRIPTION			 " -- "
		::=  { topoRRUAntSettingEntry  31 }


	topoSetRRUTdsCalPinRxNom		 OBJECT-TYPE
		SYNTAX					 Integer32( -32768 .. 32767 )
		MAX-ACCESS			 read-only
		STATUS					 current
		DESCRIPTION			 " -- "
		::=  { topoRRUAntSettingEntry  32 }


	topoRRUBandCapabilityTable		 OBJECT-TYPE
		SYNTAX					 SEQUENCE  OF	 TopoRRUBandCapabilityEntry
		MAX-ACCESS			 not-accessible
		STATUS					 current
		DESCRIPTION			 " -- "
		::=  { remoteRadioUnit  4 }


	topoRRUBandCapabilityEntry		 OBJECT-TYPE
		SYNTAX					 TopoRRUBandCapabilityEntry
		MAX-ACCESS			 not-accessible
		STATUS					 current
		DESCRIPTION			 " -- "
		INDEX						{ topoRRUBandCapRRUNo,topoRRUBandCapBandNo }
		::=  { topoRRUBandCapabilityTable  1 }


	TopoRRUBandCapabilityEntry		 ::=  SEQUENCE {
		topoRRUBandCapRRUNo					Integer32,
		topoRRUBandCapBandNo					Integer32,
		topoRRUBandCapRowStatus					RowStatus,
		topoRRUBandCapCarrierStart					Integer32,
		topoRRUBandCapCarrierEnd					Integer32,
		topoRRUBandCapBandWidth					Integer32,
		topoRRUBandCapCarrierNum					Integer32,
		topoRRUBandCapLTECarrierNum					Integer32
		}


	topoRRUBandCapRRUNo		 OBJECT-TYPE
		SYNTAX					 Integer32( 0 .. 191 )
		MAX-ACCESS			 not-accessible
		STATUS					 current
		DESCRIPTION			 " -- "
		::=  { topoRRUBandCapabilityEntry  1 }


	topoRRUBandCapBandNo		 OBJECT-TYPE
		SYNTAX					 Integer32( 0 .. 15 )
		MAX-ACCESS			 not-accessible
		STATUS					 current
		DESCRIPTION			 " -- "
		::=  { topoRRUBandCapabilityEntry  2 }


	topoRRUBandCapRowStatus		 OBJECT-TYPE
		SYNTAX					 RowStatus
		MAX-ACCESS			 read-only
		STATUS					 current
		DESCRIPTION			 " -- "
		::=  { topoRRUBandCapabilityEntry  3 }


	topoRRUBandCapCarrierStart		 OBJECT-TYPE
		SYNTAX					 Integer32( 0 .. 65535 )
		MAX-ACCESS			 read-only
		STATUS					 current
		DESCRIPTION			 " -- "
		::=  { topoRRUBandCapabilityEntry  4 }


	topoRRUBandCapCarrierEnd		 OBJECT-TYPE
		SYNTAX					 Integer32( 0 .. 65535 )
		MAX-ACCESS			 read-only
		STATUS					 current
		DESCRIPTION			 " -- "
		::=  { topoRRUBandCapabilityEntry  5 }


	topoRRUBandCapBandWidth		 OBJECT-TYPE
		SYNTAX					 Integer32( 0 .. 65535 )
		MAX-ACCESS			 read-only
		STATUS					 current
		DESCRIPTION			 " -- "
		::=  { topoRRUBandCapabilityEntry  6 }


	topoRRUBandCapCarrierNum		 OBJECT-TYPE
		SYNTAX					 Integer32( 0 .. 255 )
		MAX-ACCESS			 read-only
		STATUS					 current
		DESCRIPTION			 " -- "
		::=  { topoRRUBandCapabilityEntry  7 }


	topoRRUBandCapLTECarrierNum		 OBJECT-TYPE
		SYNTAX					 Integer32( 0 .. 255 )
		MAX-ACCESS			 read-only
		STATUS					 current
		DESCRIPTION			 " -- "
		::=  { topoRRUBandCapabilityEntry  8 }


	rruPathTable		 OBJECT-TYPE
		SYNTAX					 SEQUENCE  OF	 RruPathEntry
		MAX-ACCESS			 not-accessible
		STATUS					 current
		DESCRIPTION			 " -- "
		::=  { remoteRadioUnit  5 }


	rruPathEntry		 OBJECT-TYPE
		SYNTAX					 RruPathEntry
		MAX-ACCESS			 not-accessible
		STATUS					 current
		DESCRIPTION			 " -- "
		INDEX						{ rruPathRRUNo,rruPathNo }
		::=  { rruPathTable  1 }


	RruPathEntry		 ::=  SEQUENCE {
		rruPathRRUNo					Integer32,
		rruPathNo					Integer32,
		rruPathRowStatus					RowStatus,
		rruPathTxStatus					INTEGER,
		rruPathRxStatus					INTEGER,
		rruPathOpenState					INTEGER,
		rruPathVSWR					Unsigned32,
		rruPathTxPower					Integer32,
		rruPathTemperature					Integer32,
		rruPathVgsValue1					Integer32,
		rruPathVgsValue2					Integer32,
		rruPathVgsValue3					Integer32,
		rruPathVgsValue4					Integer32,
		rruPathRpdValue					Integer32,
		rruPathTdsTxStatus					INTEGER,
		rruPathTdsRxStatus					INTEGER,
		rruPathAntDelayFactor					Integer32,
		rruPathBand					BITS,
		rruPathLicenseState					INTEGER,
		rruPathRRUGsmCellInputPwr					Integer32,
		rruPathRRUGsmCellOutputPwr					Integer32
		}


	rruPathRRUNo		 OBJECT-TYPE
		SYNTAX					 Integer32( 0 .. 191 )
		MAX-ACCESS			 not-accessible
		STATUS					 current
		DESCRIPTION			 " -- "
		::=  { rruPathEntry  1 }


	rruPathNo		 OBJECT-TYPE
		SYNTAX					 Integer32( 1 .. 16 )
		MAX-ACCESS			 not-accessible
		STATUS					 current
		DESCRIPTION			 " -- "
		::=  { rruPathEntry  2 }


	rruPathRowStatus		 OBJECT-TYPE
		SYNTAX					 RowStatus
		MAX-ACCESS			 read-only
		STATUS					 current
		DESCRIPTION			 " -- "
		::=  { rruPathEntry  3 }


	rruPathTxStatus		 OBJECT-TYPE
		SYNTAX					 INTEGER{ unknown(-1),running(0),failure(1)  }
		MAX-ACCESS			 read-only
		STATUS					 current
		DESCRIPTION			 " -- "
		::=  { rruPathEntry  4 }


	rruPathRxStatus		 OBJECT-TYPE
		SYNTAX					 INTEGER{ unknown(-1),running(0),failure(1)  }
		MAX-ACCESS			 read-only
		STATUS					 current
		DESCRIPTION			 " -- "
		::=  { rruPathEntry  5 }


	rruPathOpenState		 OBJECT-TYPE
		SYNTAX					 INTEGER{ off(0),on(1)  }
		MAX-ACCESS			 read-write
		STATUS					 current
		DESCRIPTION			 " -- "
		::=  { rruPathEntry  6 }


	rruPathVSWR		 OBJECT-TYPE
		SYNTAX					 Unsigned32( 0 .. 10000|4294967295 )
		MAX-ACCESS			 read-only
		STATUS					 current
		DESCRIPTION			 " -- "
		::=  { rruPathEntry  7 }


	rruPathTxPower		 OBJECT-TYPE
		SYNTAX					 Integer32( -32768 .. 32767 )
		MAX-ACCESS			 read-only
		STATUS					 current
		DESCRIPTION			 " -- "
		::=  { rruPathEntry  9 }


	rruPathTemperature		 OBJECT-TYPE
		SYNTAX					 Integer32( -2147483648 .. 2147483647 )
		MAX-ACCESS			 read-only
		STATUS					 current
		DESCRIPTION			 " -- "
		::=  { rruPathEntry  10 }


	rruPathVgsValue1		 OBJECT-TYPE
		SYNTAX					 Integer32( 0 .. 65535 )
		MAX-ACCESS			 read-only
		STATUS					 current
		DESCRIPTION			 " -- "
		::=  { rruPathEntry  14 }


	rruPathVgsValue2		 OBJECT-TYPE
		SYNTAX					 Integer32( 0 .. 65535 )
		MAX-ACCESS			 read-only
		STATUS					 current
		DESCRIPTION			 " -- "
		::=  { rruPathEntry  15 }


	rruPathVgsValue3		 OBJECT-TYPE
		SYNTAX					 Integer32( 0 .. 65535 )
		MAX-ACCESS			 read-only
		STATUS					 current
		DESCRIPTION			 " -- "
		::=  { rruPathEntry  16 }


	rruPathVgsValue4		 OBJECT-TYPE
		SYNTAX					 Integer32( 0 .. 65535 )
		MAX-ACCESS			 read-only
		STATUS					 current
		DESCRIPTION			 " -- "
		::=  { rruPathEntry  17 }


	rruPathRpdValue		 OBJECT-TYPE
		SYNTAX					 Integer32( -2147483648 .. 2147483647 )
		MAX-ACCESS			 read-only
		STATUS					 current
		DESCRIPTION			 " -- "
		::=  { rruPathEntry  18 }


	rruPathTdsTxStatus		 OBJECT-TYPE
		SYNTAX					 INTEGER{ unknown(-1),running(0),failure(1)  }
		MAX-ACCESS			 read-only
		STATUS					 current
		DESCRIPTION			 " -- "
		::=  { rruPathEntry  19 }


	rruPathTdsRxStatus		 OBJECT-TYPE
		SYNTAX					 INTEGER{ unknown(-1),running(0),failure(1)  }
		MAX-ACCESS			 read-only
		STATUS					 current
		DESCRIPTION			 " -- "
		::=  { rruPathEntry  20 }


	rruPathAntDelayFactor		 OBJECT-TYPE
		SYNTAX					 Integer32( 0 .. 13 )
		MAX-ACCESS			 read-only
		STATUS					 current
		DESCRIPTION			 " -- "
		::=  { rruPathEntry  21 }


	rruPathBand		 OBJECT-TYPE
		SYNTAX					 BITS{ f(0),a(1),e(2)  }
		MAX-ACCESS			 read-only
		STATUS					 current
		DESCRIPTION			 " -- "
		::=  { rruPathEntry  22 }


	rruPathLicenseState		 OBJECT-TYPE
		SYNTAX					 INTEGER{ no(0),yes(1)  }
		MAX-ACCESS			 read-only
		STATUS					 current
		DESCRIPTION			 " -- "
		::=  { rruPathEntry  23 }


	rruPathRRUGsmCellInputPwr		 OBJECT-TYPE
		SYNTAX					 Integer32( 0 .. 550 )
		MAX-ACCESS			 read-only
		STATUS					 current
		DESCRIPTION			 " -- "
		::=  { rruPathEntry  35 }


	rruPathRRUGsmCellOutputPwr		 OBJECT-TYPE
		SYNTAX					 Integer32( 0 .. 550 )
		MAX-ACCESS			 read-only
		STATUS					 current
		DESCRIPTION			 " -- "
		::=  { rruPathEntry  36 }


	iuant		 OBJECT IDENTIFIER
		::=  { remoteRadioUnit  6 }


	retap		 OBJECT IDENTIFIER
		::=  { iuant  1 }


	retAntennaRCUTable		 OBJECT-TYPE
		SYNTAX					 SEQUENCE  OF	 RetAntennaRCUEntry
		MAX-ACCESS			 not-accessible
		STATUS					 current
		DESCRIPTION			 " -- "
		::=  { retap  1 }


	retAntennaRCUEntry		 OBJECT-TYPE
		SYNTAX					 RetAntennaRCUEntry
		MAX-ACCESS			 not-accessible
		STATUS					 current
		DESCRIPTION			 " -- "
		INDEX						{ retAntRCUNo,retSubIndexNo }
		::=  { retAntennaRCUTable  1 }


	RetAntennaRCUEntry		 ::=  SEQUENCE {
		retAntRCUNo					Integer32,
		retSubIndexNo					Integer32,
		retAntRCURowStatus					RowStatus,
		retAntRCUProductNumber					DisplayString,
		retAntRCUSerialNumber					DisplayString,
		retAntRCUHwVersion					DisplayString,
		retAntRCUSwVersion					DisplayString,
		retAntRCUUserData					DisplayString,
		retAntRCUResetTrigger					INTEGER,
		retAntRCUAlarmGetTrigger					INTEGER,
		retAntRCUAlarmClearTrigger					INTEGER,
		retAntRCUAlarmSubscribeTrigger					INTEGER,
		retAntRCUSelfTestTrigger					INTEGER,
		retAntModelNumber					DisplayString,
		retAntSerialNumber					DisplayString,
		retAntOperatingBand					DisplayString,
		retAntBeamwidthForEachOperatingBand					DisplayString,
		retAntGainForEachOperatingBand					DisplayString,
		retAntMaximumSupportedElectricalTilt					Integer32,
		retAntMinimumSupportedElectricalTilt					Integer32,
		retAntInstallationDate					DisplayString,
		retAntInstallersID					DisplayString,
		retAntBaseStationID					DisplayString,
		retAntSectorID					DisplayString,
		retAntAntennaBearing					Integer32,
		retAntInstalledMechanicalTilt					Integer32,
		retAntTilt					Integer32,
		retAntCalibrateTrigger					INTEGER,
		retAntRCUOperationState					INTEGER,
		retAntPowerSwitch					INTEGER,
		retAntFrquencyBand					BITS,
		retAntRCUSubtoRRUNo					Integer32,
		retAntMode					INTEGER,
		retAntRCUCarrier					INTEGER,
		retAntOperatingBand2					DisplayString,
		retAntOperatingBand3					DisplayString,
		retAntDownloadFileName					DisplayString,
		retAntDownloadFromDestination					DisplayString
		}


	retAntRCUNo		 OBJECT-TYPE
		SYNTAX					 Integer32( 0 .. 47 )
		MAX-ACCESS			 not-accessible
		STATUS					 current
		DESCRIPTION			 " -- "
		::=  { retAntennaRCUEntry  1 }


	retSubIndexNo		 OBJECT-TYPE
		SYNTAX					 Integer32( 1 .. 5 )
		MAX-ACCESS			 not-accessible
		STATUS					 current
		DESCRIPTION			 " -- "
		::=  { retAntennaRCUEntry  2 }


	retAntRCURowStatus		 OBJECT-TYPE
		SYNTAX					 RowStatus
		MAX-ACCESS			 read-write
		STATUS					 current
		DESCRIPTION			 " -- "
		::=  { retAntennaRCUEntry  3 }


	retAntRCUProductNumber		 OBJECT-TYPE
		SYNTAX					 DisplayString( SIZE ( 1 .. 255 ) )
		MAX-ACCESS			 read-only
		STATUS					 current
		DESCRIPTION			 " -- "
		::=  { retAntennaRCUEntry  4 }


	retAntRCUSerialNumber		 OBJECT-TYPE
		SYNTAX					 DisplayString( SIZE ( 1 .. 255 ) )
		MAX-ACCESS			 read-only
		STATUS					 current
		DESCRIPTION			 " -- "
		::=  { retAntennaRCUEntry  5 }


	retAntRCUHwVersion		 OBJECT-TYPE
		SYNTAX					 DisplayString( SIZE ( 1 .. 255 ) )
		MAX-ACCESS			 read-only
		STATUS					 current
		DESCRIPTION			 " -- "
		::=  { retAntennaRCUEntry  6 }


	retAntRCUSwVersion		 OBJECT-TYPE
		SYNTAX					 DisplayString( SIZE ( 1 .. 255 ) )
		MAX-ACCESS			 read-only
		STATUS					 current
		DESCRIPTION			 " -- "
		::=  { retAntennaRCUEntry  7 }


	retAntRCUUserData		 OBJECT-TYPE
		SYNTAX					 DisplayString( SIZE ( 1 .. 64 ) )
		MAX-ACCESS			 read-write
		STATUS					 current
		DESCRIPTION			 " -- "
		::=  { retAntennaRCUEntry  8 }


	retAntRCUResetTrigger		 OBJECT-TYPE
		SYNTAX					 INTEGER{ off(0),on(1)  }
		MAX-ACCESS			 read-write
		STATUS					 current
		DESCRIPTION			 " -- "
		::=  { retAntennaRCUEntry  9 }


	retAntRCUAlarmGetTrigger		 OBJECT-TYPE
		SYNTAX					 INTEGER{ off(0),on(1)  }
		MAX-ACCESS			 read-write
		STATUS					 current
		DESCRIPTION			 " -- "
		::=  { retAntennaRCUEntry  10 }


	retAntRCUAlarmClearTrigger		 OBJECT-TYPE
		SYNTAX					 INTEGER{ off(0),on(1)  }
		MAX-ACCESS			 read-write
		STATUS					 current
		DESCRIPTION			 " -- "
		::=  { retAntennaRCUEntry  11 }


	retAntRCUAlarmSubscribeTrigger		 OBJECT-TYPE
		SYNTAX					 INTEGER{ off(0),on(1)  }
		MAX-ACCESS			 read-write
		STATUS					 current
		DESCRIPTION			 " -- "
		::=  { retAntennaRCUEntry  12 }


	retAntRCUSelfTestTrigger		 OBJECT-TYPE
		SYNTAX					 INTEGER{ off(0),on(1)  }
		MAX-ACCESS			 read-write
		STATUS					 current
		DESCRIPTION			 " -- "
		::=  { retAntennaRCUEntry  13 }


	retAntModelNumber		 OBJECT-TYPE
		SYNTAX					 DisplayString( SIZE ( 1 .. 15 ) )
		MAX-ACCESS			 read-only
		STATUS					 current
		DESCRIPTION			 " -- "
		::=  { retAntennaRCUEntry  14 }


	retAntSerialNumber		 OBJECT-TYPE
		SYNTAX					 DisplayString( SIZE ( 1 .. 17 ) )
		MAX-ACCESS			 read-only
		STATUS					 current
		DESCRIPTION			 " -- "
		::=  { retAntennaRCUEntry  15 }


	retAntOperatingBand		 OBJECT-TYPE
		SYNTAX					 DisplayString( SIZE ( 1 .. 255 ) )
		MAX-ACCESS			 read-only
		STATUS					 current
		DESCRIPTION			 " -- "
		::=  { retAntennaRCUEntry  16 }


	retAntBeamwidthForEachOperatingBand		 OBJECT-TYPE
		SYNTAX					 DisplayString( SIZE ( 1 .. 255 ) )
		MAX-ACCESS			 read-only
		STATUS					 current
		DESCRIPTION			 " -- "
		::=  { retAntennaRCUEntry  17 }


	retAntGainForEachOperatingBand		 OBJECT-TYPE
		SYNTAX					 DisplayString( SIZE ( 1 .. 255 ) )
		MAX-ACCESS			 read-only
		STATUS					 current
		DESCRIPTION			 " -- "
		::=  { retAntennaRCUEntry  18 }


	retAntMaximumSupportedElectricalTilt		 OBJECT-TYPE
		SYNTAX					 Integer32( 0 .. 3599 )
		MAX-ACCESS			 read-only
		STATUS					 current
		DESCRIPTION			 " -- "
		::=  { retAntennaRCUEntry  19 }


	retAntMinimumSupportedElectricalTilt		 OBJECT-TYPE
		SYNTAX					 Integer32( 0 .. 3599 )
		MAX-ACCESS			 read-only
		STATUS					 current
		DESCRIPTION			 " -- "
		::=  { retAntennaRCUEntry  20 }


	retAntInstallationDate		 OBJECT-TYPE
		SYNTAX					 DisplayString( SIZE ( 6 .. 6 ) )
		MAX-ACCESS			 read-write
		STATUS					 current
		DESCRIPTION			 " -- "
		::=  { retAntennaRCUEntry  21 }


	retAntInstallersID		 OBJECT-TYPE
		SYNTAX					 DisplayString( SIZE ( 1 .. 5 ) )
		MAX-ACCESS			 read-write
		STATUS					 current
		DESCRIPTION			 " -- "
		::=  { retAntennaRCUEntry  22 }


	retAntBaseStationID		 OBJECT-TYPE
		SYNTAX					 DisplayString( SIZE ( 1 .. 32 ) )
		MAX-ACCESS			 read-write
		STATUS					 current
		DESCRIPTION			 " -- "
		::=  { retAntennaRCUEntry  23 }


	retAntSectorID		 OBJECT-TYPE
		SYNTAX					 DisplayString( SIZE ( 1 .. 32 ) )
		MAX-ACCESS			 read-write
		STATUS					 current
		DESCRIPTION			 " -- "
		::=  { retAntennaRCUEntry  24 }


	retAntAntennaBearing		 OBJECT-TYPE
		SYNTAX					 Integer32( 0 .. 3599 )
		MAX-ACCESS			 read-write
		STATUS					 current
		DESCRIPTION			 " -- "
		::=  { retAntennaRCUEntry  25 }


	retAntInstalledMechanicalTilt		 OBJECT-TYPE
		SYNTAX					 Integer32( 0 .. 3599 )
		MAX-ACCESS			 read-write
		STATUS					 current
		DESCRIPTION			 " -- "
		::=  { retAntennaRCUEntry  26 }


	retAntTilt		 OBJECT-TYPE
		SYNTAX					 Integer32( 0 .. 3599 )
		MAX-ACCESS			 read-write
		STATUS					 current
		DESCRIPTION			 " -- "
		::=  { retAntennaRCUEntry  27 }


	retAntCalibrateTrigger		 OBJECT-TYPE
		SYNTAX					 INTEGER{ off(0),on(1)  }
		MAX-ACCESS			 read-write
		STATUS					 current
		DESCRIPTION			 " -- "
		::=  { retAntennaRCUEntry  28 }


	retAntRCUOperationState		 OBJECT-TYPE
		SYNTAX					 INTEGER{ disabled(0),enabled(1),poweroff(2),upgrade(3)  }
		MAX-ACCESS			 read-only
		STATUS					 current
		DESCRIPTION			 " -- "
		::=  { retAntennaRCUEntry  29 }


	retAntPowerSwitch		 OBJECT-TYPE
		SYNTAX					 INTEGER{ off(0),on(1)  }
		MAX-ACCESS			 read-write
		STATUS					 current
		DESCRIPTION			 " -- "
		::=  { retAntennaRCUEntry  30 }


	retAntFrquencyBand		 OBJECT-TYPE
		SYNTAX					 BITS{ a(0),d(1),e(2),f(3),v(5),b41(6),t(7),b03(8),b01(9),b44(10)  }
		MAX-ACCESS			 read-only
		STATUS					 current
		DESCRIPTION			 " -- "
		::=  { retAntennaRCUEntry  31 }


	retAntRCUSubtoRRUNo		 OBJECT-TYPE
		SYNTAX					 Integer32( 0 .. 191|-1 )
		MAX-ACCESS			 read-only
		STATUS					 current
		DESCRIPTION			 " -- "
		::=  { retAntennaRCUEntry  32 }


	retAntMode		 OBJECT-TYPE
		SYNTAX					 INTEGER{ single(0),multi(1)  }
		MAX-ACCESS			 read-only
		STATUS					 current
		DESCRIPTION			 " -- "
		::=  { retAntennaRCUEntry  35 }


	retAntRCUCarrier		 OBJECT-TYPE
		SYNTAX					 INTEGER{ cmcc(0),ctcc(1),cucc(2)  }
		MAX-ACCESS			 read-write
		STATUS					 current
		DESCRIPTION			 " -- "
		::=  { retAntennaRCUEntry  36 }


	retAntOperatingBand2		 OBJECT-TYPE
		SYNTAX					 DisplayString( SIZE ( 1 .. 255 ) )
		MAX-ACCESS			 read-only
		STATUS					 current
		DESCRIPTION			 " -- "
		::=  { retAntennaRCUEntry  37 }


	retAntOperatingBand3		 OBJECT-TYPE
		SYNTAX					 DisplayString( SIZE ( 1 .. 255 ) )
		MAX-ACCESS			 read-only
		STATUS					 current
		DESCRIPTION			 " -- "
		::=  { retAntennaRCUEntry  38 }


	retAntDownloadFileName		 OBJECT-TYPE
		SYNTAX					 DisplayString( SIZE ( 0 .. 255 ) )
		MAX-ACCESS			 read-write
		STATUS					 current
		DESCRIPTION			 " -- "
		::=  { retAntennaRCUEntry  39 }


	retAntDownloadFromDestination		 OBJECT-TYPE
		SYNTAX					 DisplayString( SIZE ( 0 .. 255 ) )
		MAX-ACCESS			 read-write
		STATUS					 current
		DESCRIPTION			 " -- "
		::=  { retAntennaRCUEntry  40 }


	raeap		 OBJECT IDENTIFIER
		::=  { iuant  2 }


	raeTable		 OBJECT-TYPE
		SYNTAX					 SEQUENCE  OF	 RaeEntry
		MAX-ACCESS			 not-accessible
		STATUS					 current
		DESCRIPTION			 " -- "
		::=  { raeap  1 }


	raeEntry		 OBJECT-TYPE
		SYNTAX					 RaeEntry
		MAX-ACCESS			 not-accessible
		STATUS					 current
		DESCRIPTION			 " -- "
		INDEX						{ raeAntennaArrayNo,raeSubIndexNo }
		::=  { raeTable  1 }


	RaeEntry		 ::=  SEQUENCE {
		raeAntennaArrayNo					Integer32,
		raeSubIndexNo					Integer32,
		raeRowStatus					RowStatus,
		raeModelNumber					DisplayString,
		raeAntSerialNumber					DisplayString,
		raeBand					BITS,
		raeBeamwidthOperatBand					Unsigned32Array,
		raeGainForEachOperatingBand					Unsigned32Array,
		raeMaximumSupportedElectricalTilt					Integer32,
		raeMinimumSupportedElectricalTilt					Integer32,
		raeEquipElevation					Integer32,
		raeEquipLongitude					Integer32,
		raeEquipLatitude					Integer32,
		raeInstallationDate					DisplayString,
		raeInstallersID					DisplayString,
		raeBaseStationID					DisplayString,
		raeSectorID					DisplayString,
		raeAntennaBearing					Integer32,
		raeInstalledMechanicalTilt					Integer32,
		raeTestRecord					DisplayString,
		raeSupportFunctions					BITS,
		raeAlarmGetTrigger					INTEGER,
		raeAlarmClearTrigger					INTEGER,
		raeAlarmSubscribeTrigger					INTEGER,
		raeRestoreFactoryWeightingFactorsTrigger					INTEGER,
		raeDownloadFileName					DisplayString,
		raeDownloadFromDestination					DisplayString,
		raeFileNum					Integer32,
		raeWeightFactorInfo					DisplayString,
		raeWeightFactorVer					DisplayString,
		raeTiltNum					Integer32,
		raeTiltBuf					Integer32Array,
		raeBroadcastBeamWidthNum					Integer32,
		raeBroadcastBeamWidthBuf					Integer32Array,
		raeFrequencyBandNum					Integer32,
		raeFrequencyBandBuf					Unsigned32Array,
		raeRFPortsNum					Integer32,
		raeAntAdvancedParam					Integer32,
		raeSubtoRRUNo					Integer32,
		raeRCUNoOnRRU					Integer32,
		raeSubUnitNum					Integer32,
		raeProductNumber					DisplayString,
		raeSerialNumber					DisplayString,
		raeSoftwareVersion					DisplayString,
		raeHardwareVersion					DisplayString,
		raeResetTrigger					INTEGER
		}


	raeAntennaArrayNo		 OBJECT-TYPE
		SYNTAX					 Integer32( 0 .. 47 )
		MAX-ACCESS			 not-accessible
		STATUS					 current
		DESCRIPTION			 " -- "
		::=  { raeEntry  1 }


	raeSubIndexNo		 OBJECT-TYPE
		SYNTAX					 Integer32( 1 .. 5 )
		MAX-ACCESS			 not-accessible
		STATUS					 current
		DESCRIPTION			 " -- "
		::=  { raeEntry  2 }


	raeRowStatus		 OBJECT-TYPE
		SYNTAX					 RowStatus
		MAX-ACCESS			 read-only
		STATUS					 current
		DESCRIPTION			 " -- "
		::=  { raeEntry  3 }


	raeModelNumber		 OBJECT-TYPE
		SYNTAX					 DisplayString( SIZE ( 1 .. 15 ) )
		MAX-ACCESS			 read-only
		STATUS					 current
		DESCRIPTION			 " -- "
		::=  { raeEntry  4 }


	raeAntSerialNumber		 OBJECT-TYPE
		SYNTAX					 DisplayString( SIZE ( 1 .. 255 ) )
		MAX-ACCESS			 read-only
		STATUS					 current
		DESCRIPTION			 " -- "
		::=  { raeEntry  5 }


	raeBand		 OBJECT-TYPE
		SYNTAX					 BITS{ vi(0),v(1),iv(2),iii(3),ii(4),i(5)  }
		MAX-ACCESS			 read-only
		STATUS					 current
		DESCRIPTION			 " -- "
		::=  { raeEntry  6 }


	raeBeamwidthOperatBand		 OBJECT-TYPE
		SYNTAX					 Unsigned32Array
		MAX-ACCESS			 read-only
		STATUS					 current
		DESCRIPTION			 " -- "
		::=  { raeEntry  7 }


	raeGainForEachOperatingBand		 OBJECT-TYPE
		SYNTAX					 Unsigned32Array
		MAX-ACCESS			 read-only
		STATUS					 current
		DESCRIPTION			 " -- "
		::=  { raeEntry  8 }


	raeMaximumSupportedElectricalTilt		 OBJECT-TYPE
		SYNTAX					 Integer32( 0 .. 65535 )
		MAX-ACCESS			 read-only
		STATUS					 current
		DESCRIPTION			 " -- "
		::=  { raeEntry  9 }


	raeMinimumSupportedElectricalTilt		 OBJECT-TYPE
		SYNTAX					 Integer32( 0 .. 65535 )
		MAX-ACCESS			 read-only
		STATUS					 current
		DESCRIPTION			 " -- "
		::=  { raeEntry  10 }


	raeEquipElevation		 OBJECT-TYPE
		SYNTAX					 Integer32( -2147483648 .. 2147483647 )
		MAX-ACCESS			 read-write
		STATUS					 current
		DESCRIPTION			 " -- "
		::=  { raeEntry  11 }


	raeEquipLongitude		 OBJECT-TYPE
		SYNTAX					 Integer32( -2147483648 .. 2147483647 )
		MAX-ACCESS			 read-write
		STATUS					 current
		DESCRIPTION			 " -- "
		::=  { raeEntry  12 }


	raeEquipLatitude		 OBJECT-TYPE
		SYNTAX					 Integer32( -2147483648 .. 2147483647 )
		MAX-ACCESS			 read-write
		STATUS					 current
		DESCRIPTION			 " -- "
		::=  { raeEntry  13 }


	raeInstallationDate		 OBJECT-TYPE
		SYNTAX					 DisplayString( SIZE ( 6 .. 6 ) )
		MAX-ACCESS			 read-write
		STATUS					 current
		DESCRIPTION			 " -- "
		::=  { raeEntry  14 }


	raeInstallersID		 OBJECT-TYPE
		SYNTAX					 DisplayString( SIZE ( 1 .. 5 ) )
		MAX-ACCESS			 read-write
		STATUS					 current
		DESCRIPTION			 " -- "
		::=  { raeEntry  15 }


	raeBaseStationID		 OBJECT-TYPE
		SYNTAX					 DisplayString( SIZE ( 1 .. 32 ) )
		MAX-ACCESS			 read-write
		STATUS					 current
		DESCRIPTION			 " -- "
		::=  { raeEntry  16 }


	raeSectorID		 OBJECT-TYPE
		SYNTAX					 DisplayString( SIZE ( 1 .. 32 ) )
		MAX-ACCESS			 read-write
		STATUS					 current
		DESCRIPTION			 " -- "
		::=  { raeEntry  17 }


	raeAntennaBearing		 OBJECT-TYPE
		SYNTAX					 Integer32( 0 .. 3599 )
		MAX-ACCESS			 read-write
		STATUS					 current
		DESCRIPTION			 " -- "
		::=  { raeEntry  18 }


	raeInstalledMechanicalTilt		 OBJECT-TYPE
		SYNTAX					 Integer32( 0 .. 3599 )
		MAX-ACCESS			 read-write
		STATUS					 current
		DESCRIPTION			 " -- "
		::=  { raeEntry  19 }


	raeTestRecord		 OBJECT-TYPE
		SYNTAX					 DisplayString( SIZE ( 1 .. 70 ) )
		MAX-ACCESS			 read-only
		STATUS					 current
		DESCRIPTION			 " -- "
		::=  { raeEntry  20 }


	raeSupportFunctions		 OBJECT-TYPE
		SYNTAX					 BITS{ weightingFactor(0),locationSensor(1),heightSensor(2),antennaBearingSensor(3),installedMechanicTilt(4),antennaPatternFile(5)  }
		MAX-ACCESS			 read-only
		STATUS					 current
		DESCRIPTION			 " -- "
		::=  { raeEntry  21 }


	raeAlarmGetTrigger		 OBJECT-TYPE
		SYNTAX					 INTEGER{ off(0),on(1)  }
		MAX-ACCESS			 read-write
		STATUS					 current
		DESCRIPTION			 " -- "
		::=  { raeEntry  22 }


	raeAlarmClearTrigger		 OBJECT-TYPE
		SYNTAX					 INTEGER{ off(0),on(1)  }
		MAX-ACCESS			 read-write
		STATUS					 current
		DESCRIPTION			 " -- "
		::=  { raeEntry  23 }


	raeAlarmSubscribeTrigger		 OBJECT-TYPE
		SYNTAX					 INTEGER{ off(0),on(1)  }
		MAX-ACCESS			 read-write
		STATUS					 current
		DESCRIPTION			 " -- "
		::=  { raeEntry  24 }


	raeRestoreFactoryWeightingFactorsTrigger		 OBJECT-TYPE
		SYNTAX					 INTEGER{ off(0),on(1)  }
		MAX-ACCESS			 read-write
		STATUS					 current
		DESCRIPTION			 " -- "
		::=  { raeEntry  25 }


	raeDownloadFileName		 OBJECT-TYPE
		SYNTAX					 DisplayString( SIZE ( 1 .. 150 ) )
		MAX-ACCESS			 read-write
		STATUS					 current
		DESCRIPTION			 " -- "
		::=  { raeEntry  26 }


	raeDownloadFromDestination		 OBJECT-TYPE
		SYNTAX					 DisplayString( SIZE ( 1 .. 150 ) )
		MAX-ACCESS			 read-write
		STATUS					 current
		DESCRIPTION			 " -- "
		::=  { raeEntry  27 }


	raeFileNum		 OBJECT-TYPE
		SYNTAX					 Integer32( -2147483648 .. 2147483647 )
		MAX-ACCESS			 read-only
		STATUS					 current
		DESCRIPTION			 " -- "
		::=  { raeEntry  28 }


	raeWeightFactorInfo		 OBJECT-TYPE
		SYNTAX					 DisplayString( SIZE ( 1 .. 24 ) )
		MAX-ACCESS			 read-only
		STATUS					 current
		DESCRIPTION			 " -- "
		::=  { raeEntry  29 }


	raeWeightFactorVer		 OBJECT-TYPE
		SYNTAX					 DisplayString( SIZE ( 1 .. 24 ) )
		MAX-ACCESS			 read-only
		STATUS					 current
		DESCRIPTION			 " -- "
		::=  { raeEntry  30 }


	raeTiltNum		 OBJECT-TYPE
		SYNTAX					 Integer32( -2147483648 .. 2147483647 )
		MAX-ACCESS			 read-only
		STATUS					 current
		DESCRIPTION			 " -- "
		::=  { raeEntry  31 }


	raeTiltBuf		 OBJECT-TYPE
		SYNTAX					 Integer32Array
		MAX-ACCESS			 read-only
		STATUS					 current
		DESCRIPTION			 " -- "
		::=  { raeEntry  32 }


	raeBroadcastBeamWidthNum		 OBJECT-TYPE
		SYNTAX					 Integer32( -2147483648 .. 2147483647 )
		MAX-ACCESS			 read-only
		STATUS					 current
		DESCRIPTION			 " -- "
		::=  { raeEntry  33 }


	raeBroadcastBeamWidthBuf		 OBJECT-TYPE
		SYNTAX					 Integer32Array
		MAX-ACCESS			 read-only
		STATUS					 current
		DESCRIPTION			 " -- "
		::=  { raeEntry  34 }


	raeFrequencyBandNum		 OBJECT-TYPE
		SYNTAX					 Integer32( -2147483648 .. 2147483647 )
		MAX-ACCESS			 read-only
		STATUS					 current
		DESCRIPTION			 " -- "
		::=  { raeEntry  35 }


	raeFrequencyBandBuf		 OBJECT-TYPE
		SYNTAX					 Unsigned32Array
		MAX-ACCESS			 read-only
		STATUS					 current
		DESCRIPTION			 " -- "
		::=  { raeEntry  36 }


	raeRFPortsNum		 OBJECT-TYPE
		SYNTAX					 Integer32( -2147483648 .. 2147483647 )
		MAX-ACCESS			 read-only
		STATUS					 current
		DESCRIPTION			 " -- "
		::=  { raeEntry  37 }


	raeAntAdvancedParam		 OBJECT-TYPE
		SYNTAX					 Integer32( -2147483648 .. 2147483647 )
		MAX-ACCESS			 read-only
		STATUS					 current
		DESCRIPTION			 " -- "
		::=  { raeEntry  38 }


	raeSubtoRRUNo		 OBJECT-TYPE
		SYNTAX					 Integer32( -2147483648 .. 2147483647 )
		MAX-ACCESS			 read-only
		STATUS					 current
		DESCRIPTION			 " -- "
		::=  { raeEntry  39 }


	raeRCUNoOnRRU		 OBJECT-TYPE
		SYNTAX					 Integer32( -2147483648 .. 2147483647 )
		MAX-ACCESS			 read-only
		STATUS					 current
		DESCRIPTION			 " -- "
		::=  { raeEntry  40 }


	raeSubUnitNum		 OBJECT-TYPE
		SYNTAX					 Integer32( 0 .. 255 )
		MAX-ACCESS			 read-only
		STATUS					 current
		DESCRIPTION			 " -- "
		::=  { raeEntry  41 }


	raeProductNumber		 OBJECT-TYPE
		SYNTAX					 DisplayString( SIZE ( 1 .. 255 ) )
		MAX-ACCESS			 read-only
		STATUS					 current
		DESCRIPTION			 " -- "
		::=  { raeEntry  42 }


	raeSerialNumber		 OBJECT-TYPE
		SYNTAX					 DisplayString( SIZE ( 1 .. 255 ) )
		MAX-ACCESS			 read-only
		STATUS					 current
		DESCRIPTION			 " -- "
		::=  { raeEntry  43 }


	raeSoftwareVersion		 OBJECT-TYPE
		SYNTAX					 DisplayString( SIZE ( 1 .. 255 ) )
		MAX-ACCESS			 read-only
		STATUS					 current
		DESCRIPTION			 " -- "
		::=  { raeEntry  44 }


	raeHardwareVersion		 OBJECT-TYPE
		SYNTAX					 DisplayString( SIZE ( 1 .. 255 ) )
		MAX-ACCESS			 read-only
		STATUS					 current
		DESCRIPTION			 " -- "
		::=  { raeEntry  45 }


	raeResetTrigger		 OBJECT-TYPE
		SYNTAX					 INTEGER{ off(0),on(1)  }
		MAX-ACCESS			 read-write
		STATUS					 current
		DESCRIPTION			 " -- "
		::=  { raeEntry  46 }


	raeFileTable		 OBJECT-TYPE
		SYNTAX					 SEQUENCE  OF	 RaeFileEntry
		MAX-ACCESS			 not-accessible
		STATUS					 current
		DESCRIPTION			 " -- "
		::=  { raeap  2 }


	raeFileEntry		 OBJECT-TYPE
		SYNTAX					 RaeFileEntry
		MAX-ACCESS			 not-accessible
		STATUS					 current
		DESCRIPTION			 " -- "
		INDEX						{ raeFileAntennaArrayNo,raeFileSubIndexNo,raeFileIndex }
		::=  { raeFileTable  1 }


	RaeFileEntry		 ::=  SEQUENCE {
		raeFileAntennaArrayNo					Integer32,
		raeFileSubIndexNo					Integer32,
		raeFileIndex					Integer32,
		raeFileRowStatus					RowStatus,
		raeFileType					INTEGER,
		raeFileSize					Integer32,
		raeFileNameLen					Unsigned32,
		raeFileName					DisplayString,
		raeFileUploadPath					DisplayString,
		raeZipFileName					DisplayString
		}


	raeFileAntennaArrayNo		 OBJECT-TYPE
		SYNTAX					 Integer32( 0 .. 47 )
		MAX-ACCESS			 not-accessible
		STATUS					 current
		DESCRIPTION			 " -- "
		::=  { raeFileEntry  1 }


	raeFileSubIndexNo		 OBJECT-TYPE
		SYNTAX					 Integer32( 1 .. 5 )
		MAX-ACCESS			 not-accessible
		STATUS					 current
		DESCRIPTION			 " -- "
		::=  { raeFileEntry  2 }


	raeFileIndex		 OBJECT-TYPE
		SYNTAX					 Integer32( 0 .. 4 )
		MAX-ACCESS			 not-accessible
		STATUS					 current
		DESCRIPTION			 " -- "
		::=  { raeFileEntry  3 }


	raeFileRowStatus		 OBJECT-TYPE
		SYNTAX					 RowStatus
		MAX-ACCESS			 read-only
		STATUS					 current
		DESCRIPTION			 " -- "
		::=  { raeFileEntry  4 }


	raeFileType		 OBJECT-TYPE
		SYNTAX					 INTEGER{ weightingFactorFile(4),antennaPatternFile(5)  }
		MAX-ACCESS			 read-only
		STATUS					 current
		DESCRIPTION			 " -- "
		::=  { raeFileEntry  5 }


	raeFileSize		 OBJECT-TYPE
		SYNTAX					 Integer32( -2147483648 .. 2147483647 )
		MAX-ACCESS			 read-only
		STATUS					 current
		DESCRIPTION			 " -- "
		::=  { raeFileEntry  6 }


	raeFileNameLen		 OBJECT-TYPE
		SYNTAX					 Unsigned32( 0 .. 4294967295 )
		MAX-ACCESS			 read-only
		STATUS					 current
		DESCRIPTION			 " -- "
		::=  { raeFileEntry  7 }


	raeFileName		 OBJECT-TYPE
		SYNTAX					 DisplayString( SIZE ( 0 .. 255 ) )
		MAX-ACCESS			 read-only
		STATUS					 current
		DESCRIPTION			 " -- "
		::=  { raeFileEntry  8 }


	raeFileUploadPath		 OBJECT-TYPE
		SYNTAX					 DisplayString( SIZE ( 1 .. 150 ) )
		MAX-ACCESS			 read-write
		STATUS					 current
		DESCRIPTION			 " -- "
		::=  { raeFileEntry  9 }


	raeZipFileName		 OBJECT-TYPE
		SYNTAX					 DisplayString( SIZE ( 0 .. 255 ) )
		MAX-ACCESS			 read-only
		STATUS					 current
		DESCRIPTION			 " -- "
		::=  { raeFileEntry  10 }


	raeWeightingFactorsTable		 OBJECT-TYPE
		SYNTAX					 SEQUENCE  OF	 RaeWeightingFactorsEntry
		MAX-ACCESS			 not-accessible
		STATUS					 current
		DESCRIPTION			 " -- "
		::=  { raeap  3 }


	raeWeightingFactorsEntry		 OBJECT-TYPE
		SYNTAX					 RaeWeightingFactorsEntry
		MAX-ACCESS			 not-accessible
		STATUS					 current
		DESCRIPTION			 " -- "
		INDEX						{ raeWeightingFactorsAntennaArrayNo,raeWeightingFactorsSubIndexNo,raeWeightingFactorsInstalledMechanicalTilt,raeWeightFactorsBeamwidthOperatBand,raeWeightingFactorsFrequencyBand }
		::=  { raeWeightingFactorsTable  1 }


	RaeWeightingFactorsEntry		 ::=  SEQUENCE {
		raeWeightingFactorsAntennaArrayNo					Integer32,
		raeWeightingFactorsSubIndexNo					Integer32,
		raeWeightingFactorsInstalledMechanicalTilt					Integer32,
		raeWeightFactorsBeamwidthOperatBand					Integer32,
		raeWeightingFactorsFrequencyBand					INTEGER,
		raeWeightingFactorsAmplitude0					Integer32,
		raeWeightingFactorsPhase0					Integer32,
		raeWeightingFactorsAmplitude1					Integer32,
		raeWeightingFactorsPhase1					Integer32,
		raeWeightingFactorsAmplitude2					Integer32,
		raeWeightingFactorsPhase2					Integer32,
		raeWeightingFactorsAmplitude3					Integer32,
		raeWeightingFactorsPhase3					Integer32,
		raeWeightingFactorsAmplitude4					Integer32,
		raeWeightingFactorsPhase4					Integer32,
		raeWeightingFactorsAmplitude5					Integer32,
		raeWeightingFactorsPhase5					Integer32,
		raeWeightingFactorsAmplitude6					Integer32,
		raeWeightingFactorsPhase6					Integer32,
		raeWeightingFactorsAmplitude7					Integer32,
		raeWeightingFactorsPhase7					Integer32
		}


	raeWeightingFactorsAntennaArrayNo		 OBJECT-TYPE
		SYNTAX					 Integer32( 0 .. 191 )
		MAX-ACCESS			 not-accessible
		STATUS					 current
		DESCRIPTION			 " -- "
		::=  { raeWeightingFactorsEntry  1 }


	raeWeightingFactorsSubIndexNo		 OBJECT-TYPE
		SYNTAX					 Integer32( 1 .. 5 )
		MAX-ACCESS			 not-accessible
		STATUS					 current
		DESCRIPTION			 " -- "
		::=  { raeWeightingFactorsEntry  2 }


	raeWeightingFactorsInstalledMechanicalTilt		 OBJECT-TYPE
		SYNTAX					 Integer32( 0 .. 3599 )
		MAX-ACCESS			 not-accessible
		STATUS					 current
		DESCRIPTION			 " -- "
		::=  { raeWeightingFactorsEntry  3 }


	raeWeightFactorsBeamwidthOperatBand		 OBJECT-TYPE
		SYNTAX					 Integer32( 0 .. 360 )
		MAX-ACCESS			 not-accessible
		STATUS					 current
		DESCRIPTION			 " -- "
		::=  { raeWeightingFactorsEntry  4 }


	raeWeightingFactorsFrequencyBand		 OBJECT-TYPE
		SYNTAX					 INTEGER{ vi(0),v(1),iv(2),iii(3),ii(4),i(5)  }
		MAX-ACCESS			 not-accessible
		STATUS					 current
		DESCRIPTION			 " -- "
		::=  { raeWeightingFactorsEntry  5 }


	raeWeightingFactorsAmplitude0		 OBJECT-TYPE
		SYNTAX					 Integer32( -2147483648 .. 2147483647 )
		MAX-ACCESS			 read-only
		STATUS					 current
		DESCRIPTION			 " -- "
		::=  { raeWeightingFactorsEntry  6 }


	raeWeightingFactorsPhase0		 OBJECT-TYPE
		SYNTAX					 Integer32( -2147483648 .. 2147483647 )
		MAX-ACCESS			 read-only
		STATUS					 current
		DESCRIPTION			 " -- "
		::=  { raeWeightingFactorsEntry  7 }


	raeWeightingFactorsAmplitude1		 OBJECT-TYPE
		SYNTAX					 Integer32( -2147483648 .. 2147483647 )
		MAX-ACCESS			 read-only
		STATUS					 current
		DESCRIPTION			 " -- "
		::=  { raeWeightingFactorsEntry  8 }


	raeWeightingFactorsPhase1		 OBJECT-TYPE
		SYNTAX					 Integer32( -2147483648 .. 2147483647 )
		MAX-ACCESS			 read-only
		STATUS					 current
		DESCRIPTION			 " -- "
		::=  { raeWeightingFactorsEntry  9 }


	raeWeightingFactorsAmplitude2		 OBJECT-TYPE
		SYNTAX					 Integer32( -2147483648 .. 2147483647 )
		MAX-ACCESS			 read-only
		STATUS					 current
		DESCRIPTION			 " -- "
		::=  { raeWeightingFactorsEntry  10 }


	raeWeightingFactorsPhase2		 OBJECT-TYPE
		SYNTAX					 Integer32( -2147483648 .. 2147483647 )
		MAX-ACCESS			 read-only
		STATUS					 current
		DESCRIPTION			 " -- "
		::=  { raeWeightingFactorsEntry  11 }


	raeWeightingFactorsAmplitude3		 OBJECT-TYPE
		SYNTAX					 Integer32( -2147483648 .. 2147483647 )
		MAX-ACCESS			 read-only
		STATUS					 current
		DESCRIPTION			 " -- "
		::=  { raeWeightingFactorsEntry  12 }


	raeWeightingFactorsPhase3		 OBJECT-TYPE
		SYNTAX					 Integer32( -2147483648 .. 2147483647 )
		MAX-ACCESS			 read-only
		STATUS					 current
		DESCRIPTION			 " -- "
		::=  { raeWeightingFactorsEntry  13 }


	raeWeightingFactorsAmplitude4		 OBJECT-TYPE
		SYNTAX					 Integer32( -2147483648 .. 2147483647 )
		MAX-ACCESS			 read-only
		STATUS					 current
		DESCRIPTION			 " -- "
		::=  { raeWeightingFactorsEntry  14 }


	raeWeightingFactorsPhase4		 OBJECT-TYPE
		SYNTAX					 Integer32( -2147483648 .. 2147483647 )
		MAX-ACCESS			 read-only
		STATUS					 current
		DESCRIPTION			 " -- "
		::=  { raeWeightingFactorsEntry  15 }


	raeWeightingFactorsAmplitude5		 OBJECT-TYPE
		SYNTAX					 Integer32( -2147483648 .. 2147483647 )
		MAX-ACCESS			 read-only
		STATUS					 current
		DESCRIPTION			 " -- "
		::=  { raeWeightingFactorsEntry  16 }


	raeWeightingFactorsPhase5		 OBJECT-TYPE
		SYNTAX					 Integer32( -2147483648 .. 2147483647 )
		MAX-ACCESS			 read-only
		STATUS					 current
		DESCRIPTION			 " -- "
		::=  { raeWeightingFactorsEntry  17 }


	raeWeightingFactorsAmplitude6		 OBJECT-TYPE
		SYNTAX					 Integer32( -2147483648 .. 2147483647 )
		MAX-ACCESS			 read-only
		STATUS					 current
		DESCRIPTION			 " -- "
		::=  { raeWeightingFactorsEntry  18 }


	raeWeightingFactorsPhase6		 OBJECT-TYPE
		SYNTAX					 Integer32( -2147483648 .. 2147483647 )
		MAX-ACCESS			 read-only
		STATUS					 current
		DESCRIPTION			 " -- "
		::=  { raeWeightingFactorsEntry  19 }


	raeWeightingFactorsAmplitude7		 OBJECT-TYPE
		SYNTAX					 Integer32( -2147483648 .. 2147483647 )
		MAX-ACCESS			 read-only
		STATUS					 current
		DESCRIPTION			 " -- "
		::=  { raeWeightingFactorsEntry  20 }


	raeWeightingFactorsPhase7		 OBJECT-TYPE
		SYNTAX					 Integer32( -2147483648 .. 2147483647 )
		MAX-ACCESS			 read-only
		STATUS					 current
		DESCRIPTION			 " -- "
		::=  { raeWeightingFactorsEntry  21 }


	raeGeneralTable		 OBJECT-TYPE
		SYNTAX					 SEQUENCE  OF	 RaeGeneralEntry
		MAX-ACCESS			 not-accessible
		STATUS					 current
		DESCRIPTION			 " -- "
		::=  { raeap  4 }


	raeGeneralEntry		 OBJECT-TYPE
		SYNTAX					 RaeGeneralEntry
		MAX-ACCESS			 not-accessible
		STATUS					 current
		DESCRIPTION			 " -- "
		INDEX						{ raeGeneralAntArrayNo,raecGeneralSubIndexNo }
		::=  { raeGeneralTable  1 }


	RaeGeneralEntry		 ::=  SEQUENCE {
		raeGeneralAntArrayNo					Integer32,
		raecGeneralSubIndexNo					Integer32,
		raeGeneralFormatCode					Integer32,
		raeGeneralFileName					DisplayString,
		raeGeneralInfo					DisplayString,
		raeGeneralVer					DisplayString,
		raeGeneralAdvanced					Integer32,
		raeGeneralFreqNums					Integer32,
		raeGeneralLowFreqBuf					Unsigned32Array,
		raeGeneralHighFreqBuf					Unsigned32Array
		}


	raeGeneralAntArrayNo		 OBJECT-TYPE
		SYNTAX					 Integer32( 0 .. 191 )
		MAX-ACCESS			 not-accessible
		STATUS					 current
		DESCRIPTION			 " -- "
		::=  { raeGeneralEntry  1 }


	raecGeneralSubIndexNo		 OBJECT-TYPE
		SYNTAX					 Integer32( 1 .. 5 )
		MAX-ACCESS			 not-accessible
		STATUS					 current
		DESCRIPTION			 " -- "
		::=  { raeGeneralEntry  2 }


	raeGeneralFormatCode		 OBJECT-TYPE
		SYNTAX					 Integer32( 0 .. 255 )
		MAX-ACCESS			 read-only
		STATUS					 current
		DESCRIPTION			 " -- "
		::=  { raeGeneralEntry  3 }


	raeGeneralFileName		 OBJECT-TYPE
		SYNTAX					 DisplayString( SIZE ( 1 .. 62 ) )
		MAX-ACCESS			 read-only
		STATUS					 current
		DESCRIPTION			 " -- "
		::=  { raeGeneralEntry  4 }


	raeGeneralInfo		 OBJECT-TYPE
		SYNTAX					 DisplayString( SIZE ( 1 .. 24 ) )
		MAX-ACCESS			 read-only
		STATUS					 current
		DESCRIPTION			 " -- "
		::=  { raeGeneralEntry  5 }


	raeGeneralVer		 OBJECT-TYPE
		SYNTAX					 DisplayString( SIZE ( 1 .. 24 ) )
		MAX-ACCESS			 read-only
		STATUS					 current
		DESCRIPTION			 " -- "
		::=  { raeGeneralEntry  6 }


	raeGeneralAdvanced		 OBJECT-TYPE
		SYNTAX					 Integer32( 0 .. 65535 )
		MAX-ACCESS			 read-only
		STATUS					 current
		DESCRIPTION			 " -- "
		::=  { raeGeneralEntry  7 }


	raeGeneralFreqNums		 OBJECT-TYPE
		SYNTAX					 Integer32( 0 .. 255 )
		MAX-ACCESS			 read-only
		STATUS					 current
		DESCRIPTION			 " -- "
		::=  { raeGeneralEntry  8 }


	raeGeneralLowFreqBuf		 OBJECT-TYPE
		SYNTAX					 Unsigned32Array
		MAX-ACCESS			 read-only
		STATUS					 current
		DESCRIPTION			 " -- "
		::=  { raeGeneralEntry  9 }


	raeGeneralHighFreqBuf		 OBJECT-TYPE
		SYNTAX					 Unsigned32Array
		MAX-ACCESS			 read-only
		STATUS					 current
		DESCRIPTION			 " -- "
		::=  { raeGeneralEntry  10 }


	raeBeamBandTable		 OBJECT-TYPE
		SYNTAX					 SEQUENCE  OF	 RaeBeamBandEntry
		MAX-ACCESS			 not-accessible
		STATUS					 current
		DESCRIPTION			 " -- "
		::=  { raeap  5 }


	raeBeamBandEntry		 OBJECT-TYPE
		SYNTAX					 RaeBeamBandEntry
		MAX-ACCESS			 not-accessible
		STATUS					 current
		DESCRIPTION			 " -- "
		INDEX						{ raeBeamBandAntArrayNo,raeBeamBandSubIndexNo,raeBeamBandFreq }
		::=  { raeBeamBandTable  1 }


	RaeBeamBandEntry		 ::=  SEQUENCE {
		raeBeamBandAntArrayNo					Integer32,
		raeBeamBandSubIndexNo					Integer32,
		raeBeamBandFreq					Unsigned32,
		raeBeamBandVerticalBandNums					Integer32,
		raeBeamBandVerticalBandBuf					Unsigned32Array,
		raeBeamBandHorizonBandNums					Integer32,
		raeBeamBandHorizonBandBuf					Unsigned32Array
		}


	raeBeamBandAntArrayNo		 OBJECT-TYPE
		SYNTAX					 Integer32( 0 .. 191 )
		MAX-ACCESS			 not-accessible
		STATUS					 current
		DESCRIPTION			 " -- "
		::=  { raeBeamBandEntry  1 }


	raeBeamBandSubIndexNo		 OBJECT-TYPE
		SYNTAX					 Integer32( 1 .. 5 )
		MAX-ACCESS			 not-accessible
		STATUS					 current
		DESCRIPTION			 " -- "
		::=  { raeBeamBandEntry  2 }


	raeBeamBandFreq		 OBJECT-TYPE
		SYNTAX					 Unsigned32( 0 .. 4294967295 )
		MAX-ACCESS			 not-accessible
		STATUS					 current
		DESCRIPTION			 " -- "
		::=  { raeBeamBandEntry  3 }


	raeBeamBandVerticalBandNums		 OBJECT-TYPE
		SYNTAX					 Integer32( 0 .. 255 )
		MAX-ACCESS			 read-only
		STATUS					 current
		DESCRIPTION			 " -- "
		::=  { raeBeamBandEntry  4 }


	raeBeamBandVerticalBandBuf		 OBJECT-TYPE
		SYNTAX					 Unsigned32Array
		MAX-ACCESS			 read-only
		STATUS					 current
		DESCRIPTION			 " -- "
		::=  { raeBeamBandEntry  5 }


	raeBeamBandHorizonBandNums		 OBJECT-TYPE
		SYNTAX					 Integer32( 0 .. 255 )
		MAX-ACCESS			 read-only
		STATUS					 current
		DESCRIPTION			 " -- "
		::=  { raeBeamBandEntry  6 }


	raeBeamBandHorizonBandBuf		 OBJECT-TYPE
		SYNTAX					 Unsigned32Array
		MAX-ACCESS			 read-only
		STATUS					 current
		DESCRIPTION			 " -- "
		::=  { raeBeamBandEntry  7 }


	raePortInfoTable		 OBJECT-TYPE
		SYNTAX					 SEQUENCE  OF	 RaePortInfoEntry
		MAX-ACCESS			 not-accessible
		STATUS					 current
		DESCRIPTION			 " -- "
		::=  { raeap  6 }


	raePortInfoEntry		 OBJECT-TYPE
		SYNTAX					 RaePortInfoEntry
		MAX-ACCESS			 not-accessible
		STATUS					 current
		DESCRIPTION			 " -- "
		INDEX						{ raePortInfoAntArrayNo,raePortInfoSubIndexNo,raePortInfoFreq }
		::=  { raePortInfoTable  1 }


	RaePortInfoEntry		 ::=  SEQUENCE {
		raePortInfoAntArrayNo					Integer32,
		raePortInfoSubIndexNo					Integer32,
		raePortInfoFreq					Unsigned32,
		raePortInfoPortNums					Integer32,
		raePortInfoMode					Unsigned32Array,
		raePortInfoPortIDs					Unsigned32Array
		}


	raePortInfoAntArrayNo		 OBJECT-TYPE
		SYNTAX					 Integer32( 0 .. 191 )
		MAX-ACCESS			 not-accessible
		STATUS					 current
		DESCRIPTION			 " -- "
		::=  { raePortInfoEntry  1 }


	raePortInfoSubIndexNo		 OBJECT-TYPE
		SYNTAX					 Integer32( 1 .. 5 )
		MAX-ACCESS			 not-accessible
		STATUS					 current
		DESCRIPTION			 " -- "
		::=  { raePortInfoEntry  2 }


	raePortInfoFreq		 OBJECT-TYPE
		SYNTAX					 Unsigned32( 0 .. 4294967295 )
		MAX-ACCESS			 not-accessible
		STATUS					 current
		DESCRIPTION			 " -- "
		::=  { raePortInfoEntry  3 }


	raePortInfoPortNums		 OBJECT-TYPE
		SYNTAX					 Integer32( 0 .. 255 )
		MAX-ACCESS			 read-only
		STATUS					 current
		DESCRIPTION			 " -- "
		::=  { raePortInfoEntry  4 }


	raePortInfoMode		 OBJECT-TYPE
		SYNTAX					 Unsigned32Array
		MAX-ACCESS			 read-only
		STATUS					 current
		DESCRIPTION			 " -- "
		::=  { raePortInfoEntry  5 }


	raePortInfoPortIDs		 OBJECT-TYPE
		SYNTAX					 Unsigned32Array
		MAX-ACCESS			 read-only
		STATUS					 current
		DESCRIPTION			 " -- "
		::=  { raePortInfoEntry  6 }


	raeBmIndicatTable		 OBJECT-TYPE
		SYNTAX					 SEQUENCE  OF	 RaeBmIndicatEntry
		MAX-ACCESS			 not-accessible
		STATUS					 current
		DESCRIPTION			 " -- "
		::=  { raeap  7 }


	raeBmIndicatEntry		 OBJECT-TYPE
		SYNTAX					 RaeBmIndicatEntry
		MAX-ACCESS			 not-accessible
		STATUS					 current
		DESCRIPTION			 " -- "
		INDEX						{ raeBmIndicatAntArrayNo,raeBmIndicatSubIndexNo,raeBmIndicatFreq,raeBmIndicatVerticalBand,raeBmIndicatHorizonBand }
		::=  { raeBmIndicatTable  1 }


	RaeBmIndicatEntry		 ::=  SEQUENCE {
		raeBmIndicatAntArrayNo					Integer32,
		raeBmIndicatSubIndexNo					Integer32,
		raeBmIndicatFreq					Unsigned32,
		raeBmIndicatVerticalBand					Integer32,
		raeBmIndicatHorizonBand					Integer32,
		raeBmIndicatTiltStep					Integer32,
		raeBmIndicatTiltRangeL					Integer32,
		raeBmIndicatTiltRangeH					Integer32,
		raeBmIndicatBearingStep					Integer32,
		raeBmIndicatBearingRangeL					Integer32,
		raeBmIndicatBearingRangeH					Integer32
		}


	raeBmIndicatAntArrayNo		 OBJECT-TYPE
		SYNTAX					 Integer32( 0 .. 191 )
		MAX-ACCESS			 not-accessible
		STATUS					 current
		DESCRIPTION			 " -- "
		::=  { raeBmIndicatEntry  1 }


	raeBmIndicatSubIndexNo		 OBJECT-TYPE
		SYNTAX					 Integer32( 1 .. 5 )
		MAX-ACCESS			 not-accessible
		STATUS					 current
		DESCRIPTION			 " -- "
		::=  { raeBmIndicatEntry  2 }


	raeBmIndicatFreq		 OBJECT-TYPE
		SYNTAX					 Unsigned32( 0 .. 4294967295 )
		MAX-ACCESS			 not-accessible
		STATUS					 current
		DESCRIPTION			 " -- "
		::=  { raeBmIndicatEntry  3 }


	raeBmIndicatVerticalBand		 OBJECT-TYPE
		SYNTAX					 Integer32( 0 .. 360 )
		MAX-ACCESS			 not-accessible
		STATUS					 current
		DESCRIPTION			 " -- "
		::=  { raeBmIndicatEntry  4 }


	raeBmIndicatHorizonBand		 OBJECT-TYPE
		SYNTAX					 Integer32( 0 .. 360 )
		MAX-ACCESS			 not-accessible
		STATUS					 current
		DESCRIPTION			 " -- "
		::=  { raeBmIndicatEntry  5 }


	raeBmIndicatTiltStep		 OBJECT-TYPE
		SYNTAX					 Integer32( 0 .. 255 )
		MAX-ACCESS			 read-only
		STATUS					 current
		DESCRIPTION			 " -- "
		::=  { raeBmIndicatEntry  6 }


	raeBmIndicatTiltRangeL		 OBJECT-TYPE
		SYNTAX					 Integer32( -2147483648 .. 2147483647 )
		MAX-ACCESS			 read-only
		STATUS					 current
		DESCRIPTION			 " -- "
		::=  { raeBmIndicatEntry  7 }


	raeBmIndicatTiltRangeH		 OBJECT-TYPE
		SYNTAX					 Integer32( -2147483648 .. 2147483647 )
		MAX-ACCESS			 read-only
		STATUS					 current
		DESCRIPTION			 " -- "
		::=  { raeBmIndicatEntry  8 }


	raeBmIndicatBearingStep		 OBJECT-TYPE
		SYNTAX					 Integer32( 0 .. 255 )
		MAX-ACCESS			 read-only
		STATUS					 current
		DESCRIPTION			 " -- "
		::=  { raeBmIndicatEntry  9 }


	raeBmIndicatBearingRangeL		 OBJECT-TYPE
		SYNTAX					 Integer32( -32768 .. 32767 )
		MAX-ACCESS			 read-only
		STATUS					 current
		DESCRIPTION			 " -- "
		::=  { raeBmIndicatEntry  10 }


	raeBmIndicatBearingRangeH		 OBJECT-TYPE
		SYNTAX					 Integer32( -32768 .. 32767 )
		MAX-ACCESS			 read-only
		STATUS					 current
		DESCRIPTION			 " -- "
		::=  { raeBmIndicatEntry  11 }


	raeGroupsTable		 OBJECT-TYPE
		SYNTAX					 SEQUENCE  OF	 RaeGroupsEntry
		MAX-ACCESS			 not-accessible
		STATUS					 current
		DESCRIPTION			 " -- "
		::=  { raeap  8 }


	raeGroupsEntry		 OBJECT-TYPE
		SYNTAX					 RaeGroupsEntry
		MAX-ACCESS			 not-accessible
		STATUS					 current
		DESCRIPTION			 " -- "
		INDEX						{ raeGroupsAntArrayNo,raeGroupsSubIndexNo }
		::=  { raeGroupsTable  1 }


	RaeGroupsEntry		 ::=  SEQUENCE {
		raeGroupsAntArrayNo					Integer32,
		raeGroupsSubIndexNo					Integer32,
		raeGroupsRowStatus					RowStatus,
		raeGroupsFreq					Unsigned32,
		raeGroupsVerticalBand					Integer32,
		raeGroupsHorizonBand					Integer32,
		raeGroupsTilt					Integer32,
		raeGroupsAntennaBearing					Integer32,
		raeGroupsGroups					Integer32
		}


	raeGroupsAntArrayNo		 OBJECT-TYPE
		SYNTAX					 Integer32( 0 .. 191 )
		MAX-ACCESS			 not-accessible
		STATUS					 current
		DESCRIPTION			 " -- "
		::=  { raeGroupsEntry  1 }


	raeGroupsSubIndexNo		 OBJECT-TYPE
		SYNTAX					 Integer32( 1 .. 5 )
		MAX-ACCESS			 not-accessible
		STATUS					 current
		DESCRIPTION			 " -- "
		::=  { raeGroupsEntry  2 }


	raeGroupsRowStatus		 OBJECT-TYPE
		SYNTAX					 RowStatus
		MAX-ACCESS			 read-write
		STATUS					 current
		DESCRIPTION			 " -- "
		::=  { raeGroupsEntry  3 }


	raeGroupsFreq		 OBJECT-TYPE
		SYNTAX					 Unsigned32( 0 .. 4294967295 )
		MAX-ACCESS			 read-write
		STATUS					 current
		DESCRIPTION			 " -- "
		::=  { raeGroupsEntry  4 }


	raeGroupsVerticalBand		 OBJECT-TYPE
		SYNTAX					 Integer32( 0 .. 360 )
		MAX-ACCESS			 read-write
		STATUS					 current
		DESCRIPTION			 " -- "
		::=  { raeGroupsEntry  5 }


	raeGroupsHorizonBand		 OBJECT-TYPE
		SYNTAX					 Integer32( 0 .. 360 )
		MAX-ACCESS			 read-write
		STATUS					 current
		DESCRIPTION			 " -- "
		::=  { raeGroupsEntry  6 }


	raeGroupsTilt		 OBJECT-TYPE
		SYNTAX					 Integer32( 0 .. 359 )
		MAX-ACCESS			 read-write
		STATUS					 current
		DESCRIPTION			 " -- "
		::=  { raeGroupsEntry  7 }


	raeGroupsAntennaBearing		 OBJECT-TYPE
		SYNTAX					 Integer32( -359 .. 359 )
		MAX-ACCESS			 read-write
		STATUS					 current
		DESCRIPTION			 " -- "
		::=  { raeGroupsEntry  8 }


	raeGroupsGroups		 OBJECT-TYPE
		SYNTAX					 Integer32( 0 .. 255 )
		MAX-ACCESS			 read-only
		STATUS					 current
		DESCRIPTION			 " -- "
		::=  { raeGroupsEntry  9 }


	raeParamTable		 OBJECT-TYPE
		SYNTAX					 SEQUENCE  OF	 RaeParamEntry
		MAX-ACCESS			 not-accessible
		STATUS					 current
		DESCRIPTION			 " -- "
		::=  { raeap  9 }


	raeParamEntry		 OBJECT-TYPE
		SYNTAX					 RaeParamEntry
		MAX-ACCESS			 not-accessible
		STATUS					 current
		DESCRIPTION			 " -- "
		INDEX						{ raeParamAntArrayNo,raeParamSubIndexNo }
		::=  { raeParamTable  1 }


	RaeParamEntry		 ::=  SEQUENCE {
		raeParamAntArrayNo					Integer32,
		raeParamSubIndexNo					Integer32,
		raeParamRowStatus					RowStatus,
		raeParamFreq					Unsigned32,
		raeParamVerticalBand					Integer32,
		raeParamHorizonBand					Integer32,
		raeParamTilt					Integer32,
		raeParamAntennaBearing					Integer32,
		raeParamGroup					Integer32,
		raeParamAmplitude					Unsigned32Array,
		raeParamPhase					Integer32Array,
		raeParamUseTrigger					INTEGER
		}


	raeParamAntArrayNo		 OBJECT-TYPE
		SYNTAX					 Integer32( 0 .. 191 )
		MAX-ACCESS			 not-accessible
		STATUS					 current
		DESCRIPTION			 " -- "
		::=  { raeParamEntry  1 }


	raeParamSubIndexNo		 OBJECT-TYPE
		SYNTAX					 Integer32( 1 .. 5 )
		MAX-ACCESS			 not-accessible
		STATUS					 current
		DESCRIPTION			 " -- "
		::=  { raeParamEntry  2 }


	raeParamRowStatus		 OBJECT-TYPE
		SYNTAX					 RowStatus
		MAX-ACCESS			 read-write
		STATUS					 current
		DESCRIPTION			 " -- "
		::=  { raeParamEntry  3 }


	raeParamFreq		 OBJECT-TYPE
		SYNTAX					 Unsigned32( 0 .. 4294967295 )
		MAX-ACCESS			 read-write
		STATUS					 current
		DESCRIPTION			 " -- "
		::=  { raeParamEntry  4 }


	raeParamVerticalBand		 OBJECT-TYPE
		SYNTAX					 Integer32( 0 .. 360 )
		MAX-ACCESS			 read-write
		STATUS					 current
		DESCRIPTION			 " -- "
		::=  { raeParamEntry  5 }


	raeParamHorizonBand		 OBJECT-TYPE
		SYNTAX					 Integer32( 0 .. 360 )
		MAX-ACCESS			 read-write
		STATUS					 current
		DESCRIPTION			 " -- "
		::=  { raeParamEntry  6 }


	raeParamTilt		 OBJECT-TYPE
		SYNTAX					 Integer32( 0 .. 359 )
		MAX-ACCESS			 read-write
		STATUS					 current
		DESCRIPTION			 " -- "
		::=  { raeParamEntry  7 }


	raeParamAntennaBearing		 OBJECT-TYPE
		SYNTAX					 Integer32( -359 .. 359 )
		MAX-ACCESS			 read-write
		STATUS					 current
		DESCRIPTION			 " -- "
		::=  { raeParamEntry  8 }


	raeParamGroup		 OBJECT-TYPE
		SYNTAX					 Integer32( 0 .. 255 )
		MAX-ACCESS			 read-write
		STATUS					 current
		DESCRIPTION			 " -- "
		::=  { raeParamEntry  9 }


	raeParamAmplitude		 OBJECT-TYPE
		SYNTAX					 Unsigned32Array
		MAX-ACCESS			 read-only
		STATUS					 current
		DESCRIPTION			 " -- "
		::=  { raeParamEntry  10 }


	raeParamPhase		 OBJECT-TYPE
		SYNTAX					 Integer32Array
		MAX-ACCESS			 read-only
		STATUS					 current
		DESCRIPTION			 " -- "
		::=  { raeParamEntry  11 }


	raeParamUseTrigger		 OBJECT-TYPE
		SYNTAX					 INTEGER{ on(1)  }
		MAX-ACCESS			 read-write
		STATUS					 current
		DESCRIPTION			 " -- "
		::=  { raeParamEntry  12 }


	rruOpticalTransceiverTable		 OBJECT-TYPE
		SYNTAX					 SEQUENCE  OF	 RruOpticalTransceiverEntry
		MAX-ACCESS			 not-accessible
		STATUS					 current
		DESCRIPTION			 " -- "
		::=  { remoteRadioUnit  7 }


	rruOpticalTransceiverEntry		 OBJECT-TYPE
		SYNTAX					 RruOpticalTransceiverEntry
		MAX-ACCESS			 not-accessible
		STATUS					 current
		DESCRIPTION			 " -- "
		INDEX						{ rruOptTransRRUNo,rruOptTransIndex }
		::=  { rruOpticalTransceiverTable  1 }


	RruOpticalTransceiverEntry		 ::=  SEQUENCE {
		rruOptTransRRUNo					Integer32,
		rruOptTransIndex					INTEGER,
		rruOptTransRowStatus					RowStatus,
		rruOptTransTemperature					Integer32,
		rruOptTransVcc					Integer32,
		rruOptTransBias					Integer32,
		rruOptTransTxPower					Integer32,
		rruOptTransRxPower					Integer32,
		rruOptTransStandStatus					INTEGER,
		rruOptTransVendorName					DisplayString,
		rruOptTransS9umKmLen					Integer32,
		rruOptTransS9um100MLen					Integer32,
		rruOptTransM50um10MLen					Integer32,
		rruOptTransM625um10MLen					Integer32,
		rruOptTransBitRate					Integer32,
		rruOptTransFpgaStatus					INTEGER,
		rruOptBitErrorRate					Unsigned32
		}


	rruOptTransRRUNo		 OBJECT-TYPE
		SYNTAX					 Integer32( 0 .. 191 )
		MAX-ACCESS			 not-accessible
		STATUS					 current
		DESCRIPTION			 " -- "
		::=  { rruOpticalTransceiverEntry  1 }


	rruOptTransIndex		 OBJECT-TYPE
		SYNTAX					 INTEGER{ ofp1(0),ofp2(1)  }
		MAX-ACCESS			 not-accessible
		STATUS					 current
		DESCRIPTION			 " -- "
		::=  { rruOpticalTransceiverEntry  2 }


	rruOptTransRowStatus		 OBJECT-TYPE
		SYNTAX					 RowStatus
		MAX-ACCESS			 read-only
		STATUS					 current
		DESCRIPTION			 " -- "
		::=  { rruOpticalTransceiverEntry  3 }


	rruOptTransTemperature		 OBJECT-TYPE
		SYNTAX					 Integer32( -128 .. 127 )
		MAX-ACCESS			 read-only
		STATUS					 current
		DESCRIPTION			 " -- "
		::=  { rruOpticalTransceiverEntry  4 }


	rruOptTransVcc		 OBJECT-TYPE
		SYNTAX					 Integer32( 0 .. 65535 )
		MAX-ACCESS			 read-only
		STATUS					 current
		DESCRIPTION			 " -- "
		::=  { rruOpticalTransceiverEntry  5 }


	rruOptTransBias		 OBJECT-TYPE
		SYNTAX					 Integer32( 0 .. 65535 )
		MAX-ACCESS			 read-only
		STATUS					 current
		DESCRIPTION			 " -- "
		::=  { rruOpticalTransceiverEntry  6 }


	rruOptTransTxPower		 OBJECT-TYPE
		SYNTAX					 Integer32( -2147483648 .. 2147483647 )
		MAX-ACCESS			 read-only
		STATUS					 current
		DESCRIPTION			 " -- "
		::=  { rruOpticalTransceiverEntry  7 }


	rruOptTransRxPower		 OBJECT-TYPE
		SYNTAX					 Integer32( -2147483648 .. 2147483647 )
		MAX-ACCESS			 read-only
		STATUS					 current
		DESCRIPTION			 " -- "
		::=  { rruOpticalTransceiverEntry  8 }


	rruOptTransStandStatus		 OBJECT-TYPE
		SYNTAX					 INTEGER{ notExisted(0),existed(1)  }
		MAX-ACCESS			 read-only
		STATUS					 current
		DESCRIPTION			 " -- "
		::=  { rruOpticalTransceiverEntry  9 }


	rruOptTransVendorName		 OBJECT-TYPE
		SYNTAX					 DisplayString( SIZE ( 0 .. 255 ) )
		MAX-ACCESS			 read-only
		STATUS					 current
		DESCRIPTION			 " -- "
		::=  { rruOpticalTransceiverEntry  10 }


	rruOptTransS9umKmLen		 OBJECT-TYPE
		SYNTAX					 Integer32( 0|1 .. 255 )
		MAX-ACCESS			 read-only
		STATUS					 current
		DESCRIPTION			 " -- "
		::=  { rruOpticalTransceiverEntry  11 }


	rruOptTransS9um100MLen		 OBJECT-TYPE
		SYNTAX					 Integer32( 0|1 .. 255 )
		MAX-ACCESS			 read-only
		STATUS					 current
		DESCRIPTION			 " -- "
		::=  { rruOpticalTransceiverEntry  12 }


	rruOptTransM50um10MLen		 OBJECT-TYPE
		SYNTAX					 Integer32( 0|1 .. 255 )
		MAX-ACCESS			 read-only
		STATUS					 current
		DESCRIPTION			 " -- "
		::=  { rruOpticalTransceiverEntry  13 }


	rruOptTransM625um10MLen		 OBJECT-TYPE
		SYNTAX					 Integer32( 0|1 .. 255 )
		MAX-ACCESS			 read-only
		STATUS					 current
		DESCRIPTION			 " -- "
		::=  { rruOpticalTransceiverEntry  14 }


	rruOptTransBitRate		 OBJECT-TYPE
		SYNTAX					 Integer32( -2147483648 .. 2147483647 )
		MAX-ACCESS			 read-only
		STATUS					 current
		DESCRIPTION			 " -- "
		::=  { rruOpticalTransceiverEntry  15 }


	rruOptTransFpgaStatus		 OBJECT-TYPE
		SYNTAX					 INTEGER{ syn(0),asyn(1)  }
		MAX-ACCESS			 read-only
		STATUS					 current
		DESCRIPTION			 " -- "
		::=  { rruOpticalTransceiverEntry  16 }


	rruOptBitErrorRate		 OBJECT-TYPE
		SYNTAX					 Unsigned32( 0 .. 4294967295 )
		MAX-ACCESS			 read-only
		STATUS					 current
		DESCRIPTION			 " -- "
		::=  { rruOpticalTransceiverEntry  17 }


	topoRRUPortBandCapabTable		 OBJECT-TYPE
		SYNTAX					 SEQUENCE  OF	 TopoRRUPortBandCapabEntry
		MAX-ACCESS			 not-accessible
		STATUS					 current
		DESCRIPTION			 " -- "
		::=  { remoteRadioUnit  8 }


	topoRRUPortBandCapabEntry		 OBJECT-TYPE
		SYNTAX					 TopoRRUPortBandCapabEntry
		MAX-ACCESS			 not-accessible
		STATUS					 current
		DESCRIPTION			 " -- "
		INDEX						{ topoPortBandCapRRUNo,topoPortBandCapRRUPortNo,topoPortBandCapNo }
		::=  { topoRRUPortBandCapabTable  1 }


	TopoRRUPortBandCapabEntry		 ::=  SEQUENCE {
		topoPortBandCapRRUNo					Integer32,
		topoPortBandCapRRUPortNo					Integer32,
		topoPortBandCapNo					Integer32,
		topoPortBandCapRowStatus					RowStatus,
		topoRRUBandCap1P4CarrierNum					Integer32,
		topoRRUBandCap3MCarrierNum					Integer32,
		topoRRUBandCap5MCarrierNum					Integer32,
		topoRRUBandCap10MCarrierNum					Integer32,
		topoRRUBandCap15MCarrierNum					Integer32,
		topoRRUBandCap20MCarrierNum					Integer32
		}


	topoPortBandCapRRUNo		 OBJECT-TYPE
		SYNTAX					 Integer32( 0 .. 191 )
		MAX-ACCESS			 not-accessible
		STATUS					 current
		DESCRIPTION			 " -- "
		::=  { topoRRUPortBandCapabEntry  1 }


	topoPortBandCapRRUPortNo		 OBJECT-TYPE
		SYNTAX					 Integer32( 1 .. 16 )
		MAX-ACCESS			 not-accessible
		STATUS					 current
		DESCRIPTION			 " -- "
		::=  { topoRRUPortBandCapabEntry  2 }


	topoPortBandCapNo		 OBJECT-TYPE
		SYNTAX					 Integer32( 0 .. 15 )
		MAX-ACCESS			 not-accessible
		STATUS					 current
		DESCRIPTION			 " -- "
		::=  { topoRRUPortBandCapabEntry  3 }


	topoPortBandCapRowStatus		 OBJECT-TYPE
		SYNTAX					 RowStatus
		MAX-ACCESS			 read-only
		STATUS					 current
		DESCRIPTION			 " -- "
		::=  { topoRRUPortBandCapabEntry  4 }


	topoRRUBandCap1P4CarrierNum		 OBJECT-TYPE
		SYNTAX					 Integer32( 0 .. 255 )
		MAX-ACCESS			 read-only
		STATUS					 current
		DESCRIPTION			 " -- "
		::=  { topoRRUPortBandCapabEntry  5 }


	topoRRUBandCap3MCarrierNum		 OBJECT-TYPE
		SYNTAX					 Integer32( 0 .. 255 )
		MAX-ACCESS			 read-only
		STATUS					 current
		DESCRIPTION			 " -- "
		::=  { topoRRUPortBandCapabEntry  6 }


	topoRRUBandCap5MCarrierNum		 OBJECT-TYPE
		SYNTAX					 Integer32( 0 .. 255 )
		MAX-ACCESS			 read-only
		STATUS					 current
		DESCRIPTION			 " -- "
		::=  { topoRRUPortBandCapabEntry  7 }


	topoRRUBandCap10MCarrierNum		 OBJECT-TYPE
		SYNTAX					 Integer32( 0 .. 255 )
		MAX-ACCESS			 read-only
		STATUS					 current
		DESCRIPTION			 " -- "
		::=  { topoRRUPortBandCapabEntry  8 }


	topoRRUBandCap15MCarrierNum		 OBJECT-TYPE
		SYNTAX					 Integer32( 0 .. 255 )
		MAX-ACCESS			 read-only
		STATUS					 current
		DESCRIPTION			 " -- "
		::=  { topoRRUPortBandCapabEntry  9 }


	topoRRUBandCap20MCarrierNum		 OBJECT-TYPE
		SYNTAX					 Integer32( 0 .. 255 )
		MAX-ACCESS			 read-only
		STATUS					 current
		DESCRIPTION			 " -- "
		::=  { topoRRUPortBandCapabEntry  10 }


	rruCalcPathTable		 OBJECT-TYPE
		SYNTAX					 SEQUENCE  OF	 RruCalcPathEntry
		MAX-ACCESS			 not-accessible
		STATUS					 current
		DESCRIPTION			 " -- "
		::=  { remoteRadioUnit  9 }


	rruCalcPathEntry		 OBJECT-TYPE
		SYNTAX					 RruCalcPathEntry
		MAX-ACCESS			 not-accessible
		STATUS					 current
		DESCRIPTION			 " -- "
		INDEX						{ rruCalcPathRRUNo,rruCalcPathNo }
		::=  { rruCalcPathTable  1 }


	RruCalcPathEntry		 ::=  SEQUENCE {
		rruCalcPathRRUNo					Integer32,
		rruCalcPathNo					Integer32,
		rruCalcPathRowStatus					RowStatus,
		rruCalcPathTxStatus					INTEGER,
		rruCalcPathRxStatus					INTEGER,
		rruCalcPathAIqTxNom					Integer32,
		rruCalcPathAIqRxNom					Integer32,
		rruCalcPathPoutTxNom					Integer32,
		rruCalcPathPinRxNom					Integer32
		}


	rruCalcPathRRUNo		 OBJECT-TYPE
		SYNTAX					 Integer32( 0 .. 191 )
		MAX-ACCESS			 not-accessible
		STATUS					 current
		DESCRIPTION			 " -- "
		::=  { rruCalcPathEntry  1 }


	rruCalcPathNo		 OBJECT-TYPE
		SYNTAX					 Integer32( 1 .. 8 )
		MAX-ACCESS			 not-accessible
		STATUS					 current
		DESCRIPTION			 " -- "
		::=  { rruCalcPathEntry  2 }


	rruCalcPathRowStatus		 OBJECT-TYPE
		SYNTAX					 RowStatus
		MAX-ACCESS			 read-only
		STATUS					 current
		DESCRIPTION			 " -- "
		::=  { rruCalcPathEntry  3 }


	rruCalcPathTxStatus		 OBJECT-TYPE
		SYNTAX					 INTEGER{ unknown(-1),running(0),failure(1)  }
		MAX-ACCESS			 read-only
		STATUS					 current
		DESCRIPTION			 " -- "
		::=  { rruCalcPathEntry  4 }


	rruCalcPathRxStatus		 OBJECT-TYPE
		SYNTAX					 INTEGER{ unknown(-1),running(0),failure(1)  }
		MAX-ACCESS			 read-only
		STATUS					 current
		DESCRIPTION			 " -- "
		::=  { rruCalcPathEntry  5 }


	rruCalcPathAIqTxNom		 OBJECT-TYPE
		SYNTAX					 Integer32( -32768 .. 32767 )
		MAX-ACCESS			 read-only
		STATUS					 current
		DESCRIPTION			 " -- "
		::=  { rruCalcPathEntry  6 }


	rruCalcPathAIqRxNom		 OBJECT-TYPE
		SYNTAX					 Integer32( -32768 .. 32767 )
		MAX-ACCESS			 read-only
		STATUS					 current
		DESCRIPTION			 " -- "
		::=  { rruCalcPathEntry  7 }


	rruCalcPathPoutTxNom		 OBJECT-TYPE
		SYNTAX					 Integer32( -32768 .. 32767 )
		MAX-ACCESS			 read-only
		STATUS					 current
		DESCRIPTION			 " -- "
		::=  { rruCalcPathEntry  8 }


	rruCalcPathPinRxNom		 OBJECT-TYPE
		SYNTAX					 Integer32( -32768 .. 32767 )
		MAX-ACCESS			 read-only
		STATUS					 current
		DESCRIPTION			 " -- "
		::=  { rruCalcPathEntry  9 }


	topoRRUPACurrentTable		 OBJECT-TYPE
		SYNTAX					 SEQUENCE  OF	 TopoRRUPACurrentEntry
		MAX-ACCESS			 not-accessible
		STATUS					 current
		DESCRIPTION			 " -- "
		::=  { remoteRadioUnit  10 }


	topoRRUPACurrentEntry		 OBJECT-TYPE
		SYNTAX					 TopoRRUPACurrentEntry
		MAX-ACCESS			 not-accessible
		STATUS					 current
		DESCRIPTION			 " -- "
		INDEX						{ topoRRUPACurrentRRUNo,topoRRUPACurrentNo }
		::=  { topoRRUPACurrentTable  1 }


	TopoRRUPACurrentEntry		 ::=  SEQUENCE {
		topoRRUPACurrentRRUNo					Integer32,
		topoRRUPACurrentNo					Integer32,
		topoRRUPACurrentRowStatus					RowStatus,
		topoRRUPACurrentDescription					INTEGER,
		topoRRUPAUpAverageCurrentValue					Integer32,
		topoRRUPADownAverageCurrentValue					Integer32,
		topoRRUPAAverageCurrentValue					Integer32
		}


	topoRRUPACurrentRRUNo		 OBJECT-TYPE
		SYNTAX					 Integer32( 0 .. 191 )
		MAX-ACCESS			 not-accessible
		STATUS					 current
		DESCRIPTION			 " -- "
		::=  { topoRRUPACurrentEntry  1 }


	topoRRUPACurrentNo		 OBJECT-TYPE
		SYNTAX					 Integer32( 0 .. 15 )
		MAX-ACCESS			 not-accessible
		STATUS					 current
		DESCRIPTION			 " -- "
		::=  { topoRRUPACurrentEntry  2 }


	topoRRUPACurrentRowStatus		 OBJECT-TYPE
		SYNTAX					 RowStatus
		MAX-ACCESS			 read-only
		STATUS					 current
		DESCRIPTION			 " -- "
		::=  { topoRRUPACurrentEntry  3 }


	topoRRUPACurrentDescription		 OBJECT-TYPE
		SYNTAX					 INTEGER{ unknown(0),rru342XPara1(1),rru342XPara2(2),rru348XPara1(3),rru348XPara2(4)  }
		MAX-ACCESS			 read-only
		STATUS					 current
		DESCRIPTION			 " -- "
		::=  { topoRRUPACurrentEntry  4 }


	topoRRUPAUpAverageCurrentValue		 OBJECT-TYPE
		SYNTAX					 Integer32( -2147483648 .. 2147483647 )
		MAX-ACCESS			 read-only
		STATUS					 current
		DESCRIPTION			 " -- "
		::=  { topoRRUPACurrentEntry  5 }


	topoRRUPADownAverageCurrentValue		 OBJECT-TYPE
		SYNTAX					 Integer32( -2147483648 .. 2147483647 )
		MAX-ACCESS			 read-only
		STATUS					 current
		DESCRIPTION			 " -- "
		::=  { topoRRUPACurrentEntry  6 }


	topoRRUPAAverageCurrentValue		 OBJECT-TYPE
		SYNTAX					 Integer32( -2147483648 .. 2147483647 )
		MAX-ACCESS			 read-only
		STATUS					 current
		DESCRIPTION			 " -- "
		::=  { topoRRUPACurrentEntry  7 }


	topoRRUULPowerTable		 OBJECT-TYPE
		SYNTAX					 SEQUENCE  OF	 TopoRRUULPowerEntry
		MAX-ACCESS			 not-accessible
		STATUS					 current
		DESCRIPTION			 " -- "
		::=  { remoteRadioUnit  11 }


	topoRRUULPowerEntry		 OBJECT-TYPE
		SYNTAX					 TopoRRUULPowerEntry
		MAX-ACCESS			 not-accessible
		STATUS					 current
		DESCRIPTION			 " -- "
		INDEX						{ topoRRUULPowerRRUNo,topoRRUULPowerRRUPathNo,topoRRUULPowerMode }
		::=  { topoRRUULPowerTable  1 }


	TopoRRUULPowerEntry		 ::=  SEQUENCE {
		topoRRUULPowerRRUNo					Integer32,
		topoRRUULPowerRRUPathNo					Integer32,
		topoRRUULPowerMode					INTEGER,
		topoRRUULPowerRowStatus					RowStatus,
		topoRRUCarrier1ULPowerValue					Integer32Array,
		topoRRUCarrier2ULPowerValue					Integer32Array,
		topoRRUCarrier3ULPowerValue					Integer32Array,
		topoRRUCarrier4ULPowerValue					Integer32Array,
		topoRRUCarrier5ULPowerValue					Integer32Array,
		topoRRUCarrier6ULPowerValue					Integer32Array,
		topoRRUCarrier7ULPowerValue					Integer32Array,
		topoRRUCarrier8ULPowerValue					Integer32Array,
		topoRRUCarrier9ULPowerValue					Integer32Array,
		topoRRUCarrier10ULPowerValue					Integer32Array,
		topoRRUCarrier11ULPowerValue					Integer32Array,
		topoRRUCarrier12ULPowerValue					Integer32Array,
		topoRRUCarrier13ULPowerValue					Integer32Array,
		topoRRUCarrier14ULPowerValue					Integer32Array,
		topoRRUCarrier15ULPowerValue					Integer32Array,
		topoRRUCarrier16ULPowerValue					Integer32Array,
		topoRRUCarrier17ULPowerValue					Integer32Array,
		topoRRUCarrier18ULPowerValue					Integer32Array,
		topoRRUCarrier19ULPowerValue					Integer32Array,
		topoRRUCarrier20ULPowerValue					Integer32Array,
		topoRRUCarrier21ULPowerValue					Integer32Array,
		topoRRUCarrier22ULPowerValue					Integer32Array,
		topoRRUCarrier23ULPowerValue					Integer32Array,
		topoRRUCarrier24ULPowerValue					Integer32Array
		}


	topoRRUULPowerRRUNo		 OBJECT-TYPE
		SYNTAX					 Integer32( 0 .. 191 )
		MAX-ACCESS			 not-accessible
		STATUS					 current
		DESCRIPTION			 " -- "
		::=  { topoRRUULPowerEntry  1 }


	topoRRUULPowerRRUPathNo		 OBJECT-TYPE
		SYNTAX					 Integer32( 0 .. 15 )
		MAX-ACCESS			 not-accessible
		STATUS					 current
		DESCRIPTION			 " -- "
		::=  { topoRRUULPowerEntry  2 }


	topoRRUULPowerMode		 OBJECT-TYPE
		SYNTAX					 INTEGER{ tdsMode(0),tdlMode(1)  }
		MAX-ACCESS			 not-accessible
		STATUS					 current
		DESCRIPTION			 " -- "
		::=  { topoRRUULPowerEntry  3 }


	topoRRUULPowerRowStatus		 OBJECT-TYPE
		SYNTAX					 RowStatus
		MAX-ACCESS			 read-only
		STATUS					 current
		DESCRIPTION			 " -- "
		::=  { topoRRUULPowerEntry  4 }


	topoRRUCarrier1ULPowerValue		 OBJECT-TYPE
		SYNTAX					 Integer32Array
		MAX-ACCESS			 read-only
		STATUS					 current
		DESCRIPTION			 " -- "
		::=  { topoRRUULPowerEntry  5 }


	topoRRUCarrier2ULPowerValue		 OBJECT-TYPE
		SYNTAX					 Integer32Array
		MAX-ACCESS			 read-only
		STATUS					 current
		DESCRIPTION			 " -- "
		::=  { topoRRUULPowerEntry  6 }


	topoRRUCarrier3ULPowerValue		 OBJECT-TYPE
		SYNTAX					 Integer32Array
		MAX-ACCESS			 read-only
		STATUS					 current
		DESCRIPTION			 " -- "
		::=  { topoRRUULPowerEntry  7 }


	topoRRUCarrier4ULPowerValue		 OBJECT-TYPE
		SYNTAX					 Integer32Array
		MAX-ACCESS			 read-only
		STATUS					 current
		DESCRIPTION			 " -- "
		::=  { topoRRUULPowerEntry  8 }


	topoRRUCarrier5ULPowerValue		 OBJECT-TYPE
		SYNTAX					 Integer32Array
		MAX-ACCESS			 read-only
		STATUS					 current
		DESCRIPTION			 " -- "
		::=  { topoRRUULPowerEntry  9 }


	topoRRUCarrier6ULPowerValue		 OBJECT-TYPE
		SYNTAX					 Integer32Array
		MAX-ACCESS			 read-only
		STATUS					 current
		DESCRIPTION			 " -- "
		::=  { topoRRUULPowerEntry  10 }


	topoRRUCarrier7ULPowerValue		 OBJECT-TYPE
		SYNTAX					 Integer32Array
		MAX-ACCESS			 read-only
		STATUS					 current
		DESCRIPTION			 " -- "
		::=  { topoRRUULPowerEntry  11 }


	topoRRUCarrier8ULPowerValue		 OBJECT-TYPE
		SYNTAX					 Integer32Array
		MAX-ACCESS			 read-only
		STATUS					 current
		DESCRIPTION			 " -- "
		::=  { topoRRUULPowerEntry  12 }


	topoRRUCarrier9ULPowerValue		 OBJECT-TYPE
		SYNTAX					 Integer32Array
		MAX-ACCESS			 read-only
		STATUS					 current
		DESCRIPTION			 " -- "
		::=  { topoRRUULPowerEntry  13 }


	topoRRUCarrier10ULPowerValue		 OBJECT-TYPE
		SYNTAX					 Integer32Array
		MAX-ACCESS			 read-only
		STATUS					 current
		DESCRIPTION			 " -- "
		::=  { topoRRUULPowerEntry  14 }


	topoRRUCarrier11ULPowerValue		 OBJECT-TYPE
		SYNTAX					 Integer32Array
		MAX-ACCESS			 read-only
		STATUS					 current
		DESCRIPTION			 " -- "
		::=  { topoRRUULPowerEntry  15 }


	topoRRUCarrier12ULPowerValue		 OBJECT-TYPE
		SYNTAX					 Integer32Array
		MAX-ACCESS			 read-only
		STATUS					 current
		DESCRIPTION			 " -- "
		::=  { topoRRUULPowerEntry  16 }


	topoRRUCarrier13ULPowerValue		 OBJECT-TYPE
		SYNTAX					 Integer32Array
		MAX-ACCESS			 read-only
		STATUS					 current
		DESCRIPTION			 " -- "
		::=  { topoRRUULPowerEntry  17 }


	topoRRUCarrier14ULPowerValue		 OBJECT-TYPE
		SYNTAX					 Integer32Array
		MAX-ACCESS			 read-only
		STATUS					 current
		DESCRIPTION			 " -- "
		::=  { topoRRUULPowerEntry  18 }


	topoRRUCarrier15ULPowerValue		 OBJECT-TYPE
		SYNTAX					 Integer32Array
		MAX-ACCESS			 read-only
		STATUS					 current
		DESCRIPTION			 " -- "
		::=  { topoRRUULPowerEntry  19 }


	topoRRUCarrier16ULPowerValue		 OBJECT-TYPE
		SYNTAX					 Integer32Array
		MAX-ACCESS			 read-only
		STATUS					 current
		DESCRIPTION			 " -- "
		::=  { topoRRUULPowerEntry  20 }


	topoRRUCarrier17ULPowerValue		 OBJECT-TYPE
		SYNTAX					 Integer32Array
		MAX-ACCESS			 read-only
		STATUS					 current
		DESCRIPTION			 " -- "
		::=  { topoRRUULPowerEntry  21 }


	topoRRUCarrier18ULPowerValue		 OBJECT-TYPE
		SYNTAX					 Integer32Array
		MAX-ACCESS			 read-only
		STATUS					 current
		DESCRIPTION			 " -- "
		::=  { topoRRUULPowerEntry  22 }


	topoRRUCarrier19ULPowerValue		 OBJECT-TYPE
		SYNTAX					 Integer32Array
		MAX-ACCESS			 read-only
		STATUS					 current
		DESCRIPTION			 " -- "
		::=  { topoRRUULPowerEntry  23 }


	topoRRUCarrier20ULPowerValue		 OBJECT-TYPE
		SYNTAX					 Integer32Array
		MAX-ACCESS			 read-only
		STATUS					 current
		DESCRIPTION			 " -- "
		::=  { topoRRUULPowerEntry  24 }


	topoRRUCarrier21ULPowerValue		 OBJECT-TYPE
		SYNTAX					 Integer32Array
		MAX-ACCESS			 read-only
		STATUS					 current
		DESCRIPTION			 " -- "
		::=  { topoRRUULPowerEntry  25 }


	topoRRUCarrier22ULPowerValue		 OBJECT-TYPE
		SYNTAX					 Integer32Array
		MAX-ACCESS			 read-only
		STATUS					 current
		DESCRIPTION			 " -- "
		::=  { topoRRUULPowerEntry  26 }


	topoRRUCarrier23ULPowerValue		 OBJECT-TYPE
		SYNTAX					 Integer32Array
		MAX-ACCESS			 read-only
		STATUS					 current
		DESCRIPTION			 " -- "
		::=  { topoRRUULPowerEntry  27 }


	topoRRUCarrier24ULPowerValue		 OBJECT-TYPE
		SYNTAX					 Integer32Array
		MAX-ACCESS			 read-only
		STATUS					 current
		DESCRIPTION			 " -- "
		::=  { topoRRUULPowerEntry  28 }


	remoteHub		 OBJECT IDENTIFIER
		::=  { eNBConfig  10 }


	topologyRHUBTable		 OBJECT-TYPE
		SYNTAX					 SEQUENCE  OF	 TopologyRHUBEntry
		MAX-ACCESS			 not-accessible
		STATUS					 current
		DESCRIPTION			 " -- "
		::=  { remoteHub  1 }


	topologyRHUBEntry		 OBJECT-TYPE
		SYNTAX					 TopologyRHUBEntry
		MAX-ACCESS			 not-accessible
		STATUS					 current
		DESCRIPTION			 " -- "
		INDEX						{ topoRHUBNo }
		::=  { topologyRHUBTable  1 }


	TopologyRHUBEntry		 ::=  SEQUENCE {
		topoRHUBNo					Integer32,
		topoRHUBRowStatus					RowStatus,
		topoRHUBLocation					DisplayString,
		topoRHUBMacAddr					DisplayString,
		topoRHUBAccessRackNo					Integer32,
		topoRHUBAccessShelfNo					Integer32,
		topoRHUBAccessSlotNo					Integer32,
		topoRHUBAccessBoardType					INTEGER,
		topoRHUBOfp1AccessOfpPortNo					Integer32,
		topoRHUBOfp1AccessLinePosition					Integer32,
		topoRHUBAccessUlTimeDelay					Unsigned32,
		topoRHUBAccessDlTimeDelay					Unsigned32,
		topoRHUBIsNetMatched					INTEGER,
		topoRHUBMaxTimeDelayCompensation					Unsigned32,
		topoRHUBSoftwareVersion					DisplayString,
		topoRHUBFirmwareVersion					DisplayString,
		topoRHUBAccessPhase					INTEGER,
		topoRHUBClockState					INTEGER,
		topoRHUBResetTrigger					INTEGER,
		topoRHUBNextResetTimer					Unsigned32,
		topoRHUBSystemTime					DateAndTime,
		topoRHUBOfpWorkMode					INTEGER,
		topoRHUBLogDestination					DisplayString,
		topoRHUBLogFileType					INTEGER,
		topoRHUBRemoteResetNextRHUBTrigger					INTEGER,
		topoRHUBRemoteResetNextRHUBTimer					Unsigned32,
		topoRHUBFaultStatus					INTEGER,
		topoRHUBUnavaiableReason					BITS,
		topoRHUBUUpTime					DateAndTime,
		topoRHUBFiberFaultReason					BITS,
		topoRHUBDLMaxTimeDelayCompensation					Unsigned32,
		topoRHUBULMaxTimeDelayCompensation					Unsigned32,
		topoRHUBTemperature					Integer32,
		topoRHUBOfp2AccessOfpPortNo					Integer32,
		topoRHUBOfp2AccessLinePosition					Integer32,
		topoRHUBUpLinkSlaveOfpPortNo					Integer32,
		topoRHUBMainOfpNo					Integer32,
		topoRHUBOfp3AccessOfpPortNo					Integer32,
		topoRHUBOfp3AccessLinePosition					Integer32,
		topoRHUBOfp4AccessOfpPortNo					Integer32,
		topoRHUBOfp4AccessLinePosition					Integer32,
		topoRHUBGsmCellInputPwr					Integer32,
		topoRHUBGsmCellOutputPwr					Integer32,
		topoRHUBAutTMSwitch					INTEGER
		}


	topoRHUBNo		 OBJECT-TYPE
		SYNTAX					 Integer32( 200 .. 254 )
		MAX-ACCESS			 not-accessible
		STATUS					 current
		DESCRIPTION			 " -- "
		::=  { topologyRHUBEntry  1 }


	topoRHUBRowStatus		 OBJECT-TYPE
		SYNTAX					 RowStatus
		MAX-ACCESS			 read-only
		STATUS					 current
		DESCRIPTION			 " -- "
		::=  { topologyRHUBEntry  2 }


	topoRHUBLocation		 OBJECT-TYPE
		SYNTAX					 DisplayString( SIZE ( 1 .. 255 ) )
		MAX-ACCESS			 read-only
		STATUS					 current
		DESCRIPTION			 " -- "
		::=  { topologyRHUBEntry  3 }


	topoRHUBMacAddr		 OBJECT-TYPE
		SYNTAX					 DisplayString( SIZE ( 12 .. 12 ) )
		MAX-ACCESS			 read-only
		STATUS					 current
		DESCRIPTION			 " -- "
		::=  { topologyRHUBEntry  4 }


	topoRHUBAccessRackNo		 OBJECT-TYPE
		SYNTAX					 Integer32( 0 .. 0|-1 )
		MAX-ACCESS			 read-only
		STATUS					 current
		DESCRIPTION			 " -- "
		::=  { topologyRHUBEntry  5 }


	topoRHUBAccessShelfNo		 OBJECT-TYPE
		SYNTAX					 Integer32( 0 .. 0|-1 )
		MAX-ACCESS			 read-only
		STATUS					 current
		DESCRIPTION			 " -- "
		::=  { topologyRHUBEntry  6 }


	topoRHUBAccessSlotNo		 OBJECT-TYPE
		SYNTAX					 Integer32( 1 .. 7|-1 )
		MAX-ACCESS			 read-only
		STATUS					 current
		DESCRIPTION			 " -- "
		::=  { topologyRHUBEntry  7 }


	topoRHUBAccessBoardType		 OBJECT-TYPE
		SYNTAX					 INTEGER{ unknown(0),ccu(54),ceu(56),bbu(58),iiu(66),bcu(67),biu(68),accu(70),abbut(71),abbuf(72),eiuDof(75),scta(97),bpia(98),bpoa(99),bpoe(109),tdru311B(113),tdru312(114),bpof(128),sctd(141),mmba(142),bpog(143),bpoh(177),scte(178),sctf(240),bpoi(241)  }
		MAX-ACCESS			 read-only
		STATUS					 current
		DESCRIPTION			 " -- "
		::=  { topologyRHUBEntry  8 }


	topoRHUBOfp1AccessOfpPortNo		 OBJECT-TYPE
		SYNTAX					 Integer32( 0 .. 5|-1 )
		MAX-ACCESS			 read-only
		STATUS					 current
		DESCRIPTION			 " -- "
		::=  { topologyRHUBEntry  9 }


	topoRHUBOfp1AccessLinePosition		 OBJECT-TYPE
		SYNTAX					 Integer32( 1 .. 6|-1 )
		MAX-ACCESS			 read-only
		STATUS					 current
		DESCRIPTION			 " -- "
		::=  { topologyRHUBEntry  10 }


	topoRHUBAccessUlTimeDelay		 OBJECT-TYPE
		SYNTAX					 Unsigned32( 0 .. 4294967295 )
		MAX-ACCESS			 read-only
		STATUS					 current
		DESCRIPTION			 " -- "
		::=  { topologyRHUBEntry  11 }


	topoRHUBAccessDlTimeDelay		 OBJECT-TYPE
		SYNTAX					 Unsigned32( 0 .. 4294967295 )
		MAX-ACCESS			 read-only
		STATUS					 current
		DESCRIPTION			 " -- "
		::=  { topologyRHUBEntry  12 }


	topoRHUBIsNetMatched		 OBJECT-TYPE
		SYNTAX					 INTEGER{ matched(0),unmatched(1)  }
		MAX-ACCESS			 read-only
		STATUS					 current
		DESCRIPTION			 " -- "
		::=  { topologyRHUBEntry  13 }


	topoRHUBMaxTimeDelayCompensation		 OBJECT-TYPE
		SYNTAX					 Unsigned32( 0 .. 4294967295 )
		MAX-ACCESS			 read-only
		STATUS					 current
		DESCRIPTION			 " -- "
		::=  { topologyRHUBEntry  14 }


	topoRHUBSoftwareVersion		 OBJECT-TYPE
		SYNTAX					 DisplayString( SIZE ( 40 .. 40 ) )
		MAX-ACCESS			 read-only
		STATUS					 current
		DESCRIPTION			 " -- "
		::=  { topologyRHUBEntry  15 }


	topoRHUBFirmwareVersion		 OBJECT-TYPE
		SYNTAX					 DisplayString( SIZE ( 40 .. 40 ) )
		MAX-ACCESS			 read-only
		STATUS					 current
		DESCRIPTION			 " -- "
		::=  { topologyRHUBEntry  16 }


	topoRHUBAccessPhase		 OBJECT-TYPE
		SYNTAX					 INTEGER{ unknown(0),broadcastAccess(1),pathSetup(2),versionUpdate(3),timeDelayMeasure(4),antConfig(5),available(6)  }
		MAX-ACCESS			 read-only
		STATUS					 current
		DESCRIPTION			 " -- "
		::=  { topologyRHUBEntry  17 }


	topoRHUBClockState		 OBJECT-TYPE
		SYNTAX					 INTEGER{ unknown(-1),syn(0),asyn(1)  }
		MAX-ACCESS			 read-only
		STATUS					 current
		DESCRIPTION			 " -- "
		::=  { topologyRHUBEntry  18 }


	topoRHUBResetTrigger		 OBJECT-TYPE
		SYNTAX					 INTEGER{ notEffectNextRHUB(0),effectNextRHUB(1),bbuCmdCode(2),remoteResetRHUB(11)  }
		MAX-ACCESS			 read-write
		STATUS					 current
		DESCRIPTION			 " -- "
		::=  { topologyRHUBEntry  19 }


	topoRHUBNextResetTimer		 OBJECT-TYPE
		SYNTAX					 Unsigned32( 0 .. 65535 )
		MAX-ACCESS			 read-write
		STATUS					 current
		DESCRIPTION			 " -- "
		::=  { topologyRHUBEntry  20 }


	topoRHUBSystemTime		 OBJECT-TYPE
		SYNTAX					 DateAndTime
		MAX-ACCESS			 read-only
		STATUS					 current
		DESCRIPTION			 " -- "
		::=  { topologyRHUBEntry  21 }


	topoRHUBOfpWorkMode		 OBJECT-TYPE
		SYNTAX					 INTEGER{ unknown(-1),normal(1),lined(2),shared(4),linedshared(5)  }
		MAX-ACCESS			 read-only
		STATUS					 current
		DESCRIPTION			 " -- "
		::=  { topologyRHUBEntry  22 }


	topoRHUBLogDestination		 OBJECT-TYPE
		SYNTAX					 DisplayString( SIZE ( 1 .. 150 ) )
		MAX-ACCESS			 read-write
		STATUS					 current
		DESCRIPTION			 " -- "
		::=  { topologyRHUBEntry  23 }


	topoRHUBLogFileType		 OBJECT-TYPE
		SYNTAX					 INTEGER{ alarm(0),user(1),system(2),all(3),operate(4)  }
		MAX-ACCESS			 read-write
		STATUS					 current
		DESCRIPTION			 " -- "
		::=  { topologyRHUBEntry  24 }


	topoRHUBRemoteResetNextRHUBTrigger		 OBJECT-TYPE
		SYNTAX					 INTEGER{ on(0)  }
		MAX-ACCESS			 read-write
		STATUS					 current
		DESCRIPTION			 " -- "
		::=  { topologyRHUBEntry  25 }


	topoRHUBRemoteResetNextRHUBTimer		 OBJECT-TYPE
		SYNTAX					 Unsigned32( 500 .. 65535 )
		MAX-ACCESS			 read-write
		STATUS					 current
		DESCRIPTION			 " -- "
		::=  { topologyRHUBEntry  26 }


	topoRHUBFaultStatus		 OBJECT-TYPE
		SYNTAX					 INTEGER{ normal(0),fault(1)  }
		MAX-ACCESS			 read-only
		STATUS					 current
		DESCRIPTION			 " -- "
		::=  { topologyRHUBEntry  27 }


	topoRHUBUnavaiableReason		 OBJECT-TYPE
		SYNTAX					 BITS{ rHUBMasterOfpAbnormalBBU(0),rHUBSlaveOfpAbnormalBBU(1),rHUBLocalCrystaloidUnlock(2),rHUBSlaveOfpAbnormalRHUB(3),rHUBOfpModuleMixedUse(4)  }
		MAX-ACCESS			 read-only
		STATUS					 current
		DESCRIPTION			 " -- "
		::=  { topologyRHUBEntry  28 }


	topoRHUBUUpTime		 OBJECT-TYPE
		SYNTAX					 DateAndTime
		MAX-ACCESS			 read-only
		STATUS					 current
		DESCRIPTION			 " -- "
		::=  { topologyRHUBEntry  29 }


	topoRHUBFiberFaultReason		 OBJECT-TYPE
		SYNTAX					 BITS{ rHUBMasterOfpAbnormalBBU(0),rHUBSlaveOfpAbnormalBBU(1),rHUBSlaveOfpAbnormalRHUB(2)  }
		MAX-ACCESS			 read-only
		STATUS					 current
		DESCRIPTION			 " -- "
		::=  { topologyRHUBEntry  30 }


	topoRHUBDLMaxTimeDelayCompensation		 OBJECT-TYPE
		SYNTAX					 Unsigned32( 0 .. 4294967295 )
		MAX-ACCESS			 read-only
		STATUS					 current
		DESCRIPTION			 " -- "
		::=  { topologyRHUBEntry  31 }


	topoRHUBULMaxTimeDelayCompensation		 OBJECT-TYPE
		SYNTAX					 Unsigned32( 0 .. 4294967295 )
		MAX-ACCESS			 read-only
		STATUS					 current
		DESCRIPTION			 " -- "
		::=  { topologyRHUBEntry  32 }


	topoRHUBTemperature		 OBJECT-TYPE
		SYNTAX					 Integer32( -2147483648 .. 2147483647 )
		MAX-ACCESS			 read-only
		STATUS					 current
		DESCRIPTION			 " -- "
		::=  { topologyRHUBEntry  33 }


	topoRHUBOfp2AccessOfpPortNo		 OBJECT-TYPE
		SYNTAX					 Integer32( 0 .. 5|-1 )
		MAX-ACCESS			 read-only
		STATUS					 current
		DESCRIPTION			 " -- "
		::=  { topologyRHUBEntry  41 }


	topoRHUBOfp2AccessLinePosition		 OBJECT-TYPE
		SYNTAX					 Integer32( 1 .. 6|-1 )
		MAX-ACCESS			 read-only
		STATUS					 current
		DESCRIPTION			 " -- "
		::=  { topologyRHUBEntry  42 }


	topoRHUBUpLinkSlaveOfpPortNo		 OBJECT-TYPE
		SYNTAX					 Integer32( 0 .. 5|-1 )
		MAX-ACCESS			 read-only
		STATUS					 current
		DESCRIPTION			 " -- "
		::=  { topologyRHUBEntry  43 }


	topoRHUBMainOfpNo		 OBJECT-TYPE
		SYNTAX					 Integer32( 0 .. 5|-1 )
		MAX-ACCESS			 read-only
		STATUS					 current
		DESCRIPTION			 " -- "
		::=  { topologyRHUBEntry  44 }


	topoRHUBOfp3AccessOfpPortNo		 OBJECT-TYPE
		SYNTAX					 Integer32( 0 .. 5|-1 )
		MAX-ACCESS			 read-only
		STATUS					 current
		DESCRIPTION			 " -- "
		::=  { topologyRHUBEntry  45 }


	topoRHUBOfp3AccessLinePosition		 OBJECT-TYPE
		SYNTAX					 Integer32( 1 .. 6|-1 )
		MAX-ACCESS			 read-only
		STATUS					 current
		DESCRIPTION			 " -- "
		::=  { topologyRHUBEntry  46 }


	topoRHUBOfp4AccessOfpPortNo		 OBJECT-TYPE
		SYNTAX					 Integer32( 0 .. 5|-1 )
		MAX-ACCESS			 read-only
		STATUS					 current
		DESCRIPTION			 " -- "
		::=  { topologyRHUBEntry  47 }


	topoRHUBOfp4AccessLinePosition		 OBJECT-TYPE
		SYNTAX					 Integer32( 1 .. 6|-1 )
		MAX-ACCESS			 read-only
		STATUS					 current
		DESCRIPTION			 " -- "
		::=  { topologyRHUBEntry  48 }


	topoRHUBGsmCellInputPwr		 OBJECT-TYPE
		SYNTAX					 Integer32( 0 )
		MAX-ACCESS			 read-only
		STATUS					 current
		DESCRIPTION			 " -- "
		::=  { topologyRHUBEntry  50 }


	topoRHUBGsmCellOutputPwr		 OBJECT-TYPE
		SYNTAX					 Integer32( 0 .. 550 )
		MAX-ACCESS			 read-only
		STATUS					 current
		DESCRIPTION			 " -- "
		::=  { topologyRHUBEntry  51 }


	topoRHUBAutTMSwitch		 OBJECT-TYPE
		SYNTAX					 INTEGER{ off(0),on(1)  }
		MAX-ACCESS			 read-write
		STATUS					 current
		DESCRIPTION			 " -- "
		::=  { topologyRHUBEntry  53 }


	rhubOpticalTransceiverTable		 OBJECT-TYPE
		SYNTAX					 SEQUENCE  OF	 RhubOpticalTransceiverEntry
		MAX-ACCESS			 not-accessible
		STATUS					 current
		DESCRIPTION			 " -- "
		::=  { remoteHub  2 }


	rhubOpticalTransceiverEntry		 OBJECT-TYPE
		SYNTAX					 RhubOpticalTransceiverEntry
		MAX-ACCESS			 not-accessible
		STATUS					 current
		DESCRIPTION			 " -- "
		INDEX						{ rhubOptTransrhubNo,rhubOptTransIndex }
		::=  { rhubOpticalTransceiverTable  1 }


	RhubOpticalTransceiverEntry		 ::=  SEQUENCE {
		rhubOptTransrhubNo					Integer32,
		rhubOptTransIndex					INTEGER,
		rhubOptTransRowStatus					RowStatus,
		rhubOptTransTemperature					Integer32,
		rhubOptTransVcc					Integer32,
		rhubOptTransBias					Integer32,
		rhubOptTransTxPower					Integer32,
		rhubOptTransRxPower					Integer32,
		rhubOptTransStandStatus					INTEGER,
		rhubOptTransVendorName					DisplayString,
		rhubOptTransS9umKmLen					Integer32,
		rhubOptTransS9um100MLen					Integer32,
		rhubOptTransM50um10MLen					Integer32,
		rhubOptTransM625um10MLen					Integer32,
		rhubOptTransBitRate					Integer32,
		rhubOptTransFpgaStatus					INTEGER
		}


	rhubOptTransrhubNo		 OBJECT-TYPE
		SYNTAX					 Integer32( 200 .. 254 )
		MAX-ACCESS			 not-accessible
		STATUS					 current
		DESCRIPTION			 " -- "
		::=  { rhubOpticalTransceiverEntry  1 }


	rhubOptTransIndex		 OBJECT-TYPE
		SYNTAX					 INTEGER{ ofp1(0),ofp2(1),ofp3(2),ofp4(3)  }
		MAX-ACCESS			 not-accessible
		STATUS					 current
		DESCRIPTION			 " -- "
		::=  { rhubOpticalTransceiverEntry  2 }


	rhubOptTransRowStatus		 OBJECT-TYPE
		SYNTAX					 RowStatus
		MAX-ACCESS			 read-only
		STATUS					 current
		DESCRIPTION			 " -- "
		::=  { rhubOpticalTransceiverEntry  3 }


	rhubOptTransTemperature		 OBJECT-TYPE
		SYNTAX					 Integer32( -128 .. 127 )
		MAX-ACCESS			 read-only
		STATUS					 current
		DESCRIPTION			 " -- "
		::=  { rhubOpticalTransceiverEntry  4 }


	rhubOptTransVcc		 OBJECT-TYPE
		SYNTAX					 Integer32( 0 .. 65535 )
		MAX-ACCESS			 read-only
		STATUS					 current
		DESCRIPTION			 " -- "
		::=  { rhubOpticalTransceiverEntry  5 }


	rhubOptTransBias		 OBJECT-TYPE
		SYNTAX					 Integer32( 0 .. 65535 )
		MAX-ACCESS			 read-only
		STATUS					 current
		DESCRIPTION			 " -- "
		::=  { rhubOpticalTransceiverEntry  6 }


	rhubOptTransTxPower		 OBJECT-TYPE
		SYNTAX					 Integer32( -2147483648 .. 2147483647 )
		MAX-ACCESS			 read-only
		STATUS					 current
		DESCRIPTION			 " -- "
		::=  { rhubOpticalTransceiverEntry  7 }


	rhubOptTransRxPower		 OBJECT-TYPE
		SYNTAX					 Integer32( -2147483648 .. 2147483647 )
		MAX-ACCESS			 read-only
		STATUS					 current
		DESCRIPTION			 " -- "
		::=  { rhubOpticalTransceiverEntry  8 }


	rhubOptTransStandStatus		 OBJECT-TYPE
		SYNTAX					 INTEGER{ notExisted(0),existed(1)  }
		MAX-ACCESS			 read-only
		STATUS					 current
		DESCRIPTION			 " -- "
		::=  { rhubOpticalTransceiverEntry  9 }


	rhubOptTransVendorName		 OBJECT-TYPE
		SYNTAX					 DisplayString( SIZE ( 0 .. 255 ) )
		MAX-ACCESS			 read-only
		STATUS					 current
		DESCRIPTION			 " -- "
		::=  { rhubOpticalTransceiverEntry  10 }


	rhubOptTransS9umKmLen		 OBJECT-TYPE
		SYNTAX					 Integer32( 0|1 .. 255 )
		MAX-ACCESS			 read-only
		STATUS					 current
		DESCRIPTION			 " -- "
		::=  { rhubOpticalTransceiverEntry  11 }


	rhubOptTransS9um100MLen		 OBJECT-TYPE
		SYNTAX					 Integer32( 0|1 .. 255 )
		MAX-ACCESS			 read-only
		STATUS					 current
		DESCRIPTION			 " -- "
		::=  { rhubOpticalTransceiverEntry  12 }


	rhubOptTransM50um10MLen		 OBJECT-TYPE
		SYNTAX					 Integer32( 0|1 .. 255 )
		MAX-ACCESS			 read-only
		STATUS					 current
		DESCRIPTION			 " -- "
		::=  { rhubOpticalTransceiverEntry  13 }


	rhubOptTransM625um10MLen		 OBJECT-TYPE
		SYNTAX					 Integer32( 0|1 .. 255 )
		MAX-ACCESS			 read-only
		STATUS					 current
		DESCRIPTION			 " -- "
		::=  { rhubOpticalTransceiverEntry  14 }


	rhubOptTransBitRate		 OBJECT-TYPE
		SYNTAX					 Integer32( -2147483648 .. 2147483647 )
		MAX-ACCESS			 read-only
		STATUS					 current
		DESCRIPTION			 " -- "
		::=  { rhubOpticalTransceiverEntry  15 }


	rhubOptTransFpgaStatus		 OBJECT-TYPE
		SYNTAX					 INTEGER{ syn(0),asyn(1)  }
		MAX-ACCESS			 read-only
		STATUS					 current
		DESCRIPTION			 " -- "
		::=  { rhubOpticalTransceiverEntry  16 }


	rhubEtherTable		 OBJECT-TYPE
		SYNTAX					 SEQUENCE  OF	 RhubEtherEntry
		MAX-ACCESS			 not-accessible
		STATUS					 current
		DESCRIPTION			 " -- "
		::=  { remoteHub  3 }


	rhubEtherEntry		 OBJECT-TYPE
		SYNTAX					 RhubEtherEntry
		MAX-ACCESS			 not-accessible
		STATUS					 current
		DESCRIPTION			 " -- "
		INDEX						{ rhubEtherRHUBNo,rhubEtherIndex }
		::=  { rhubEtherTable  1 }


	RhubEtherEntry		 ::=  SEQUENCE {
		rhubEtherRHUBNo					Integer32,
		rhubEtherIndex					INTEGER,
		rhubEtherRowStatus					RowStatus,
		rhubEtherPortSwitch					INTEGER,
		rhubEtherStatus					INTEGER,
		rhubEtherOutputVoltage					Integer32,
		rhubEtherOutputCurrent					Integer32,
		rhubEthActurlSpeed					Integer32,
		rhubEthFpgaBer					Unsigned32
		}


	rhubEtherRHUBNo		 OBJECT-TYPE
		SYNTAX					 Integer32( 200 .. 254 )
		MAX-ACCESS			 not-accessible
		STATUS					 current
		DESCRIPTION			 " -- "
		::=  { rhubEtherEntry  1 }


	rhubEtherIndex		 OBJECT-TYPE
		SYNTAX					 INTEGER{ ire1(0),ire2(1),ire3(2),ire4(3),ire5(4),ire6(5),ire7(6),ire8(7)  }
		MAX-ACCESS			 not-accessible
		STATUS					 current
		DESCRIPTION			 " -- "
		::=  { rhubEtherEntry  2 }


	rhubEtherRowStatus		 OBJECT-TYPE
		SYNTAX					 RowStatus
		MAX-ACCESS			 read-only
		STATUS					 current
		DESCRIPTION			 " -- "
		::=  { rhubEtherEntry  3 }


	rhubEtherPortSwitch		 OBJECT-TYPE
		SYNTAX					 INTEGER{ off(0),on(1)  }
		MAX-ACCESS			 read-write
		STATUS					 current
		DESCRIPTION			 " -- "
		::=  { rhubEtherEntry  4 }


	rhubEtherStatus		 OBJECT-TYPE
		SYNTAX					 INTEGER{ down(0),up(1)  }
		MAX-ACCESS			 read-only
		STATUS					 current
		DESCRIPTION			 " -- "
		::=  { rhubEtherEntry  5 }


	rhubEtherOutputVoltage		 OBJECT-TYPE
		SYNTAX					 Integer32( 400 .. 540 )
		MAX-ACCESS			 read-only
		STATUS					 current
		DESCRIPTION			 " -- "
		::=  { rhubEtherEntry  6 }


	rhubEtherOutputCurrent		 OBJECT-TYPE
		SYNTAX					 Integer32( 0 .. 600 )
		MAX-ACCESS			 read-only
		STATUS					 current
		DESCRIPTION			 " -- "
		::=  { rhubEtherEntry  7 }


	rhubEthActurlSpeed		 OBJECT-TYPE
		SYNTAX					 Integer32( -2147483648 .. 2147483647 )
		MAX-ACCESS			 read-only
		STATUS					 current
		DESCRIPTION			 " -- "
		::=  { rhubEtherEntry  8 }


	rhubEthFpgaBer		 OBJECT-TYPE
		SYNTAX					 Unsigned32( 0 .. 4294967295 )
		MAX-ACCESS			 read-only
		STATUS					 current
		DESCRIPTION			 " -- "
		::=  { rhubEtherEntry  9 }


	networkElementLayoutPlan		 OBJECT IDENTIFIER
		::=  { eNB  7 }


	baseInfo		 OBJECT IDENTIFIER
		::=  { networkElementLayoutPlan  1 }


	rruBaseInfo		 OBJECT IDENTIFIER
		::=  { baseInfo  1 }


	rruTypeTable		 OBJECT-TYPE
		SYNTAX					 SEQUENCE  OF	 RruTypeEntry
		MAX-ACCESS			 not-accessible
		STATUS					 current
		DESCRIPTION			 " -- "
		::=  { rruBaseInfo  1 }


	rruTypeEntry		 OBJECT-TYPE
		SYNTAX					 RruTypeEntry
		MAX-ACCESS			 not-accessible
		STATUS					 current
		DESCRIPTION			 " -- "
		INDEX						{ rruTypeManufacturerIndex,rruTypeIndex }
		::=  { rruTypeTable  1 }


	RruTypeEntry		 ::=  SEQUENCE {
		rruTypeManufacturerIndex					INTEGER,
		rruTypeIndex					Integer32,
		rruTypeRowStatus					RowStatus,
		rruTypeName					DisplayString,
		rruTypeMaxAntPathNum					Integer32,
		rruTypeMaxTxPower					Integer32,
		rruTypeBandWidth					Unsigned32,
		rruTypeFiberLength					BITS,
		rruTypeIrCompressMode					BITS,
		rruTypeSupportCellWorkMode					BITS,
		rruTypeFamilyName					DisplayString
		}


	rruTypeManufacturerIndex		 OBJECT-TYPE
		SYNTAX					 INTEGER{ erisson(2),datang(4),dingqiao(6),putian(8),zhongxing(10)  }
		MAX-ACCESS			 read-create
		STATUS					 current
		DESCRIPTION			 " -- "
		::=  { rruTypeEntry  1 }


	rruTypeIndex		 OBJECT-TYPE
		SYNTAX					 Integer32( 0 .. 255 )
		MAX-ACCESS			 read-create
		STATUS					 current
		DESCRIPTION			 " -- "
		::=  { rruTypeEntry  2 }


	rruTypeRowStatus		 OBJECT-TYPE
		SYNTAX					 RowStatus
		MAX-ACCESS			 read-create
		STATUS					 current
		DESCRIPTION			 " -- "
		::=  { rruTypeEntry  3 }


	rruTypeName		 OBJECT-TYPE
		SYNTAX					 DisplayString( SIZE ( 1 .. 100 ) )
		MAX-ACCESS			 read-create
		STATUS					 current
		DESCRIPTION			 " -- "
		::=  { rruTypeEntry  4 }


	rruTypeMaxAntPathNum		 OBJECT-TYPE
		SYNTAX					 Integer32( 1 .. 8 )
		MAX-ACCESS			 read-create
		STATUS					 current
		DESCRIPTION			 " -- "
		::=  { rruTypeEntry  5 }


	rruTypeMaxTxPower		 OBJECT-TYPE
		SYNTAX					 Integer32( -2147483648 .. 2147483647 )
		MAX-ACCESS			 read-create
		STATUS					 current
		DESCRIPTION			 " -- "
		::=  { rruTypeEntry  6 }


	rruTypeBandWidth		 OBJECT-TYPE
		SYNTAX					 Unsigned32( 0 .. 255 )
		MAX-ACCESS			 read-create
		STATUS					 current
		DESCRIPTION			 " -- "
		::=  { rruTypeEntry  7 }


	rruTypeFiberLength		 OBJECT-TYPE
		SYNTAX					 BITS{ ten(0),twenty(1),forty(2)  }
		MAX-ACCESS			 read-create
		STATUS					 current
		DESCRIPTION			 " -- "
		::=  { rruTypeEntry  8 }


	rruTypeIrCompressMode		 OBJECT-TYPE
		SYNTAX					 BITS{ notCompress(0),compress(1)  }
		MAX-ACCESS			 read-create
		STATUS					 current
		DESCRIPTION			 " -- "
		::=  { rruTypeEntry  9 }


	rruTypeSupportCellWorkMode		 OBJECT-TYPE
		SYNTAX					 BITS{ lte(0),td(1),fdd(2)  }
		MAX-ACCESS			 read-create
		STATUS					 current
		DESCRIPTION			 " -- "
		::=  { rruTypeEntry  10 }


	rruTypeFamilyName		 OBJECT-TYPE
		SYNTAX					 DisplayString( SIZE ( 1 .. 100 ) )
		MAX-ACCESS			 read-create
		STATUS					 current
		DESCRIPTION			 " -- "
		::=  { rruTypeEntry  11 }


	rruTypePortTable		 OBJECT-TYPE
		SYNTAX					 SEQUENCE  OF	 RruTypePortEntry
		MAX-ACCESS			 not-accessible
		STATUS					 current
		DESCRIPTION			 " -- "
		::=  { rruBaseInfo  2 }


	rruTypePortEntry		 OBJECT-TYPE
		SYNTAX					 RruTypePortEntry
		MAX-ACCESS			 not-accessible
		STATUS					 current
		DESCRIPTION			 " -- "
		INDEX						{ rruTypePortManufacturerIndex,rruTypePortIndex,rruTypePortNo }
		::=  { rruTypePortTable  1 }


	RruTypePortEntry		 ::=  SEQUENCE {
		rruTypePortManufacturerIndex					INTEGER,
		rruTypePortIndex					Integer32,
		rruTypePortNo					Integer32,
		rruTypePortRowStatus					RowStatus,
		rruTypePortPathNo					Integer32,
		rruTypePortSupportFreqBand					BITS,
		rruTypePortSupportFreqBandWidth					Unsigned32,
		rruTypePortSupportAbandTdsCarrierNum					Unsigned32,
		rruTypePortSupportFBandTdsCarrierNum					Unsigned32,
		rruTypePortCalAIqTxNom					Integer32,
		rruTypePortCalAIqRxNom					Integer32,
		rruTypePortCalPoutTxNom					Integer32,
		rruTypePortCalPinRxNom					Integer32,
		rruTypePortAntMaxPower					Integer32
		}


	rruTypePortManufacturerIndex		 OBJECT-TYPE
		SYNTAX					 INTEGER{ erisson(2),datang(4),dingqiao(6),putian(8),zhongxing(10)  }
		MAX-ACCESS			 read-create
		STATUS					 current
		DESCRIPTION			 " -- "
		::=  { rruTypePortEntry  1 }


	rruTypePortIndex		 OBJECT-TYPE
		SYNTAX					 Integer32( 0 .. 255 )
		MAX-ACCESS			 read-create
		STATUS					 current
		DESCRIPTION			 " -- "
		::=  { rruTypePortEntry  2 }


	rruTypePortNo		 OBJECT-TYPE
		SYNTAX					 Integer32( 1 .. 16 )
		MAX-ACCESS			 read-create
		STATUS					 current
		DESCRIPTION			 " -- "
		::=  { rruTypePortEntry  3 }


	rruTypePortRowStatus		 OBJECT-TYPE
		SYNTAX					 RowStatus
		MAX-ACCESS			 read-create
		STATUS					 current
		DESCRIPTION			 " -- "
		::=  { rruTypePortEntry  4 }


	rruTypePortPathNo		 OBJECT-TYPE
		SYNTAX					 Integer32( 1 .. 8 )
		MAX-ACCESS			 read-create
		STATUS					 current
		DESCRIPTION			 " -- "
		::=  { rruTypePortEntry  5 }


	rruTypePortSupportFreqBand		 OBJECT-TYPE
		SYNTAX					 BITS{ a(0),d(1),e(2),f(3),dl(4),v(5),b41(6),t(7),b03(8),b01(9),b44(10)  }
		MAX-ACCESS			 read-create
		STATUS					 current
		DESCRIPTION			 " -- "
		::=  { rruTypePortEntry  6 }


	rruTypePortSupportFreqBandWidth		 OBJECT-TYPE
		SYNTAX					 Unsigned32( 0 .. 255 )
		MAX-ACCESS			 read-create
		STATUS					 current
		DESCRIPTION			 " -- "
		::=  { rruTypePortEntry  7 }


	rruTypePortSupportAbandTdsCarrierNum		 OBJECT-TYPE
		SYNTAX					 Unsigned32( 0 .. 255 )
		MAX-ACCESS			 read-create
		STATUS					 current
		DESCRIPTION			 " -- "
		::=  { rruTypePortEntry  8 }


	rruTypePortSupportFBandTdsCarrierNum		 OBJECT-TYPE
		SYNTAX					 Unsigned32( 0 .. 255 )
		MAX-ACCESS			 read-create
		STATUS					 current
		DESCRIPTION			 " -- "
		::=  { rruTypePortEntry  9 }


	rruTypePortCalAIqTxNom		 OBJECT-TYPE
		SYNTAX					 Integer32( -2147483648 .. 2147483647 )
		MAX-ACCESS			 read-create
		STATUS					 current
		DESCRIPTION			 " -- "
		::=  { rruTypePortEntry  10 }


	rruTypePortCalAIqRxNom		 OBJECT-TYPE
		SYNTAX					 Integer32( -2147483648 .. 2147483647 )
		MAX-ACCESS			 read-create
		STATUS					 current
		DESCRIPTION			 " -- "
		::=  { rruTypePortEntry  11 }


	rruTypePortCalPoutTxNom		 OBJECT-TYPE
		SYNTAX					 Integer32( -2147483648 .. 2147483647 )
		MAX-ACCESS			 read-create
		STATUS					 current
		DESCRIPTION			 " -- "
		::=  { rruTypePortEntry  12 }


	rruTypePortCalPinRxNom		 OBJECT-TYPE
		SYNTAX					 Integer32( -2147483648 .. 2147483647 )
		MAX-ACCESS			 read-create
		STATUS					 current
		DESCRIPTION			 " -- "
		::=  { rruTypePortEntry  13 }


	rruTypePortAntMaxPower		 OBJECT-TYPE
		SYNTAX					 Integer32( -2147483648 .. 2147483647 )
		MAX-ACCESS			 read-create
		STATUS					 current
		DESCRIPTION			 " -- "
		::=  { rruTypePortEntry  14 }


	antennaBaseInfo		 OBJECT IDENTIFIER
		::=  { baseInfo  2 }


	antennaArrayTypeTable		 OBJECT-TYPE
		SYNTAX					 SEQUENCE  OF	 AntennaArrayTypeEntry
		MAX-ACCESS			 not-accessible
		STATUS					 current
		DESCRIPTION			 " -- "
		::=  { antennaBaseInfo  1 }


	antennaArrayTypeEntry		 OBJECT-TYPE
		SYNTAX					 AntennaArrayTypeEntry
		MAX-ACCESS			 not-accessible
		STATUS					 current
		DESCRIPTION			 " -- "
		INDEX						{ antArrayVendor,antArrayIndex }
		::=  { antennaArrayTypeTable  1 }


	AntennaArrayTypeEntry		 ::=  SEQUENCE {
		antArrayVendor					Integer32,
		antArrayIndex					Integer32,
		antArrayRowStatus					RowStatus,
		antArrayModelName					DisplayString,
		antArrayType					INTEGER,
		antArrayNum					Integer32,
		antArrayDistance					Integer32
		}


	antArrayVendor		 OBJECT-TYPE
		SYNTAX					 Integer32( 0 .. 255 )
		MAX-ACCESS			 read-create
		STATUS					 current
		DESCRIPTION			 " -- "
		::=  { antennaArrayTypeEntry  1 }


	antArrayIndex		 OBJECT-TYPE
		SYNTAX					 Integer32( 0 .. 47 )
		MAX-ACCESS			 read-create
		STATUS					 current
		DESCRIPTION			 " -- "
		::=  { antennaArrayTypeEntry  2 }


	antArrayRowStatus		 OBJECT-TYPE
		SYNTAX					 RowStatus
		MAX-ACCESS			 read-create
		STATUS					 current
		DESCRIPTION			 " -- "
		::=  { antennaArrayTypeEntry  3 }


	antArrayModelName		 OBJECT-TYPE
		SYNTAX					 DisplayString( SIZE ( 1 .. 100 ) )
		MAX-ACCESS			 read-create
		STATUS					 current
		DESCRIPTION			 " -- "
		::=  { antennaArrayTypeEntry  4 }


	antArrayType		 OBJECT-TYPE
		SYNTAX					 INTEGER{ ula(0),uca(1),polar(2)  }
		MAX-ACCESS			 read-create
		STATUS					 current
		DESCRIPTION			 " -- "
		::=  { antennaArrayTypeEntry  5 }


	antArrayNum		 OBJECT-TYPE
		SYNTAX					 Integer32( 1 .. 8 )
		MAX-ACCESS			 read-create
		STATUS					 current
		DESCRIPTION			 " -- "
		::=  { antennaArrayTypeEntry  6 }


	antArrayDistance		 OBJECT-TYPE
		SYNTAX					 Integer32( 0 .. 65535 )
		MAX-ACCESS			 read-create
		STATUS					 current
		DESCRIPTION			 " -- "
		::=  { antennaArrayTypeEntry  7 }


	antennaWeightTable		 OBJECT-TYPE
		SYNTAX					 SEQUENCE  OF	 AntennaWeightEntry
		MAX-ACCESS			 not-accessible
		STATUS					 current
		DESCRIPTION			 " -- "
		::=  { antennaBaseInfo  2 }


	antennaWeightEntry		 OBJECT-TYPE
		SYNTAX					 AntennaWeightEntry
		MAX-ACCESS			 not-accessible
		STATUS					 current
		DESCRIPTION			 " -- "
		INDEX						{ antWeightArrayNo,antWeightFrequencyBand,antWeightStatusIndex }
		::=  { antennaWeightTable  1 }


	AntennaWeightEntry		 ::=  SEQUENCE {
		antWeightArrayNo					Integer32,
		antWeightFrequencyBand					INTEGER,
		antWeightStatusIndex					BITS,
		antWeightRowStatus					RowStatus,
		antWeightHalfPowerBeamWidth					Integer32,
		antWeightBeamDirection					Integer32,
		antWeightAmplitude0					Integer32,
		antWeightPhase0					Integer32,
		antWeightAmplitude1					Integer32,
		antWeightPhase1					Integer32,
		antWeightAmplitude2					Integer32,
		antWeightPhase2					Integer32,
		antWeightAmplitude3					Integer32,
		antWeightPhase3					Integer32,
		antWeightAmplitude4					Integer32,
		antWeightPhase4					Integer32,
		antWeightAmplitude5					Integer32,
		antWeightPhase5					Integer32,
		antWeightAmplitude6					Integer32,
		antWeightPhase6					Integer32,
		antWeightAmplitude7					Integer32,
		antWeightPhase7					Integer32,
		antWeightLibIndex					Integer32
		}


	antWeightArrayNo		 OBJECT-TYPE
		SYNTAX					 Integer32( 0 .. 191 )
		MAX-ACCESS			 read-create
		STATUS					 current
		DESCRIPTION			 " -- "
		::=  { antennaWeightEntry  1 }


	antWeightFrequencyBand		 OBJECT-TYPE
		SYNTAX					 INTEGER{ a(1),d(2),e(4),f(8),v(32),b41(64),t(128),b03(256),b01(512),b44(1024),f1(8192),f2(16384)  }
		MAX-ACCESS			 read-create
		STATUS					 current
		DESCRIPTION			 " -- "
		::=  { antennaWeightEntry  2 }


	antWeightStatusIndex		 OBJECT-TYPE
		SYNTAX					 BITS{ ant1(0),ant2(1),ant3(2),ant4(3),ant5(4),ant6(5),ant7(6),ant8(7)  }
		MAX-ACCESS			 read-create
		STATUS					 current
		DESCRIPTION			 " -- "
		::=  { antennaWeightEntry  3 }


	antWeightRowStatus		 OBJECT-TYPE
		SYNTAX					 RowStatus
		MAX-ACCESS			 read-create
		STATUS					 current
		DESCRIPTION			 " -- "
		::=  { antennaWeightEntry  4 }


	antWeightHalfPowerBeamWidth		 OBJECT-TYPE
		SYNTAX					 Integer32( 0 .. 360 )
		MAX-ACCESS			 read-create
		STATUS					 current
		DESCRIPTION			 " -- "
		::=  { antennaWeightEntry  5 }


	antWeightBeamDirection		 OBJECT-TYPE
		SYNTAX					 Integer32( -40 .. 40 )
		MAX-ACCESS			 read-create
		STATUS					 current
		DESCRIPTION			 " -- "
		::=  { antennaWeightEntry  6 }


	antWeightAmplitude0		 OBJECT-TYPE
		SYNTAX					 Integer32( -2147483648 .. 2147483647 )
		MAX-ACCESS			 read-create
		STATUS					 current
		DESCRIPTION			 " -- "
		::=  { antennaWeightEntry  7 }


	antWeightPhase0		 OBJECT-TYPE
		SYNTAX					 Integer32( -2147483648 .. 2147483647 )
		MAX-ACCESS			 read-create
		STATUS					 current
		DESCRIPTION			 " -- "
		::=  { antennaWeightEntry  8 }


	antWeightAmplitude1		 OBJECT-TYPE
		SYNTAX					 Integer32( -2147483648 .. 2147483647 )
		MAX-ACCESS			 read-create
		STATUS					 current
		DESCRIPTION			 " -- "
		::=  { antennaWeightEntry  9 }


	antWeightPhase1		 OBJECT-TYPE
		SYNTAX					 Integer32( -2147483648 .. 2147483647 )
		MAX-ACCESS			 read-create
		STATUS					 current
		DESCRIPTION			 " -- "
		::=  { antennaWeightEntry  10 }


	antWeightAmplitude2		 OBJECT-TYPE
		SYNTAX					 Integer32( -2147483648 .. 2147483647 )
		MAX-ACCESS			 read-create
		STATUS					 current
		DESCRIPTION			 " -- "
		::=  { antennaWeightEntry  11 }


	antWeightPhase2		 OBJECT-TYPE
		SYNTAX					 Integer32( -2147483648 .. 2147483647 )
		MAX-ACCESS			 read-create
		STATUS					 current
		DESCRIPTION			 " -- "
		::=  { antennaWeightEntry  12 }


	antWeightAmplitude3		 OBJECT-TYPE
		SYNTAX					 Integer32( -2147483648 .. 2147483647 )
		MAX-ACCESS			 read-create
		STATUS					 current
		DESCRIPTION			 " -- "
		::=  { antennaWeightEntry  13 }


	antWeightPhase3		 OBJECT-TYPE
		SYNTAX					 Integer32( -2147483648 .. 2147483647 )
		MAX-ACCESS			 read-create
		STATUS					 current
		DESCRIPTION			 " -- "
		::=  { antennaWeightEntry  14 }


	antWeightAmplitude4		 OBJECT-TYPE
		SYNTAX					 Integer32( -2147483648 .. 2147483647 )
		MAX-ACCESS			 read-create
		STATUS					 current
		DESCRIPTION			 " -- "
		::=  { antennaWeightEntry  15 }


	antWeightPhase4		 OBJECT-TYPE
		SYNTAX					 Integer32( -2147483648 .. 2147483647 )
		MAX-ACCESS			 read-create
		STATUS					 current
		DESCRIPTION			 " -- "
		::=  { antennaWeightEntry  16 }


	antWeightAmplitude5		 OBJECT-TYPE
		SYNTAX					 Integer32( -2147483648 .. 2147483647 )
		MAX-ACCESS			 read-create
		STATUS					 current
		DESCRIPTION			 " -- "
		::=  { antennaWeightEntry  17 }


	antWeightPhase5		 OBJECT-TYPE
		SYNTAX					 Integer32( -2147483648 .. 2147483647 )
		MAX-ACCESS			 read-create
		STATUS					 current
		DESCRIPTION			 " -- "
		::=  { antennaWeightEntry  18 }


	antWeightAmplitude6		 OBJECT-TYPE
		SYNTAX					 Integer32( -2147483648 .. 2147483647 )
		MAX-ACCESS			 read-create
		STATUS					 current
		DESCRIPTION			 " -- "
		::=  { antennaWeightEntry  19 }


	antWeightPhase6		 OBJECT-TYPE
		SYNTAX					 Integer32( -2147483648 .. 2147483647 )
		MAX-ACCESS			 read-create
		STATUS					 current
		DESCRIPTION			 " -- "
		::=  { antennaWeightEntry  20 }


	antWeightAmplitude7		 OBJECT-TYPE
		SYNTAX					 Integer32( -2147483648 .. 2147483647 )
		MAX-ACCESS			 read-create
		STATUS					 current
		DESCRIPTION			 " -- "
		::=  { antennaWeightEntry  21 }


	antWeightPhase7		 OBJECT-TYPE
		SYNTAX					 Integer32( -2147483648 .. 2147483647 )
		MAX-ACCESS			 read-create
		STATUS					 current
		DESCRIPTION			 " -- "
		::=  { antennaWeightEntry  22 }


	antWeightLibIndex		 OBJECT-TYPE
		SYNTAX					 Integer32( -1|0 .. 65535 )
		MAX-ACCESS			 read-create
		STATUS					 current
		DESCRIPTION			 " -- "
		::=  { antennaWeightEntry  23 }


	raeUseingWeightTable		 OBJECT-TYPE
		SYNTAX					 SEQUENCE  OF	 RaeUseingWeightEntry
		MAX-ACCESS			 not-accessible
		STATUS					 current
		DESCRIPTION			 " -- "
		::=  { antennaBaseInfo  3 }


	raeUseingWeightEntry		 OBJECT-TYPE
		SYNTAX					 RaeUseingWeightEntry
		MAX-ACCESS			 not-accessible
		STATUS					 current
		DESCRIPTION			 " -- "
		INDEX						{ antUseingWeightArrayNo }
		::=  { raeUseingWeightTable  1 }


	RaeUseingWeightEntry		 ::=  SEQUENCE {
		antUseingWeightArrayNo					Integer32,
		antUseingWeightRowStatus					RowStatus,
		antUseingWeightAmplitude0					Integer32,
		antUseingWeightPhase0					Integer32,
		antUseingWeightAmplitude1					Integer32,
		antUseingWeightPhase1					Integer32,
		antUseingWeightAmplitude2					Integer32,
		antUseingWeightPhase2					Integer32,
		antUseingWeightAmplitude3					Integer32,
		antUseingWeightPhase3					Integer32,
		antUseingWeightAmplitude4					Integer32,
		antUseingWeightPhase4					Integer32,
		antUseingWeightAmplitude5					Integer32,
		antUseingWeightPhase5					Integer32,
		antUseingWeightAmplitude6					Integer32,
		antUseingWeightPhase6					Integer32,
		antUseingWeightAmplitude7					Integer32,
		antUseingWeightPhase7					Integer32
		}


	antUseingWeightArrayNo		 OBJECT-TYPE
		SYNTAX					 Integer32( 0 .. 47 )
		MAX-ACCESS			 read-create
		STATUS					 current
		DESCRIPTION			 " -- "
		::=  { raeUseingWeightEntry  1 }


	antUseingWeightRowStatus		 OBJECT-TYPE
		SYNTAX					 RowStatus
		MAX-ACCESS			 read-create
		STATUS					 current
		DESCRIPTION			 " -- "
		::=  { raeUseingWeightEntry  2 }


	antUseingWeightAmplitude0		 OBJECT-TYPE
		SYNTAX					 Integer32( -2147483648 .. 2147483647 )
		MAX-ACCESS			 read-create
		STATUS					 current
		DESCRIPTION			 " -- "
		::=  { raeUseingWeightEntry  3 }


	antUseingWeightPhase0		 OBJECT-TYPE
		SYNTAX					 Integer32( -2147483648 .. 2147483647 )
		MAX-ACCESS			 read-create
		STATUS					 current
		DESCRIPTION			 " -- "
		::=  { raeUseingWeightEntry  4 }


	antUseingWeightAmplitude1		 OBJECT-TYPE
		SYNTAX					 Integer32( -2147483648 .. 2147483647 )
		MAX-ACCESS			 read-create
		STATUS					 current
		DESCRIPTION			 " -- "
		::=  { raeUseingWeightEntry  5 }


	antUseingWeightPhase1		 OBJECT-TYPE
		SYNTAX					 Integer32( -2147483648 .. 2147483647 )
		MAX-ACCESS			 read-create
		STATUS					 current
		DESCRIPTION			 " -- "
		::=  { raeUseingWeightEntry  6 }


	antUseingWeightAmplitude2		 OBJECT-TYPE
		SYNTAX					 Integer32( -2147483648 .. 2147483647 )
		MAX-ACCESS			 read-create
		STATUS					 current
		DESCRIPTION			 " -- "
		::=  { raeUseingWeightEntry  7 }


	antUseingWeightPhase2		 OBJECT-TYPE
		SYNTAX					 Integer32( -2147483648 .. 2147483647 )
		MAX-ACCESS			 read-create
		STATUS					 current
		DESCRIPTION			 " -- "
		::=  { raeUseingWeightEntry  8 }


	antUseingWeightAmplitude3		 OBJECT-TYPE
		SYNTAX					 Integer32( -2147483648 .. 2147483647 )
		MAX-ACCESS			 read-create
		STATUS					 current
		DESCRIPTION			 " -- "
		::=  { raeUseingWeightEntry  9 }


	antUseingWeightPhase3		 OBJECT-TYPE
		SYNTAX					 Integer32( -2147483648 .. 2147483647 )
		MAX-ACCESS			 read-create
		STATUS					 current
		DESCRIPTION			 " -- "
		::=  { raeUseingWeightEntry  10 }


	antUseingWeightAmplitude4		 OBJECT-TYPE
		SYNTAX					 Integer32( -2147483648 .. 2147483647 )
		MAX-ACCESS			 read-create
		STATUS					 current
		DESCRIPTION			 " -- "
		::=  { raeUseingWeightEntry  11 }


	antUseingWeightPhase4		 OBJECT-TYPE
		SYNTAX					 Integer32( -2147483648 .. 2147483647 )
		MAX-ACCESS			 read-create
		STATUS					 current
		DESCRIPTION			 " -- "
		::=  { raeUseingWeightEntry  12 }


	antUseingWeightAmplitude5		 OBJECT-TYPE
		SYNTAX					 Integer32( -2147483648 .. 2147483647 )
		MAX-ACCESS			 read-create
		STATUS					 current
		DESCRIPTION			 " -- "
		::=  { raeUseingWeightEntry  13 }


	antUseingWeightPhase5		 OBJECT-TYPE
		SYNTAX					 Integer32( -2147483648 .. 2147483647 )
		MAX-ACCESS			 read-create
		STATUS					 current
		DESCRIPTION			 " -- "
		::=  { raeUseingWeightEntry  14 }


	antUseingWeightAmplitude6		 OBJECT-TYPE
		SYNTAX					 Integer32( -2147483648 .. 2147483647 )
		MAX-ACCESS			 read-create
		STATUS					 current
		DESCRIPTION			 " -- "
		::=  { raeUseingWeightEntry  15 }


	antUseingWeightPhase6		 OBJECT-TYPE
		SYNTAX					 Integer32( -2147483648 .. 2147483647 )
		MAX-ACCESS			 read-create
		STATUS					 current
		DESCRIPTION			 " -- "
		::=  { raeUseingWeightEntry  16 }


	antUseingWeightAmplitude7		 OBJECT-TYPE
		SYNTAX					 Integer32( -2147483648 .. 2147483647 )
		MAX-ACCESS			 read-create
		STATUS					 current
		DESCRIPTION			 " -- "
		::=  { raeUseingWeightEntry  17 }


	antUseingWeightPhase7		 OBJECT-TYPE
		SYNTAX					 Integer32( -2147483648 .. 2147483647 )
		MAX-ACCESS			 read-create
		STATUS					 current
		DESCRIPTION			 " -- "
		::=  { raeUseingWeightEntry  18 }


	netEquipInfo		 OBJECT IDENTIFIER
		::=  { networkElementLayoutPlan  2 }


	netBoardTable		 OBJECT-TYPE
		SYNTAX					 SEQUENCE  OF	 NetBoardEntry
		MAX-ACCESS			 not-accessible
		STATUS					 current
		DESCRIPTION			 " -- "
		::=  { netEquipInfo  1 }


	netBoardEntry		 OBJECT-TYPE
		SYNTAX					 NetBoardEntry
		MAX-ACCESS			 not-accessible
		STATUS					 current
		DESCRIPTION			 " -- "
		INDEX						{ netBoardRackNo,netBoardShelfNo,netBoardSlotNo }
		::=  { netBoardTable  1 }


	NetBoardEntry		 ::=  SEQUENCE {
		netBoardRackNo					Integer32,
		netBoardShelfNo					Integer32,
		netBoardSlotNo					Integer32,
		netBoardRowStatus					RowStatus,
		netBoardType					INTEGER,
		netBoardWorkMode					INTEGER,
		netBoardIrFrameType					INTEGER
		}


	netBoardRackNo		 OBJECT-TYPE
		SYNTAX					 Integer32( 0 .. 0 )
		MAX-ACCESS			 not-accessible
		STATUS					 current
		DESCRIPTION			 " -- "
		::=  { netBoardEntry  1 }


	netBoardShelfNo		 OBJECT-TYPE
		SYNTAX					 Integer32( 0 .. 0 )
		MAX-ACCESS			 not-accessible
		STATUS					 current
		DESCRIPTION			 " -- "
		::=  { netBoardEntry  2 }


	netBoardSlotNo		 OBJECT-TYPE
		SYNTAX					 Integer32( 0 .. 11 )
		MAX-ACCESS			 not-accessible
		STATUS					 current
		DESCRIPTION			 " -- "
		::=  { netBoardEntry  3 }


	netBoardRowStatus		 OBJECT-TYPE
		SYNTAX					 RowStatus
		MAX-ACCESS			 read-create
		STATUS					 current
		DESCRIPTION			 " -- "
		::=  { netBoardEntry  4 }


	netBoardType		 OBJECT-TYPE
		SYNTAX					 INTEGER{ unknown(0),riuDof(48),riuE1(49),riuA(50),gcu(52),ccu(54),ceu(56),bbu(58),aifur6C8A(59),ifur3C6A(60),ifur6C1A(61),ifur3C4A(62),aifur9C1A(63),gru(64),ctu(65),iiu(66),bcu(67),biu(68),accu(70),abbut(71),abbuf(72),eiuE1(73),synu(74),eiuDof(75),aifur12C1A(77),aifur9C8A(78),scta(97),bpia(98),bpoa(99),gpscu(100),emu(101),geu(102),emau(103),etpa(104),etpd(105),psu(106),fcu(107),bpoc(108),bpoe(109),emdu(110),etpc(111),bpof(128),etpe(129),sctc(130),sctd(141),mmba(142),bpog(143),bpoh(177),scte(178),mmbc(224),sctf(240),bpoi(241)  }
		MAX-ACCESS			 read-create
		STATUS					 current
		DESCRIPTION			 " -- "
		::=  { netBoardEntry  5 }


	netBoardWorkMode		 OBJECT-TYPE
		SYNTAX					 INTEGER{ lte(2),td(4),fdd(8)  }
		MAX-ACCESS			 read-create
		STATUS					 current
		DESCRIPTION			 " -- "
		::=  { netBoardEntry  6 }


	netBoardIrFrameType		 OBJECT-TYPE
		SYNTAX					 INTEGER{ tdriTd(0),tdriLte(1),cpri(2),cprihdlc(3)  }
		MAX-ACCESS			 read-create
		STATUS					 current
		DESCRIPTION			 " -- "
		::=  { netBoardEntry  7 }


	netRemoteRadioUnit		 OBJECT IDENTIFIER
		::=  { netEquipInfo  2 }


	netRRUTable		 OBJECT-TYPE
		SYNTAX					 SEQUENCE  OF	 NetRRUEntry
		MAX-ACCESS			 not-accessible
		STATUS					 current
		DESCRIPTION			 " -- "
		::=  { netRemoteRadioUnit  1 }


	netRRUEntry		 OBJECT-TYPE
		SYNTAX					 NetRRUEntry
		MAX-ACCESS			 not-accessible
		STATUS					 current
		DESCRIPTION			 " -- "
		INDEX						{ netRRUNo }
		::=  { netRRUTable  1 }


	NetRRUEntry		 ::=  SEQUENCE {
		netRRUNo					Integer32,
		netRRURowStatus					RowStatus,
		netRRUManufacturerIndex					INTEGER,
		netRRUTypeIndex					Integer32,
		netRRULocation					DisplayString,
		netRRUOfpWorkMode					INTEGER,
		netRRUAccessRackNo					Integer32,
		netRRUAccessShelfNo					Integer32,
		netRRUAccessSlotNo					Integer32,
		netRRUAccessBoardType					INTEGER,
		netRRUOfp1AccessOfpPortNo					Integer32,
		netRRUOfp1AccessLinePosition					Integer32,
		netRRUOfp2AccessOfpPortNo					Integer32,
		netRRUOfp2AccessLinePosition					Integer32,
		netRRUFiberLength					INTEGER,
		netRRUPGCSwitch					INTEGER,
		netRRUPGCSetRange					Unsigned32,
		netRRUJamResistantSwitch					INTEGER,
		netRRUJamResistantSetRange					Integer32,
		netRRUOfp1AccessEthernetPort					INTEGER,
		netRRUHubNo					Integer32,
		netRRUOfp2AccessEthernetPort					INTEGER,
		netRRUGsmSwitch					INTEGER,
		netRRUAntCombinGrpNo					Integer32
		}


	netRRUNo		 OBJECT-TYPE
		SYNTAX					 Integer32( 0 .. 191 )
		MAX-ACCESS			 not-accessible
		STATUS					 current
		DESCRIPTION			 " -- "
		::=  { netRRUEntry  1 }


	netRRURowStatus		 OBJECT-TYPE
		SYNTAX					 RowStatus
		MAX-ACCESS			 read-create
		STATUS					 current
		DESCRIPTION			 " -- "
		::=  { netRRUEntry  2 }


	netRRUManufacturerIndex		 OBJECT-TYPE
		SYNTAX					 INTEGER{ erisson(2),datang(4),dingqiao(6),putian(8),zhongxing(10)  }
		MAX-ACCESS			 read-create
		STATUS					 current
		DESCRIPTION			 " -- "
		::=  { netRRUEntry  3 }


	netRRUTypeIndex		 OBJECT-TYPE
		SYNTAX					 Integer32( 0 .. 255 )
		MAX-ACCESS			 read-create
		STATUS					 current
		DESCRIPTION			 " -- "
		::=  { netRRUEntry  4 }


	netRRULocation		 OBJECT-TYPE
		SYNTAX					 DisplayString( SIZE ( 1 .. 255 ) )
		MAX-ACCESS			 read-create
		STATUS					 current
		DESCRIPTION			 " -- "
		::=  { netRRUEntry  5 }


	netRRUOfpWorkMode		 OBJECT-TYPE
		SYNTAX					 INTEGER{ normal(1),lined(2),backup(3),shared(4)  }
		MAX-ACCESS			 read-create
		STATUS					 current
		DESCRIPTION			 " -- "
		::=  { netRRUEntry  6 }


	netRRUAccessRackNo		 OBJECT-TYPE
		SYNTAX					 Integer32( 0 .. 0|-1 )
		MAX-ACCESS			 read-create
		STATUS					 current
		DESCRIPTION			 " -- "
		::=  { netRRUEntry  7 }


	netRRUAccessShelfNo		 OBJECT-TYPE
		SYNTAX					 Integer32( 0 .. 0|-1 )
		MAX-ACCESS			 read-create
		STATUS					 current
		DESCRIPTION			 " -- "
		::=  { netRRUEntry  8 }


	netRRUAccessSlotNo		 OBJECT-TYPE
		SYNTAX					 Integer32( 2 .. 7|-1 )
		MAX-ACCESS			 read-create
		STATUS					 current
		DESCRIPTION			 " -- "
		::=  { netRRUEntry  9 }


	netRRUAccessBoardType		 OBJECT-TYPE
		SYNTAX					 INTEGER{ unknown(0),ccu(54),ceu(56),bbu(58),iiu(66),bcu(67),biu(68),accu(70),abbut(71),abbuf(72),eiuDof(75),scta(97),bpia(98),bpoa(99),bpoe(109),tdru311B(113),tdru312(114),bpof(128),sctd(141),mmba(142),bpog(143),bpoh(177),scte(178),mmbc(224),sctf(240),bpoi(241)  }
		MAX-ACCESS			 read-create
		STATUS					 current
		DESCRIPTION			 " -- "
		::=  { netRRUEntry  10 }


	netRRUOfp1AccessOfpPortNo		 OBJECT-TYPE
		SYNTAX					 Integer32( 0 .. 5|-1 )
		MAX-ACCESS			 read-create
		STATUS					 current
		DESCRIPTION			 " -- "
		::=  { netRRUEntry  11 }


	netRRUOfp1AccessLinePosition		 OBJECT-TYPE
		SYNTAX					 Integer32( 1 .. 6|-1 )
		MAX-ACCESS			 read-create
		STATUS					 current
		DESCRIPTION			 " -- "
		::=  { netRRUEntry  12 }


	netRRUOfp2AccessOfpPortNo		 OBJECT-TYPE
		SYNTAX					 Integer32( 0 .. 5|-1 )
		MAX-ACCESS			 read-create
		STATUS					 current
		DESCRIPTION			 " -- "
		::=  { netRRUEntry  13 }


	netRRUOfp2AccessLinePosition		 OBJECT-TYPE
		SYNTAX					 Integer32( 1 .. 6|-1 )
		MAX-ACCESS			 read-create
		STATUS					 current
		DESCRIPTION			 " -- "
		::=  { netRRUEntry  14 }


	netRRUFiberLength		 OBJECT-TYPE
		SYNTAX					 INTEGER{ ten(0),twenty(1),forty(2)  }
		MAX-ACCESS			 read-create
		STATUS					 current
		DESCRIPTION			 " -- "
		::=  { netRRUEntry  15 }


	netRRUPGCSwitch		 OBJECT-TYPE
		SYNTAX					 INTEGER{ off(0),on(1)  }
		MAX-ACCESS			 read-create
		STATUS					 current
		DESCRIPTION			 " -- "
		::=  { netRRUEntry  16 }


	netRRUPGCSetRange		 OBJECT-TYPE
		SYNTAX					 Unsigned32( 0 .. 17 )
		MAX-ACCESS			 read-create
		STATUS					 current
		DESCRIPTION			 " -- "
		::=  { netRRUEntry  17 }


	netRRUJamResistantSwitch		 OBJECT-TYPE
		SYNTAX					 INTEGER{ off(0),on(1)  }
		MAX-ACCESS			 read-create
		STATUS					 current
		DESCRIPTION			 " -- "
		::=  { netRRUEntry  19 }


	netRRUJamResistantSetRange		 OBJECT-TYPE
		SYNTAX					 Integer32( -12 .. -7 )
		MAX-ACCESS			 read-create
		STATUS					 current
		DESCRIPTION			 " -- "
		::=  { netRRUEntry  20 }


	netRRUOfp1AccessEthernetPort		 OBJECT-TYPE
		SYNTAX					 INTEGER{ port1(0),port2(1),port3(2),port4(3),port5(4),port6(5),port7(6),port8(7),unknown(-1)  }
		MAX-ACCESS			 read-create
		STATUS					 current
		DESCRIPTION			 " -- "
		::=  { netRRUEntry  22 }


	netRRUHubNo		 OBJECT-TYPE
		SYNTAX					 Integer32( 200 .. 254|-1 )
		MAX-ACCESS			 read-create
		STATUS					 current
		DESCRIPTION			 " -- "
		::=  { netRRUEntry  23 }


	netRRUOfp2AccessEthernetPort		 OBJECT-TYPE
		SYNTAX					 INTEGER{ port1(0),port2(1),port3(2),port4(3),port5(4),port6(5),port7(6),port8(7),unknown(-1)  }
		MAX-ACCESS			 read-create
		STATUS					 current
		DESCRIPTION			 " -- "
		::=  { netRRUEntry  24 }


	netRRUGsmSwitch		 OBJECT-TYPE
		SYNTAX					 INTEGER{ off(0),on(1)  }
		MAX-ACCESS			 read-create
		STATUS					 current
		DESCRIPTION			 " -- "
		::=  { netRRUEntry  25 }


	netRRUAntCombinGrpNo		 OBJECT-TYPE
		SYNTAX					 Integer32( 0 .. 65535 )
		MAX-ACCESS			 read-create
		STATUS					 current
		DESCRIPTION			 " -- "
		::=  { netRRUEntry  26 }


	netAntenna		 OBJECT IDENTIFIER
		::=  { netRemoteRadioUnit  2 }


	netAntennaArrayTable		 OBJECT-TYPE
		SYNTAX					 SEQUENCE  OF	 NetAntennaArrayEntry
		MAX-ACCESS			 not-accessible
		STATUS					 current
		DESCRIPTION			 " -- "
		::=  { netAntenna  1 }


	netAntennaArrayEntry		 OBJECT-TYPE
		SYNTAX					 NetAntennaArrayEntry
		MAX-ACCESS			 not-accessible
		STATUS					 current
		DESCRIPTION			 " -- "
		INDEX						{ netAntArrayNo }
		::=  { netAntennaArrayTable  1 }


	NetAntennaArrayEntry		 ::=  SEQUENCE {
		netAntArrayNo					Integer32,
		netAntArrayRowStatus					RowStatus,
		netAntArrayVendorIndex					Integer32,
		netAntArrayTypeIndex					Integer32,
		netAntArrayPosition					Integer32,
		netAntArrayLocation					DisplayString,
		netAntArrayIsRet					INTEGER,
		netAntArrayHalfPowerBeamWidth					Integer32,
		netAntArrayTdsInfoValidFlag					INTEGER,
		netAntArrayVendorName					DisplayString,
		netAntArrayModel					DisplayString,
		netAntArrayType					INTEGER,
		netAntArrayNum					Integer32,
		netAntArrayDistance					Integer32,
		netAntArrayGain					Integer32,
		netAntArrayRAEScanTrigger					INTEGER
		}


	netAntArrayNo		 OBJECT-TYPE
		SYNTAX					 Integer32( 0 .. 191 )
		MAX-ACCESS			 not-accessible
		STATUS					 current
		DESCRIPTION			 " -- "
		::=  { netAntennaArrayEntry  1 }


	netAntArrayRowStatus		 OBJECT-TYPE
		SYNTAX					 RowStatus
		MAX-ACCESS			 read-create
		STATUS					 current
		DESCRIPTION			 " -- "
		::=  { netAntennaArrayEntry  2 }


	netAntArrayVendorIndex		 OBJECT-TYPE
		SYNTAX					 Integer32( 0 .. 255 )
		MAX-ACCESS			 read-create
		STATUS					 current
		DESCRIPTION			 " -- "
		::=  { netAntennaArrayEntry  3 }


	netAntArrayTypeIndex		 OBJECT-TYPE
		SYNTAX					 Integer32( 0 .. 47 )
		MAX-ACCESS			 read-create
		STATUS					 current
		DESCRIPTION			 " -- "
		::=  { netAntennaArrayEntry  4 }


	netAntArrayPosition		 OBJECT-TYPE
		SYNTAX					 Integer32( 0 .. 359 )
		MAX-ACCESS			 read-create
		STATUS					 current
		DESCRIPTION			 " -- "
		::=  { netAntennaArrayEntry  5 }


	netAntArrayLocation		 OBJECT-TYPE
		SYNTAX					 DisplayString( SIZE ( 1 .. 255 ) )
		MAX-ACCESS			 read-create
		STATUS					 current
		DESCRIPTION			 " -- "
		::=  { netAntennaArrayEntry  6 }


	netAntArrayIsRet		 OBJECT-TYPE
		SYNTAX					 INTEGER{ unsupport(0),support(1)  }
		MAX-ACCESS			 read-create
		STATUS					 current
		DESCRIPTION			 " -- "
		::=  { netAntennaArrayEntry  7 }


	netAntArrayHalfPowerBeamWidth		 OBJECT-TYPE
		SYNTAX					 Integer32( 0 .. 360 )
		MAX-ACCESS			 read-create
		STATUS					 current
		DESCRIPTION			 " -- "
		::=  { netAntennaArrayEntry  8 }


	netAntArrayTdsInfoValidFlag		 OBJECT-TYPE
		SYNTAX					 INTEGER{ invalid(0),valid(1)  }
		MAX-ACCESS			 read-only
		STATUS					 current
		DESCRIPTION			 " -- "
		::=  { netAntennaArrayEntry  9 }


	netAntArrayVendorName		 OBJECT-TYPE
		SYNTAX					 DisplayString( SIZE ( 1 .. 255 ) )
		MAX-ACCESS			 read-only
		STATUS					 current
		DESCRIPTION			 " -- "
		::=  { netAntennaArrayEntry  10 }


	netAntArrayModel		 OBJECT-TYPE
		SYNTAX					 DisplayString( SIZE ( 1 .. 255 ) )
		MAX-ACCESS			 read-only
		STATUS					 current
		DESCRIPTION			 " -- "
		::=  { netAntennaArrayEntry  11 }


	netAntArrayType		 OBJECT-TYPE
		SYNTAX					 INTEGER{ uca(1),ula(2),dis(3),polar(4),tideula(5)  }
		MAX-ACCESS			 read-only
		STATUS					 current
		DESCRIPTION			 " -- "
		::=  { netAntennaArrayEntry  12 }


	netAntArrayNum		 OBJECT-TYPE
		SYNTAX					 Integer32( 1 .. 8 )
		MAX-ACCESS			 read-only
		STATUS					 current
		DESCRIPTION			 " -- "
		::=  { netAntennaArrayEntry  13 }


	netAntArrayDistance		 OBJECT-TYPE
		SYNTAX					 Integer32( 0 .. 65535 )
		MAX-ACCESS			 read-only
		STATUS					 current
		DESCRIPTION			 " -- "
		::=  { netAntennaArrayEntry  14 }


	netAntArrayGain		 OBJECT-TYPE
		SYNTAX					 Integer32( -2147483648 .. 2147483647 )
		MAX-ACCESS			 read-only
		STATUS					 current
		DESCRIPTION			 " -- "
		::=  { netAntennaArrayEntry  15 }


	netAntArrayRAEScanTrigger		 OBJECT-TYPE
		SYNTAX					 INTEGER{ off(0),on(1)  }
		MAX-ACCESS			 read-write
		STATUS					 current
		DESCRIPTION			 " -- "
		::=  { netAntennaArrayEntry  16 }


	netRETAntRCUTable		 OBJECT-TYPE
		SYNTAX					 SEQUENCE  OF	 NetRETAntRCUEntry
		MAX-ACCESS			 not-accessible
		STATUS					 current
		DESCRIPTION			 " -- "
		::=  { netAntenna  2 }


	netRETAntRCUEntry		 OBJECT-TYPE
		SYNTAX					 NetRETAntRCUEntry
		MAX-ACCESS			 not-accessible
		STATUS					 current
		DESCRIPTION			 " -- "
		INDEX						{ netRETAntRCUNo }
		::=  { netRETAntRCUTable  1 }


	NetRETAntRCUEntry		 ::=  SEQUENCE {
		netRETAntRCUNo					Integer32,
		netRETAntRCURowStatus					RowStatus,
		netRETAntRCULocation					DisplayString
		}


	netRETAntRCUNo		 OBJECT-TYPE
		SYNTAX					 Integer32( 0 .. 191 )
		MAX-ACCESS			 not-accessible
		STATUS					 current
		DESCRIPTION			 " -- "
		::=  { netRETAntRCUEntry  1 }


	netRETAntRCURowStatus		 OBJECT-TYPE
		SYNTAX					 RowStatus
		MAX-ACCESS			 read-create
		STATUS					 current
		DESCRIPTION			 " -- "
		::=  { netRETAntRCUEntry  2 }


	netRETAntRCULocation		 OBJECT-TYPE
		SYNTAX					 DisplayString( SIZE ( 1 .. 255 ) )
		MAX-ACCESS			 read-write
		STATUS					 current
		DESCRIPTION			 " -- "
		::=  { netRETAntRCUEntry  3 }


	netRRUAntennaSettingTable		 OBJECT-TYPE
		SYNTAX					 SEQUENCE  OF	 NetRRUAntennaSettingEntry
		MAX-ACCESS			 not-accessible
		STATUS					 current
		DESCRIPTION			 " -- "
		::=  { netRemoteRadioUnit  3 }


	netRRUAntennaSettingEntry		 OBJECT-TYPE
		SYNTAX					 NetRRUAntennaSettingEntry
		MAX-ACCESS			 not-accessible
		STATUS					 current
		DESCRIPTION			 " -- "
		INDEX						{ netSetRRUNo,netSetRRUPortNo }
		::=  { netRRUAntennaSettingTable  1 }


	NetRRUAntennaSettingEntry		 ::=  SEQUENCE {
		netSetRRUNo					Integer32,
		netSetRRUPortNo					Integer32,
		netSetRRUPortWithAntennaRowStatus					RowStatus,
		netSetRRUPortAntArrayNo					Integer32,
		netSetRRUPortAntArrayPathNo					Integer32,
		netSetRRUPortRETAntSupport					INTEGER,
		netSetRRUPortRETAntRCUNo					Integer32,
		netSetRRUPortSubtoLocalCellId					Integer32,
		netSetRRUPortTxRxStatus					INTEGER,
		netSetRRUPortSubtoLocalCellId2					Integer32,
		netSetRRUPortSubtoLocalCellId3					Integer32,
		netSetRRUPortSubtoLocalCellId4					Integer32,
		netSetRRUPortGroupNo					Integer32,
		netSetRRUPortSubtoTdsLocalCellId					Integer32,
		netSetRRUPortSubtoAntPathNoInLocalCell					Integer32,
		netSetRRUPortCellPortionId					Integer32,
		netSetRRUPortBand					INTEGER,
		netSetRRUPortManualConfigPortNo					Integer32
		}


	netSetRRUNo		 OBJECT-TYPE
		SYNTAX					 Integer32( 0 .. 191 )
		MAX-ACCESS			 not-accessible
		STATUS					 current
		DESCRIPTION			 " -- "
		::=  { netRRUAntennaSettingEntry  1 }


	netSetRRUPortNo		 OBJECT-TYPE
		SYNTAX					 Integer32( 1 .. 16 )
		MAX-ACCESS			 not-accessible
		STATUS					 current
		DESCRIPTION			 " -- "
		::=  { netRRUAntennaSettingEntry  2 }


	netSetRRUPortWithAntennaRowStatus		 OBJECT-TYPE
		SYNTAX					 RowStatus
		MAX-ACCESS			 read-create
		STATUS					 current
		DESCRIPTION			 " -- "
		::=  { netRRUAntennaSettingEntry  3 }


	netSetRRUPortAntArrayNo		 OBJECT-TYPE
		SYNTAX					 Integer32( 0 .. 191|-1 )
		MAX-ACCESS			 read-create
		STATUS					 current
		DESCRIPTION			 " -- "
		::=  { netRRUAntennaSettingEntry  4 }


	netSetRRUPortAntArrayPathNo		 OBJECT-TYPE
		SYNTAX					 Integer32( 1 .. 8|-1 )
		MAX-ACCESS			 read-create
		STATUS					 current
		DESCRIPTION			 " -- "
		::=  { netRRUAntennaSettingEntry  5 }


	netSetRRUPortRETAntSupport		 OBJECT-TYPE
		SYNTAX					 INTEGER{ unsupport(0),support(1)  }
		MAX-ACCESS			 read-create
		STATUS					 current
		DESCRIPTION			 " -- "
		::=  { netRRUAntennaSettingEntry  6 }


	netSetRRUPortRETAntRCUNo		 OBJECT-TYPE
		SYNTAX					 Integer32( 0 .. 191|-1 )
		MAX-ACCESS			 read-create
		STATUS					 current
		DESCRIPTION			 " -- "
		::=  { netRRUAntennaSettingEntry  7 }


	netSetRRUPortSubtoLocalCellId		 OBJECT-TYPE
		SYNTAX					 Integer32( 0 .. 23|-1 )
		MAX-ACCESS			 read-create
		STATUS					 current
		DESCRIPTION			 " -- "
		::=  { netRRUAntennaSettingEntry  8 }


	netSetRRUPortTxRxStatus		 OBJECT-TYPE
		SYNTAX					 INTEGER{ rx(1),tx(2),rxAndTx(3),invalid(4)  }
		MAX-ACCESS			 read-create
		STATUS					 current
		DESCRIPTION			 " -- "
		::=  { netRRUAntennaSettingEntry  9 }


	netSetRRUPortSubtoLocalCellId2		 OBJECT-TYPE
		SYNTAX					 Integer32( 0 .. 23|-1 )
		MAX-ACCESS			 read-create
		STATUS					 current
		DESCRIPTION			 " -- "
		::=  { netRRUAntennaSettingEntry  10 }


	netSetRRUPortSubtoLocalCellId3		 OBJECT-TYPE
		SYNTAX					 Integer32( 0 .. 23|-1 )
		MAX-ACCESS			 read-create
		STATUS					 current
		DESCRIPTION			 " -- "
		::=  { netRRUAntennaSettingEntry  11 }


	netSetRRUPortSubtoLocalCellId4		 OBJECT-TYPE
		SYNTAX					 Integer32( 0 .. 23|-1 )
		MAX-ACCESS			 read-create
		STATUS					 current
		DESCRIPTION			 " -- "
		::=  { netRRUAntennaSettingEntry  12 }


	netSetRRUPortGroupNo		 OBJECT-TYPE
		SYNTAX					 Integer32( 0 .. 23|-1 )
		MAX-ACCESS			 read-create
		STATUS					 current
		DESCRIPTION			 " -- "
		::=  { netRRUAntennaSettingEntry  13 }


	netSetRRUPortSubtoTdsLocalCellId		 OBJECT-TYPE
		SYNTAX					 Integer32( 0 .. 11|-1 )
		MAX-ACCESS			 read-create
		STATUS					 current
		DESCRIPTION			 " -- "
		::=  { netRRUAntennaSettingEntry  14 }


	netSetRRUPortSubtoAntPathNoInLocalCell		 OBJECT-TYPE
		SYNTAX					 Integer32( 0 .. 255|-1 )
		MAX-ACCESS			 read-create
		STATUS					 current
		DESCRIPTION			 " -- "
		::=  { netRRUAntennaSettingEntry  15 }


	netSetRRUPortCellPortionId		 OBJECT-TYPE
		SYNTAX					 Integer32( -1|0 .. 7 )
		MAX-ACCESS			 read-create
		STATUS					 current
		DESCRIPTION			 " -- "
		::=  { netRRUAntennaSettingEntry  16 }


	netSetRRUPortBand		 OBJECT-TYPE
		SYNTAX					 INTEGER{ unknown(0),f(1),a(2),fa(3),e(4),fe(5),ae(6),fae(7)  }
		MAX-ACCESS			 read-create
		STATUS					 current
		DESCRIPTION			 " -- "
		::=  { netRRUAntennaSettingEntry  17 }


	netSetRRUPortManualConfigPortNo		 OBJECT-TYPE
		SYNTAX					 Integer32( 0 .. 3 )
		MAX-ACCESS			 read-create
		STATUS					 current
		DESCRIPTION			 " -- "
		::=  { netRRUAntennaSettingEntry  18 }


	netIROptPlanTable		 OBJECT-TYPE
		SYNTAX					 SEQUENCE  OF	 NetIROptPlanEntry
		MAX-ACCESS			 not-accessible
		STATUS					 current
		DESCRIPTION			 " -- "
		::=  { netRemoteRadioUnit  4 }


	netIROptPlanEntry		 OBJECT-TYPE
		SYNTAX					 NetIROptPlanEntry
		MAX-ACCESS			 not-accessible
		STATUS					 current
		DESCRIPTION			 " -- "
		INDEX						{ netIROfpPortRackNo,netIROfpPortShelfNo,netIROfpPortSlotNo,netIROfpPortIndexOnBoard }
		::=  { netIROptPlanTable  1 }


	NetIROptPlanEntry		 ::=  SEQUENCE {
		netIROfpPortRackNo					Integer32,
		netIROfpPortShelfNo					Integer32,
		netIROfpPortSlotNo					Integer32,
		netIROfpPortIndexOnBoard					Integer32,
		netIROfpPortRowStatus					RowStatus,
		netIROfpTransPlanSpeed					INTEGER
		}


	netIROfpPortRackNo		 OBJECT-TYPE
		SYNTAX					 Integer32( 0 .. 0 )
		MAX-ACCESS			 not-accessible
		STATUS					 current
		DESCRIPTION			 " -- "
		::=  { netIROptPlanEntry  1 }


	netIROfpPortShelfNo		 OBJECT-TYPE
		SYNTAX					 Integer32( 0 .. 0 )
		MAX-ACCESS			 not-accessible
		STATUS					 current
		DESCRIPTION			 " -- "
		::=  { netIROptPlanEntry  2 }


	netIROfpPortSlotNo		 OBJECT-TYPE
		SYNTAX					 Integer32( 0 .. 16 )
		MAX-ACCESS			 not-accessible
		STATUS					 current
		DESCRIPTION			 " -- "
		::=  { netIROptPlanEntry  3 }


	netIROfpPortIndexOnBoard		 OBJECT-TYPE
		SYNTAX					 Integer32( 0 .. 5 )
		MAX-ACCESS			 not-accessible
		STATUS					 current
		DESCRIPTION			 " -- "
		::=  { netIROptPlanEntry  4 }


	netIROfpPortRowStatus		 OBJECT-TYPE
		SYNTAX					 RowStatus
		MAX-ACCESS			 read-create
		STATUS					 current
		DESCRIPTION			 " -- "
		::=  { netIROptPlanEntry  5 }


	netIROfpTransPlanSpeed		 OBJECT-TYPE
		SYNTAX					 INTEGER{ mbps2500(0),mbps5000(1),mbps6000(2),mbps10000(3)  }
		MAX-ACCESS			 read-write
		STATUS					 current
		DESCRIPTION			 " -- "
		::=  { netIROptPlanEntry  6 }


	netRRURootAlarmTable		 OBJECT-TYPE
		SYNTAX					 SEQUENCE  OF	 NetRRURootAlarmEntry
		MAX-ACCESS			 not-accessible
		STATUS					 current
		DESCRIPTION			 " -- "
		::=  { netRemoteRadioUnit  5 }


	netRRURootAlarmEntry		 OBJECT-TYPE
		SYNTAX					 NetRRURootAlarmEntry
		MAX-ACCESS			 not-accessible
		STATUS					 current
		DESCRIPTION			 " -- "
		INDEX						{ netRRURootAlarmRRUNo }
		::=  { netRRURootAlarmTable  1 }


	NetRRURootAlarmEntry		 ::=  SEQUENCE {
		netRRURootAlarmRRUNo					Integer32,
		netRRURootAlarmRowStatus					RowStatus,
		netRRURootAlarmType1					Integer32,
		netRRURootAlarmState1					INTEGER,
		netRRURootAlarmType2					Integer32,
		netRRURootAlarmState2					INTEGER,
		netRRURootAlarmType3					Integer32,
		netRRURootAlarmState3					INTEGER,
		netRRURootAlarmType4					Integer32,
		netRRURootAlarmState4					INTEGER,
		netRRURootAlarmType5					Integer32,
		netRRURootAlarmState5					INTEGER,
		netRRURootAlarmType6					Integer32,
		netRRURootAlarmState6					INTEGER,
		netRRURootAlarmType7					Integer32,
		netRRURootAlarmState7					INTEGER,
		netRRURootAlarmType8					Integer32,
		netRRURootAlarmState8					INTEGER
		}


	netRRURootAlarmRRUNo		 OBJECT-TYPE
		SYNTAX					 Integer32( 0 .. 191 )
		MAX-ACCESS			 not-accessible
		STATUS					 current
		DESCRIPTION			 " -- "
		::=  { netRRURootAlarmEntry  1 }


	netRRURootAlarmRowStatus		 OBJECT-TYPE
		SYNTAX					 RowStatus
		MAX-ACCESS			 read-create
		STATUS					 current
		DESCRIPTION			 " -- "
		::=  { netRRURootAlarmEntry  2 }


	netRRURootAlarmType1		 OBJECT-TYPE
		SYNTAX					 Integer32( 0|1235 .. 1250 )
		MAX-ACCESS			 read-create
		STATUS					 current
		DESCRIPTION			 " -- "
		::=  { netRRURootAlarmEntry  3 }


	netRRURootAlarmState1		 OBJECT-TYPE
		SYNTAX					 INTEGER{ unknown(0),off(1),on(2)  }
		MAX-ACCESS			 read-create
		STATUS					 current
		DESCRIPTION			 " -- "
		::=  { netRRURootAlarmEntry  4 }


	netRRURootAlarmType2		 OBJECT-TYPE
		SYNTAX					 Integer32( 0|1235 .. 1250 )
		MAX-ACCESS			 read-create
		STATUS					 current
		DESCRIPTION			 " -- "
		::=  { netRRURootAlarmEntry  5 }


	netRRURootAlarmState2		 OBJECT-TYPE
		SYNTAX					 INTEGER{ unknown(0),off(1),on(2)  }
		MAX-ACCESS			 read-create
		STATUS					 current
		DESCRIPTION			 " -- "
		::=  { netRRURootAlarmEntry  6 }


	netRRURootAlarmType3		 OBJECT-TYPE
		SYNTAX					 Integer32( 0|1235 .. 1250 )
		MAX-ACCESS			 read-create
		STATUS					 current
		DESCRIPTION			 " -- "
		::=  { netRRURootAlarmEntry  7 }


	netRRURootAlarmState3		 OBJECT-TYPE
		SYNTAX					 INTEGER{ unknown(0),off(1),on(2)  }
		MAX-ACCESS			 read-create
		STATUS					 current
		DESCRIPTION			 " -- "
		::=  { netRRURootAlarmEntry  8 }


	netRRURootAlarmType4		 OBJECT-TYPE
		SYNTAX					 Integer32( 0|1235 .. 1250 )
		MAX-ACCESS			 read-create
		STATUS					 current
		DESCRIPTION			 " -- "
		::=  { netRRURootAlarmEntry  9 }


	netRRURootAlarmState4		 OBJECT-TYPE
		SYNTAX					 INTEGER{ unknown(0),off(1),on(2)  }
		MAX-ACCESS			 read-create
		STATUS					 current
		DESCRIPTION			 " -- "
		::=  { netRRURootAlarmEntry  10 }


	netRRURootAlarmType5		 OBJECT-TYPE
		SYNTAX					 Integer32( 0|1235 .. 1250 )
		MAX-ACCESS			 read-create
		STATUS					 current
		DESCRIPTION			 " -- "
		::=  { netRRURootAlarmEntry  11 }


	netRRURootAlarmState5		 OBJECT-TYPE
		SYNTAX					 INTEGER{ unknown(0),off(1),on(2)  }
		MAX-ACCESS			 read-create
		STATUS					 current
		DESCRIPTION			 " -- "
		::=  { netRRURootAlarmEntry  12 }


	netRRURootAlarmType6		 OBJECT-TYPE
		SYNTAX					 Integer32( 0|1235 .. 1250 )
		MAX-ACCESS			 read-create
		STATUS					 current
		DESCRIPTION			 " -- "
		::=  { netRRURootAlarmEntry  13 }


	netRRURootAlarmState6		 OBJECT-TYPE
		SYNTAX					 INTEGER{ unknown(0),off(1),on(2)  }
		MAX-ACCESS			 read-create
		STATUS					 current
		DESCRIPTION			 " -- "
		::=  { netRRURootAlarmEntry  14 }


	netRRURootAlarmType7		 OBJECT-TYPE
		SYNTAX					 Integer32( 0|1235 .. 1250 )
		MAX-ACCESS			 read-create
		STATUS					 current
		DESCRIPTION			 " -- "
		::=  { netRRURootAlarmEntry  15 }


	netRRURootAlarmState7		 OBJECT-TYPE
		SYNTAX					 INTEGER{ unknown(0),off(1),on(2)  }
		MAX-ACCESS			 read-create
		STATUS					 current
		DESCRIPTION			 " -- "
		::=  { netRRURootAlarmEntry  16 }


	netRRURootAlarmType8		 OBJECT-TYPE
		SYNTAX					 Integer32( 0|1235 .. 1250 )
		MAX-ACCESS			 read-create
		STATUS					 current
		DESCRIPTION			 " -- "
		::=  { netRRURootAlarmEntry  17 }


	netRRURootAlarmState8		 OBJECT-TYPE
		SYNTAX					 INTEGER{ unknown(0),off(1),on(2)  }
		MAX-ACCESS			 read-create
		STATUS					 current
		DESCRIPTION			 " -- "
		::=  { netRRURootAlarmEntry  18 }


	netRHUBTable		 OBJECT-TYPE
		SYNTAX					 SEQUENCE  OF	 NetRHUBEntry
		MAX-ACCESS			 not-accessible
		STATUS					 current
		DESCRIPTION			 " -- "
		::=  { netRemoteRadioUnit  6 }


	netRHUBEntry		 OBJECT-TYPE
		SYNTAX					 NetRHUBEntry
		MAX-ACCESS			 not-accessible
		STATUS					 current
		DESCRIPTION			 " -- "
		INDEX						{ netRHUBNo }
		::=  { netRHUBTable  1 }


	NetRHUBEntry		 ::=  SEQUENCE {
		netRHUBNo					Integer32,
		netRHUBRowStatus					RowStatus,
		netRHUBLocation					DisplayString,
		netRHUBOfpWorkMode					INTEGER,
		netRHUBAccessRackNo					Integer32,
		netRHUBAccessShelfNo					Integer32,
		netRHUBAccessSlotNo					Integer32,
		netRHUBAccessBoardType					INTEGER,
		netRHUBOfp1AccessOfpPortNo					Integer32,
		netRHUBOfp1AccessLinePosition					Integer32,
		netRHUBFiberLength					INTEGER,
		netRHUBOfp2AccessOfpPortNo					Integer32,
		netRHUBOfp2AccessLinePosition					Integer32,
		netRHUBType					DisplayString,
		netRHUBChannelGain					Unsigned32
		}


	netRHUBNo		 OBJECT-TYPE
		SYNTAX					 Integer32( 200 .. 254 )
		MAX-ACCESS			 not-accessible
		STATUS					 current
		DESCRIPTION			 " -- "
		::=  { netRHUBEntry  1 }


	netRHUBRowStatus		 OBJECT-TYPE
		SYNTAX					 RowStatus
		MAX-ACCESS			 read-create
		STATUS					 current
		DESCRIPTION			 " -- "
		::=  { netRHUBEntry  2 }


	netRHUBLocation		 OBJECT-TYPE
		SYNTAX					 DisplayString( SIZE ( 1 .. 255 ) )
		MAX-ACCESS			 read-create
		STATUS					 current
		DESCRIPTION			 " -- "
		::=  { netRHUBEntry  3 }


	netRHUBOfpWorkMode		 OBJECT-TYPE
		SYNTAX					 INTEGER{ normal(1),lined(2),shared(4),linedshared(5)  }
		MAX-ACCESS			 read-create
		STATUS					 current
		DESCRIPTION			 " -- "
		::=  { netRHUBEntry  4 }


	netRHUBAccessRackNo		 OBJECT-TYPE
		SYNTAX					 Integer32( 0 .. 0|-1 )
		MAX-ACCESS			 read-create
		STATUS					 current
		DESCRIPTION			 " -- "
		::=  { netRHUBEntry  5 }


	netRHUBAccessShelfNo		 OBJECT-TYPE
		SYNTAX					 Integer32( 0 .. 0|-1 )
		MAX-ACCESS			 read-create
		STATUS					 current
		DESCRIPTION			 " -- "
		::=  { netRHUBEntry  6 }


	netRHUBAccessSlotNo		 OBJECT-TYPE
		SYNTAX					 Integer32( 2 .. 7|-1 )
		MAX-ACCESS			 read-create
		STATUS					 current
		DESCRIPTION			 " -- "
		::=  { netRHUBEntry  7 }


	netRHUBAccessBoardType		 OBJECT-TYPE
		SYNTAX					 INTEGER{ unknown(0),bpoh(177),bpoi(241)  }
		MAX-ACCESS			 read-create
		STATUS					 current
		DESCRIPTION			 " -- "
		::=  { netRHUBEntry  8 }


	netRHUBOfp1AccessOfpPortNo		 OBJECT-TYPE
		SYNTAX					 Integer32( 0 .. 5|-1 )
		MAX-ACCESS			 read-create
		STATUS					 current
		DESCRIPTION			 " -- "
		::=  { netRHUBEntry  9 }


	netRHUBOfp1AccessLinePosition		 OBJECT-TYPE
		SYNTAX					 Integer32( 1 .. 4|-1 )
		MAX-ACCESS			 read-create
		STATUS					 current
		DESCRIPTION			 " -- "
		::=  { netRHUBEntry  10 }


	netRHUBFiberLength		 OBJECT-TYPE
		SYNTAX					 INTEGER{ ten(0),twenty(1),forty(2)  }
		MAX-ACCESS			 read-create
		STATUS					 current
		DESCRIPTION			 " -- "
		::=  { netRHUBEntry  11 }


	netRHUBOfp2AccessOfpPortNo		 OBJECT-TYPE
		SYNTAX					 Integer32( 0 .. 5|-1 )
		MAX-ACCESS			 read-create
		STATUS					 current
		DESCRIPTION			 " -- "
		::=  { netRHUBEntry  12 }


	netRHUBOfp2AccessLinePosition		 OBJECT-TYPE
		SYNTAX					 Integer32( 1 .. 4|-1 )
		MAX-ACCESS			 read-create
		STATUS					 current
		DESCRIPTION			 " -- "
		::=  { netRHUBEntry  13 }


	netRHUBType		 OBJECT-TYPE
		SYNTAX					 DisplayString( SIZE ( 1 .. 255 ) )
		MAX-ACCESS			 read-create
		STATUS					 current
		DESCRIPTION			 " -- "
		::=  { netRHUBEntry  14 }


	netRHUBChannelGain		 OBJECT-TYPE
		SYNTAX					 Unsigned32( 0 .. 450 )
		MAX-ACCESS			 read-create
		STATUS					 current
		DESCRIPTION			 " -- "
		::=  { netRHUBEntry  15 }


	netEthPlanTable		 OBJECT-TYPE
		SYNTAX					 SEQUENCE  OF	 NetEthPlanEntry
		MAX-ACCESS			 not-accessible
		STATUS					 current
		DESCRIPTION			 " -- "
		::=  { netRemoteRadioUnit  7 }


	netEthPlanEntry		 OBJECT-TYPE
		SYNTAX					 NetEthPlanEntry
		MAX-ACCESS			 not-accessible
		STATUS					 current
		DESCRIPTION			 " -- "
		INDEX						{ netEthPortRackNo,netEthPortShelfNo,netEthPortSlotNo,netEthRHUBNo,netEthPortIndexOnHub }
		::=  { netEthPlanTable  1 }


	NetEthPlanEntry		 ::=  SEQUENCE {
		netEthPortRackNo					Integer32,
		netEthPortShelfNo					Integer32,
		netEthPortSlotNo					Integer32,
		netEthRHUBNo					Integer32,
		netEthPortIndexOnHub					Integer32,
		netEthPortRowStatus					RowStatus,
		netEthTransPlanSpeed					INTEGER
		}


	netEthPortRackNo		 OBJECT-TYPE
		SYNTAX					 Integer32( 0 .. 0 )
		MAX-ACCESS			 not-accessible
		STATUS					 current
		DESCRIPTION			 " -- "
		::=  { netEthPlanEntry  1 }


	netEthPortShelfNo		 OBJECT-TYPE
		SYNTAX					 Integer32( 0 .. 0 )
		MAX-ACCESS			 not-accessible
		STATUS					 current
		DESCRIPTION			 " -- "
		::=  { netEthPlanEntry  2 }


	netEthPortSlotNo		 OBJECT-TYPE
		SYNTAX					 Integer32( 0 .. 16 )
		MAX-ACCESS			 not-accessible
		STATUS					 current
		DESCRIPTION			 " -- "
		::=  { netEthPlanEntry  3 }


	netEthRHUBNo		 OBJECT-TYPE
		SYNTAX					 Integer32( 200 .. 254 )
		MAX-ACCESS			 not-accessible
		STATUS					 current
		DESCRIPTION			 " -- "
		::=  { netEthPlanEntry  4 }


	netEthPortIndexOnHub		 OBJECT-TYPE
		SYNTAX					 Integer32( 0 .. 7 )
		MAX-ACCESS			 not-accessible
		STATUS					 current
		DESCRIPTION			 " -- "
		::=  { netEthPlanEntry  5 }


	netEthPortRowStatus		 OBJECT-TYPE
		SYNTAX					 RowStatus
		MAX-ACCESS			 read-create
		STATUS					 current
		DESCRIPTION			 " -- "
		::=  { netEthPlanEntry  6 }


	netEthTransPlanSpeed		 OBJECT-TYPE
		SYNTAX					 INTEGER{ mbps1250(0),mbps2500(1),mbps5000(2),mbps10000(4)  }
		MAX-ACCESS			 read-write
		STATUS					 current
		DESCRIPTION			 " -- "
		::=  { netEthPlanEntry  7 }


	linkCommon		 OBJECT IDENTIFIER
		::=  { eNb  1 }


	linkCommonOperationStatus		 OBJECT-TYPE
		SYNTAX					 INTEGER{ disabled(0),enabled(1)  }
		MAX-ACCESS			 read-only
		STATUS					 current
		DESCRIPTION			 " -- "
		::=  { linkCommon  1 }


	linkCommonOperationTDSStatus		 OBJECT-TYPE
		SYNTAX					 INTEGER{ disabled(0),enabled(1)  }
		MAX-ACCESS			 read-only
		STATUS					 current
		DESCRIPTION			 " -- "
		::=  { linkCommon  2 }


	iubSignalTransportMode		 OBJECT-TYPE
		SYNTAX					 INTEGER{ atm(0),ip(1),atmFirst(2),ipFirst(3)  }
		MAX-ACCESS			 read-write
		STATUS					 current
		DESCRIPTION			 " -- "
		::=  { linkCommon  5 }


	iubServiceTransportMode		 OBJECT-TYPE
		SYNTAX					 INTEGER{ atm(0),ip(1),atmip(2)  }
		MAX-ACCESS			 read-write
		STATUS					 current
		DESCRIPTION			 " -- "
		::=  { linkCommon  6 }


	linkCommonMtuValue		 OBJECT-TYPE
		SYNTAX					 Unsigned32( 1400 .. 1600|0 )
		MAX-ACCESS			 read-write
		STATUS					 current
		DESCRIPTION			 " -- "
		::=  { linkCommon  7 }


	ofPortTable		 OBJECT-TYPE
		SYNTAX					 SEQUENCE  OF	 OfPortEntry
		MAX-ACCESS			 not-accessible
		STATUS					 current
		DESCRIPTION			 " -- "
		::=  { ipPhysicalPort  2 }


	ofPortEntry		 OBJECT-TYPE
		SYNTAX					 OfPortEntry
		MAX-ACCESS			 not-accessible
		STATUS					 current
		DESCRIPTION			 " -- "
		INDEX						{ ofPortRackNo,ofPortShelfNo,ofPortSlotNo,ofPortPhyPortId }
		::=  { ofPortTable  1 }


	OfPortEntry		 ::=  SEQUENCE {
		ofPortRackNo					Integer32,
		ofPortShelfNo					Integer32,
		ofPortSlotNo					Integer32,
		ofPortPhyPortId					Integer32,
		ofPortRowStatus					RowStatus,
		ofPortModuleExistState					INTEGER,
		ofPortActiveStatus					INTEGER
		}


	ofPortRackNo		 OBJECT-TYPE
		SYNTAX					 Integer32( 0 .. 0 )
		MAX-ACCESS			 not-accessible
		STATUS					 current
		DESCRIPTION			 " -- "
		::=  { ofPortEntry  1 }


	ofPortShelfNo		 OBJECT-TYPE
		SYNTAX					 Integer32( 0 .. 0 )
		MAX-ACCESS			 not-accessible
		STATUS					 current
		DESCRIPTION			 " -- "
		::=  { ofPortEntry  2 }


	ofPortSlotNo		 OBJECT-TYPE
		SYNTAX					 Integer32( 0 .. 16 )
		MAX-ACCESS			 not-accessible
		STATUS					 current
		DESCRIPTION			 " -- "
		::=  { ofPortEntry  3 }


	ofPortPhyPortId		 OBJECT-TYPE
		SYNTAX					 Integer32( 0 .. 1 )
		MAX-ACCESS			 not-accessible
		STATUS					 current
		DESCRIPTION			 " -- "
		::=  { ofPortEntry  4 }


	ofPortRowStatus		 OBJECT-TYPE
		SYNTAX					 RowStatus
		MAX-ACCESS			 read-only
		STATUS					 current
		DESCRIPTION			 " -- "
		::=  { ofPortEntry  5 }


	ofPortModuleExistState		 OBJECT-TYPE
		SYNTAX					 INTEGER{ notExisted(0),existed(1)  }
		MAX-ACCESS			 read-only
		STATUS					 current
		DESCRIPTION			 " -- "
		::=  { ofPortEntry  6 }


	ofPortActiveStatus		 OBJECT-TYPE
		SYNTAX					 INTEGER{ inactive(0),active(1)  }
		MAX-ACCESS			 read-only
		STATUS					 current
		DESCRIPTION			 " -- "
		::=  { ofPortEntry  7 }


	ipLogicPort		 OBJECT IDENTIFIER
		::=  { eNb  3 }


	ipAddrTable		 OBJECT-TYPE
		SYNTAX					 SEQUENCE  OF	 IpAddrEntry
		MAX-ACCESS			 not-accessible
		STATUS					 current
		DESCRIPTION			 " -- "
		::=  { ipLogicPort  1 }


	ipAddrEntry		 OBJECT-TYPE
		SYNTAX					 IpAddrEntry
		MAX-ACCESS			 not-accessible
		STATUS					 current
		DESCRIPTION			 " -- "
		INDEX						{ ipAddrIndex }
		::=  { ipAddrTable  1 }


	IpAddrEntry		 ::=  SEQUENCE {
		ipAddrIndex					Integer32,
		ipAddrRowStatus					RowStatus,
		ipAddrLocalIpAddressType					InetAddressType,
		ipAddrLocalIpAddress					InetAddress,
		ipAddrLocalIpMask					InetAddress,
		ipAddrPhyType					INTEGER,
		ipAddrRackNo					Integer32,
		ipAddrShelfNo					Integer32,
		ipAddrSlotNo					Integer32,
		ipAddrPhyPortId					Integer32,
		ipAddrCfgStatus					INTEGER
		}


	ipAddrIndex		 OBJECT-TYPE
		SYNTAX					 Integer32( 0 .. 3 )
		MAX-ACCESS			 not-accessible
		STATUS					 current
		DESCRIPTION			 " -- "
		::=  { ipAddrEntry  1 }


	ipAddrRowStatus		 OBJECT-TYPE
		SYNTAX					 RowStatus
		MAX-ACCESS			 read-create
		STATUS					 current
		DESCRIPTION			 " -- "
		::=  { ipAddrEntry  2 }


	ipAddrLocalIpAddressType		 OBJECT-TYPE
		SYNTAX					 InetAddressType
		MAX-ACCESS			 read-create
		STATUS					 current
		DESCRIPTION			 " -- "
		::=  { ipAddrEntry  3 }


	ipAddrLocalIpAddress		 OBJECT-TYPE
		SYNTAX					 InetAddress
		MAX-ACCESS			 read-create
		STATUS					 current
		DESCRIPTION			 " -- "
		::=  { ipAddrEntry  4 }


	ipAddrLocalIpMask		 OBJECT-TYPE
		SYNTAX					 InetAddress
		MAX-ACCESS			 read-create
		STATUS					 current
		DESCRIPTION			 " -- "
		::=  { ipAddrEntry  5 }


	ipAddrPhyType		 OBJECT-TYPE
		SYNTAX					 INTEGER{ eth(0),ops(2)  }
		MAX-ACCESS			 read-create
		STATUS					 current
		DESCRIPTION			 " -- "
		::=  { ipAddrEntry  6 }


	ipAddrRackNo		 OBJECT-TYPE
		SYNTAX					 Integer32( 0 .. 0 )
		MAX-ACCESS			 read-create
		STATUS					 current
		DESCRIPTION			 " -- "
		::=  { ipAddrEntry  7 }


	ipAddrShelfNo		 OBJECT-TYPE
		SYNTAX					 Integer32( 0 .. 0 )
		MAX-ACCESS			 read-create
		STATUS					 current
		DESCRIPTION			 " -- "
		::=  { ipAddrEntry  8 }


	ipAddrSlotNo		 OBJECT-TYPE
		SYNTAX					 Integer32( 0 .. 16 )
		MAX-ACCESS			 read-create
		STATUS					 current
		DESCRIPTION			 " -- "
		::=  { ipAddrEntry  9 }


	ipAddrPhyPortId		 OBJECT-TYPE
		SYNTAX					 Integer32( 0 .. 1 )
		MAX-ACCESS			 read-create
		STATUS					 current
		DESCRIPTION			 " -- "
		::=  { ipAddrEntry  10 }


	ipAddrCfgStatus		 OBJECT-TYPE
		SYNTAX					 INTEGER{ unknown(0),ok(3),invalid(-1)  }
		MAX-ACCESS			 read-only
		STATUS					 current
		DESCRIPTION			 " -- "
		::=  { ipAddrEntry  11 }


	ipPathTable		 OBJECT-TYPE
		SYNTAX					 SEQUENCE  OF	 IpPathEntry
		MAX-ACCESS			 not-accessible
		STATUS					 current
		DESCRIPTION			 " -- "
		::=  { ipLogicPort  2 }


	ipPathEntry		 OBJECT-TYPE
		SYNTAX					 IpPathEntry
		MAX-ACCESS			 not-accessible
		STATUS					 current
		DESCRIPTION			 " -- "
		INDEX						{ ipPathIpAddrIndex,ipPathIndex }
		::=  { ipPathTable  1 }


	IpPathEntry		 ::=  SEQUENCE {
		ipPathIpAddrIndex					Integer32,
		ipPathIndex					Integer32,
		ipPathRowStatus					RowStatus,
		ipPathType					INTEGER,
		ipPathMaxTxBandwidth					Integer32,
		ipPathMaxRxBandwidth					Integer32,
		ipPathSetupStatus					INTEGER
		}


	ipPathIpAddrIndex		 OBJECT-TYPE
		SYNTAX					 Integer32( 0 .. 3 )
		MAX-ACCESS			 not-accessible
		STATUS					 current
		DESCRIPTION			 " -- "
		::=  { ipPathEntry  1 }


	ipPathIndex		 OBJECT-TYPE
		SYNTAX					 Integer32( 0 .. 10 )
		MAX-ACCESS			 not-accessible
		STATUS					 current
		DESCRIPTION			 " -- "
		::=  { ipPathEntry  2 }


	ipPathRowStatus		 OBJECT-TYPE
		SYNTAX					 RowStatus
		MAX-ACCESS			 read-create
		STATUS					 current
		DESCRIPTION			 " -- "
		::=  { ipPathEntry  3 }


	ipPathType		 OBJECT-TYPE
		SYNTAX					 INTEGER{ controlPlane(1),userPlane(2)  }
		MAX-ACCESS			 read-create
		STATUS					 current
		DESCRIPTION			 " -- "
		::=  { ipPathEntry  4 }


	ipPathMaxTxBandwidth		 OBJECT-TYPE
		SYNTAX					 Integer32( 32 .. 1000000 )
		MAX-ACCESS			 read-create
		STATUS					 current
		DESCRIPTION			 " -- "
		::=  { ipPathEntry  5 }


	ipPathMaxRxBandwidth		 OBJECT-TYPE
		SYNTAX					 Integer32( 0 .. 1000000 )
		MAX-ACCESS			 read-create
		STATUS					 current
		DESCRIPTION			 " -- "
		::=  { ipPathEntry  6 }


	ipPathSetupStatus		 OBJECT-TYPE
		SYNTAX					 INTEGER{ unknown(0),driverOK(1),ok(3),invalid(-1)  }
		MAX-ACCESS			 read-only
		STATUS					 current
		DESCRIPTION			 " -- "
		::=  { ipPathEntry  7 }


	iubIPPathTable		 OBJECT-TYPE
		SYNTAX					 SEQUENCE  OF	 IubIPPathEntry
		MAX-ACCESS			 not-accessible
		STATUS					 current
		DESCRIPTION			 " -- "
		::=  { ipLogicPort  3 }


	iubIPPathEntry		 OBJECT-TYPE
		SYNTAX					 IubIPPathEntry
		MAX-ACCESS			 not-accessible
		STATUS					 current
		DESCRIPTION			 " -- "
		INDEX						{ iubIPPathIPPortIndex,iubIPPathIndex }
		::=  { iubIPPathTable  1 }


	IubIPPathEntry		 ::=  SEQUENCE {
		iubIPPathIPPortIndex					Integer32,
		iubIPPathIndex					Integer32,
		iubIPPathRowStatus					RowStatus,
		iubIPPathServiceType					INTEGER,
		iubIPPathMaxTxBandwidth					Integer32,
		iubIPPathMaxRxBandwidth					Integer32,
		iubIPPathEnableMacQos					INTEGER,
		iubIPPathVlanId					Integer32,
		iubIPPathSetupStatus					INTEGER,
		iubIPPathMacPri					Integer32,
		iubIPPathDelTrigger					INTEGER,
		iubIPPathMCMLPPPClassNumber					Integer32,
		iubIPPathGuarTxBandwidth					Integer32
		}


	iubIPPathIPPortIndex		 OBJECT-TYPE
		SYNTAX					 Integer32( 0 .. 3 )
		MAX-ACCESS			 not-accessible
		STATUS					 current
		DESCRIPTION			 " -- "
		::=  { iubIPPathEntry  1 }


	iubIPPathIndex		 OBJECT-TYPE
		SYNTAX					 Integer32( 0 .. 7 )
		MAX-ACCESS			 not-accessible
		STATUS					 current
		DESCRIPTION			 " -- "
		::=  { iubIPPathEntry  2 }


	iubIPPathRowStatus		 OBJECT-TYPE
		SYNTAX					 RowStatus
		MAX-ACCESS			 read-create
		STATUS					 current
		DESCRIPTION			 " -- "
		::=  { iubIPPathEntry  3 }


	iubIPPathServiceType		 OBJECT-TYPE
		SYNTAX					 INTEGER{ unknown(0),csSpeech(1),csStreaming(2),csConversational(3),hsdpaStreaming(4),hsdpaInteractive(5),hsdpaBackground(6),hsupaStreaming(7),hsupaInteractive(8),hsupaBackground(9),hsupaConversational(10),r4psStreaming(11),r4psInteractive(12),r4psBackground(13),r4psConversational(14),signaling(15),nbapSignal(16),cch(17),om(18),default(19)  }
		MAX-ACCESS			 read-create
		STATUS					 current
		DESCRIPTION			 " -- "
		::=  { iubIPPathEntry  4 }


	iubIPPathMaxTxBandwidth		 OBJECT-TYPE
		SYNTAX					 Integer32( 32 .. 100000 )
		MAX-ACCESS			 read-create
		STATUS					 current
		DESCRIPTION			 " -- "
		::=  { iubIPPathEntry  5 }


	iubIPPathMaxRxBandwidth		 OBJECT-TYPE
		SYNTAX					 Integer32( 32 .. 100000 )
		MAX-ACCESS			 read-create
		STATUS					 current
		DESCRIPTION			 " -- "
		::=  { iubIPPathEntry  6 }


	iubIPPathEnableMacQos		 OBJECT-TYPE
		SYNTAX					 INTEGER{ disabled(0),enabled(1)  }
		MAX-ACCESS			 read-create
		STATUS					 current
		DESCRIPTION			 " -- "
		::=  { iubIPPathEntry  7 }


	iubIPPathVlanId		 OBJECT-TYPE
		SYNTAX					 Integer32( 0|1 .. 4094 )
		MAX-ACCESS			 read-create
		STATUS					 current
		DESCRIPTION			 " -- "
		::=  { iubIPPathEntry  8 }


	iubIPPathSetupStatus		 OBJECT-TYPE
		SYNTAX					 INTEGER{ unknown(0),driverOK(1),ok(3)  }
		MAX-ACCESS			 read-only
		STATUS					 current
		DESCRIPTION			 " -- "
		::=  { iubIPPathEntry  9 }


	iubIPPathMacPri		 OBJECT-TYPE
		SYNTAX					 Integer32( -1|0 .. 7 )
		MAX-ACCESS			 read-create
		STATUS					 current
		DESCRIPTION			 " -- "
		::=  { iubIPPathEntry  10 }


	iubIPPathDelTrigger		 OBJECT-TYPE
		SYNTAX					 INTEGER{ off(0),on(1)  }
		MAX-ACCESS			 read-write
		STATUS					 current
		DESCRIPTION			 " -- "
		::=  { iubIPPathEntry  11 }


	iubIPPathMCMLPPPClassNumber		 OBJECT-TYPE
		SYNTAX					 Integer32( 0 .. 3 )
		MAX-ACCESS			 read-create
		STATUS					 current
		DESCRIPTION			 " -- "
		::=  { iubIPPathEntry  12 }


	iubIPPathGuarTxBandwidth		 OBJECT-TYPE
		SYNTAX					 Integer32( 32 .. 100000 )
		MAX-ACCESS			 read-create
		STATUS					 current
		DESCRIPTION			 " -- "
		::=  { iubIPPathEntry  13 }


	ipControlLink		 OBJECT IDENTIFIER
		::=  { eNb  4 }


	sctpTable		 OBJECT-TYPE
		SYNTAX					 SEQUENCE  OF	 SctpEntry
		MAX-ACCESS			 not-accessible
		STATUS					 current
		DESCRIPTION			 " -- "
		::=  { ipControlLink  1 }


	sctpEntry		 OBJECT-TYPE
		SYNTAX					 SctpEntry
		MAX-ACCESS			 not-accessible
		STATUS					 current
		DESCRIPTION			 " -- "
		INDEX						{ sctpIndex }
		::=  { sctpTable  1 }


	SctpEntry		 ::=  SEQUENCE {
		sctpIndex					Integer32,
		sctpRowStatus					RowStatus,
		sctpWorkingMode					INTEGER,
		sctpLocalIpAddrIndex1					Integer32,
		sctpLocalIpAddrIndex2					Integer32,
		sctpLocalIpAddrIndex3					Integer32,
		sctpLocalIpAddrIndex4					Integer32,
		sctpPeerIpAddressType					InetAddressType,
		sctpPeerIpAddr1					InetAddress,
		sctpPeerIpAddr2					InetAddress,
		sctpPeerIpAddr3					InetAddress,
		sctpPeerIpAddr4					InetAddress,
		sctpPeerType					INTEGER,
		sctpStatus					INTEGER,
		sctpBlockSwitch					INTEGER,
		sctpResetTrigger					INTEGER,
		sctpSignalBearStatus					INTEGER,
		sctpDataType					INTEGER,
		sctpPeerPortNumber					Integer32,
		sctpDeleteFlag					INTEGER
		}


	sctpIndex		 OBJECT-TYPE
		SYNTAX					 Integer32( 0 .. 81 )
		MAX-ACCESS			 not-accessible
		STATUS					 current
		DESCRIPTION			 " -- "
		::=  { sctpEntry  1 }


	sctpRowStatus		 OBJECT-TYPE
		SYNTAX					 RowStatus
		MAX-ACCESS			 read-create
		STATUS					 current
		DESCRIPTION			 " -- "
		::=  { sctpEntry  2 }


	sctpWorkingMode		 OBJECT-TYPE
		SYNTAX					 INTEGER{ server(0),client(1)  }
		MAX-ACCESS			 read-create
		STATUS					 current
		DESCRIPTION			 " -- "
		::=  { sctpEntry  3 }


	sctpLocalIpAddrIndex1		 OBJECT-TYPE
		SYNTAX					 Integer32( 0 .. 3|-1 )
		MAX-ACCESS			 read-create
		STATUS					 current
		DESCRIPTION			 " -- "
		::=  { sctpEntry  4 }


	sctpLocalIpAddrIndex2		 OBJECT-TYPE
		SYNTAX					 Integer32( 0 .. 3|-1 )
		MAX-ACCESS			 read-create
		STATUS					 current
		DESCRIPTION			 " -- "
		::=  { sctpEntry  5 }


	sctpLocalIpAddrIndex3		 OBJECT-TYPE
		SYNTAX					 Integer32( 0 .. 3|-1 )
		MAX-ACCESS			 read-create
		STATUS					 current
		DESCRIPTION			 " -- "
		::=  { sctpEntry  6 }


	sctpLocalIpAddrIndex4		 OBJECT-TYPE
		SYNTAX					 Integer32( 0 .. 3|-1 )
		MAX-ACCESS			 read-create
		STATUS					 current
		DESCRIPTION			 " -- "
		::=  { sctpEntry  7 }


	sctpPeerIpAddressType		 OBJECT-TYPE
		SYNTAX					 InetAddressType
		MAX-ACCESS			 read-create
		STATUS					 current
		DESCRIPTION			 " -- "
		::=  { sctpEntry  8 }


	sctpPeerIpAddr1		 OBJECT-TYPE
		SYNTAX					 InetAddress
		MAX-ACCESS			 read-create
		STATUS					 current
		DESCRIPTION			 " -- "
		::=  { sctpEntry  9 }


	sctpPeerIpAddr2		 OBJECT-TYPE
		SYNTAX					 InetAddress
		MAX-ACCESS			 read-create
		STATUS					 current
		DESCRIPTION			 " -- "
		::=  { sctpEntry  10 }


	sctpPeerIpAddr3		 OBJECT-TYPE
		SYNTAX					 InetAddress
		MAX-ACCESS			 read-create
		STATUS					 current
		DESCRIPTION			 " -- "
		::=  { sctpEntry  11 }


	sctpPeerIpAddr4		 OBJECT-TYPE
		SYNTAX					 InetAddress
		MAX-ACCESS			 read-create
		STATUS					 current
		DESCRIPTION			 " -- "
		::=  { sctpEntry  12 }


	sctpPeerType		 OBJECT-TYPE
		SYNTAX					 INTEGER{ mme(0),eNB(1),rnc(2)  }
		MAX-ACCESS			 read-create
		STATUS					 current
		DESCRIPTION			 " -- "
		::=  { sctpEntry  13 }


	sctpStatus		 OBJECT-TYPE
		SYNTAX					 INTEGER{ unknown(0),driverCfgOk(1),driverOk(2),ok(3)  }
		MAX-ACCESS			 read-only
		STATUS					 current
		DESCRIPTION			 " -- "
		::=  { sctpEntry  14 }


	sctpBlockSwitch		 OBJECT-TYPE
		SYNTAX					 INTEGER{ block(0),unblock(1)  }
		MAX-ACCESS			 read-write
		STATUS					 current
		DESCRIPTION			 " -- "
		::=  { sctpEntry  15 }


	sctpResetTrigger		 OBJECT-TYPE
		SYNTAX					 INTEGER{ on(0)  }
		MAX-ACCESS			 read-write
		STATUS					 current
		DESCRIPTION			 " -- "
		::=  { sctpEntry  16 }


	sctpSignalBearStatus		 OBJECT-TYPE
		SYNTAX					 INTEGER{ invalid(-1),unknown(0),setup(1),block(2)  }
		MAX-ACCESS			 read-only
		STATUS					 current
		DESCRIPTION			 " -- "
		::=  { sctpEntry  17 }


	sctpDataType		 OBJECT-TYPE
		SYNTAX					 INTEGER{ valid(0),invalid(1)  }
		MAX-ACCESS			 read-only
		STATUS					 current
		DESCRIPTION			 " -- "
		::=  { sctpEntry  18 }


	sctpPeerPortNumber		 OBJECT-TYPE
		SYNTAX					 Integer32( -2147483648 .. 2147483647 )
		MAX-ACCESS			 read-write
		STATUS					 current
		DESCRIPTION			 " -- "
		::=  { sctpEntry  19 }


	sctpDeleteFlag		 OBJECT-TYPE
		SYNTAX					 INTEGER{ off(0),on(1)  }
		MAX-ACCESS			 read-write
		STATUS					 current
		DESCRIPTION			 " -- "
		::=  { sctpEntry  20 }


	sctpStreamTable		 OBJECT-TYPE
		SYNTAX					 SEQUENCE  OF	 SctpStreamEntry
		MAX-ACCESS			 not-accessible
		STATUS					 current
		DESCRIPTION			 " -- "
		::=  { ipControlLink  2 }


	sctpStreamEntry		 OBJECT-TYPE
		SYNTAX					 SctpStreamEntry
		MAX-ACCESS			 not-accessible
		STATUS					 current
		DESCRIPTION			 " -- "
		INDEX						{ sctpStreamSctpIndex,sctpStreamIndex }
		::=  { sctpStreamTable  1 }


	SctpStreamEntry		 ::=  SEQUENCE {
		sctpStreamSctpIndex					Integer32,
		sctpStreamIndex					Integer32,
		sctpStreamRowStatus					RowStatus,
		sctpStreamIdTx					Integer32,
		sctpStreamIdRx					Integer32,
		sctpStreamIsCommonDedi					INTEGER,
		sctpStreamLinkId					Integer32
		}


	sctpStreamSctpIndex		 OBJECT-TYPE
		SYNTAX					 Integer32( 0 .. 81 )
		MAX-ACCESS			 not-accessible
		STATUS					 current
		DESCRIPTION			 " -- "
		::=  { sctpStreamEntry  1 }


	sctpStreamIndex		 OBJECT-TYPE
		SYNTAX					 Integer32( 0 .. 1 )
		MAX-ACCESS			 not-accessible
		STATUS					 current
		DESCRIPTION			 " -- "
		::=  { sctpStreamEntry  2 }


	sctpStreamRowStatus		 OBJECT-TYPE
		SYNTAX					 RowStatus
		MAX-ACCESS			 read-create
		STATUS					 current
		DESCRIPTION			 " -- "
		::=  { sctpStreamEntry  3 }


	sctpStreamIdTx		 OBJECT-TYPE
		SYNTAX					 Integer32( 0 .. 65535 )
		MAX-ACCESS			 read-create
		STATUS					 current
		DESCRIPTION			 " -- "
		::=  { sctpStreamEntry  4 }


	sctpStreamIdRx		 OBJECT-TYPE
		SYNTAX					 Integer32( 0 .. 65535 )
		MAX-ACCESS			 read-create
		STATUS					 current
		DESCRIPTION			 " -- "
		::=  { sctpStreamEntry  5 }


	sctpStreamIsCommonDedi		 OBJECT-TYPE
		SYNTAX					 INTEGER{ common(0),dedicated(1),both(2)  }
		MAX-ACCESS			 read-create
		STATUS					 current
		DESCRIPTION			 " -- "
		::=  { sctpStreamEntry  6 }


	sctpStreamLinkId		 OBJECT-TYPE
		SYNTAX					 Integer32( -2147483648 .. 2147483647 )
		MAX-ACCESS			 read-only
		STATUS					 current
		DESCRIPTION			 " -- "
		::=  { sctpStreamEntry  7 }


	sctpTimer		 OBJECT IDENTIFIER
		::=  { ipControlLink  3 }


	sctpTimerRTOInitial		 OBJECT-TYPE
		SYNTAX					 Unsigned32( 1 .. 120000 )
		MAX-ACCESS			 read-only
		STATUS					 current
		DESCRIPTION			 " -- "
		::=  { sctpTimer  1 }


	sctpTimerRTOMin		 OBJECT-TYPE
		SYNTAX					 Unsigned32( 1 .. 120000 )
		MAX-ACCESS			 read-only
		STATUS					 current
		DESCRIPTION			 " -- "
		::=  { sctpTimer  2 }


	sctpTimerRTOMax		 OBJECT-TYPE
		SYNTAX					 Unsigned32( 1 .. 120000 )
		MAX-ACCESS			 read-only
		STATUS					 current
		DESCRIPTION			 " -- "
		::=  { sctpTimer  3 }


	sctpTimerValidCookieLife		 OBJECT-TYPE
		SYNTAX					 Unsigned32( 1 .. 120 )
		MAX-ACCESS			 read-only
		STATUS					 current
		DESCRIPTION			 " -- "
		::=  { sctpTimer  4 }


	sctpTimerAssocMaxRetrans		 OBJECT-TYPE
		SYNTAX					 Unsigned32( 1 .. 20 )
		MAX-ACCESS			 read-only
		STATUS					 current
		DESCRIPTION			 " -- "
		::=  { sctpTimer  5 }


	sctpTimerPathMaxRetrans		 OBJECT-TYPE
		SYNTAX					 Unsigned32( 1 .. 20 )
		MAX-ACCESS			 read-only
		STATUS					 current
		DESCRIPTION			 " -- "
		::=  { sctpTimer  6 }


	sctpTimerMaxInitRetransmits		 OBJECT-TYPE
		SYNTAX					 Unsigned32( 1 .. 16 )
		MAX-ACCESS			 read-only
		STATUS					 current
		DESCRIPTION			 " -- "
		::=  { sctpTimer  7 }


	sctpTimerHBInterval		 OBJECT-TYPE
		SYNTAX					 Unsigned32( 1 .. 60000 )
		MAX-ACCESS			 read-only
		STATUS					 current
		DESCRIPTION			 " -- "
		::=  { sctpTimer  8 }


	omLinkStatistic		 OBJECT IDENTIFIER
		::=  { ipControlLink  4 }


	omLinkStatInPkts		 OBJECT-TYPE
		SYNTAX					 Unsigned32( 0 .. 4294967295 )
		MAX-ACCESS			 read-only
		STATUS					 current
		DESCRIPTION			 " -- "
		::=  { omLinkStatistic  1 }


	omLinkStatOutPkts		 OBJECT-TYPE
		SYNTAX					 Unsigned32( 0 .. 4294967295 )
		MAX-ACCESS			 read-only
		STATUS					 current
		DESCRIPTION			 " -- "
		::=  { omLinkStatistic  2 }


	iubSCTPStatistic		 OBJECT IDENTIFIER
		::=  { ipControlLink  5 }


	iubSCTPStatInPkts		 OBJECT-TYPE
		SYNTAX					 Unsigned32( 0 .. 4294967295 )
		MAX-ACCESS			 read-only
		STATUS					 current
		DESCRIPTION			 " -- "
		::=  { iubSCTPStatistic  1 }


	iubSCTPStatOutPkts		 OBJECT-TYPE
		SYNTAX					 Unsigned32( 0 .. 4294967295 )
		MAX-ACCESS			 read-only
		STATUS					 current
		DESCRIPTION			 " -- "
		::=  { iubSCTPStatistic  2 }


	iubSCTPStatOutLossPkts		 OBJECT-TYPE
		SYNTAX					 Unsigned32( 0 .. 4294967295 )
		MAX-ACCESS			 read-only
		STATUS					 current
		DESCRIPTION			 " -- "
		::=  { iubSCTPStatistic  3 }


	iubSCTPStatOutLossPktsThreshold		 OBJECT-TYPE
		SYNTAX					 Unsigned32( 0 .. 4294967295 )
		MAX-ACCESS			 read-write
		STATUS					 current
		DESCRIPTION			 " -- "
		::=  { iubSCTPStatistic  4 }


	iubSCTPStatOutLossRateThreshold		 OBJECT-TYPE
		SYNTAX					 Unsigned32( 0 .. 1000 )
		MAX-ACCESS			 read-write
		STATUS					 current
		DESCRIPTION			 " -- "
		::=  { iubSCTPStatistic  5 }


	iubSCTPStatOutLossCheckPeriod		 OBJECT-TYPE
		SYNTAX					 Unsigned32( 0 .. 600 )
		MAX-ACCESS			 read-write
		STATUS					 current
		DESCRIPTION			 " -- "
		::=  { iubSCTPStatistic  6 }


	iubSCTPStatOutLossRateLongThreshold		 OBJECT-TYPE
		SYNTAX					 Unsigned32( 0 .. 1000 )
		MAX-ACCESS			 read-write
		STATUS					 current
		DESCRIPTION			 " -- "
		::=  { iubSCTPStatistic  7 }


	iubSCTPStatOutLossCheckLongPeriod		 OBJECT-TYPE
		SYNTAX					 Unsigned32( 1 .. 24 )
		MAX-ACCESS			 read-write
		STATUS					 current
		DESCRIPTION			 " -- "
		::=  { iubSCTPStatistic  8 }


	ipManagementLink		 OBJECT IDENTIFIER
		::=  { eNb  5 }


	omLinkTable		 OBJECT-TYPE
		SYNTAX					 SEQUENCE  OF	 OmLinkEntry
		MAX-ACCESS			 not-accessible
		STATUS					 current
		DESCRIPTION			 " -- "
		::=  { ipManagementLink  1 }


	omLinkEntry		 OBJECT-TYPE
		SYNTAX					 OmLinkEntry
		MAX-ACCESS			 not-accessible
		STATUS					 current
		DESCRIPTION			 " -- "
		INDEX						{ omLinkIndex }
		::=  { omLinkTable  1 }


	OmLinkEntry		 ::=  SEQUENCE {
		omLinkIndex					Integer32,
		omLinkRowStatus					RowStatus,
		omLinkSetupStatus					INTEGER,
		omLinkLocalIPAddressType					InetAddressType,
		omLinkLocalIPAddress					InetAddress,
		omLinkLocalIpMask					InetAddress,
		omLinkDefaultGWIpAddr					InetAddress,
		omLinkPeerIpAddrType					InetAddressType,
		omLinkPeerIpAddr					InetAddress,
		omLinkMaxTxBandwidth					Integer32,
		omLinkMaxRxBandwidth					Integer32,
		omLinkDSCP					Integer32,
		omLinkEnableMacQos					INTEGER,
		omLinkMacPri					Integer32,
		omLinkVlanId					Integer32,
		omLinkPhyType					INTEGER,
		omLinkRackNo					Integer32,
		omLinkShelfNo					Integer32,
		omLinkSlotNo					Integer32,
		omLinkPhyPortId					Integer32,
		omLinkRecoverTimer					Unsigned32,
		omLinkIsRealTimeValid					INTEGER,
		omLinkNetworkAttribute					INTEGER
		}


	omLinkIndex		 OBJECT-TYPE
		SYNTAX					 Integer32( 0 .. 2 )
		MAX-ACCESS			 not-accessible
		STATUS					 current
		DESCRIPTION			 " -- "
		::=  { omLinkEntry  1 }


	omLinkRowStatus		 OBJECT-TYPE
		SYNTAX					 RowStatus
		MAX-ACCESS			 read-only
		STATUS					 current
		DESCRIPTION			 " -- "
		::=  { omLinkEntry  2 }


	omLinkSetupStatus		 OBJECT-TYPE
		SYNTAX					 INTEGER{ unknown(0),notReady(1),ok(2)  }
		MAX-ACCESS			 read-only
		STATUS					 current
		DESCRIPTION			 " -- "
		::=  { omLinkEntry  3 }


	omLinkLocalIPAddressType		 OBJECT-TYPE
		SYNTAX					 InetAddressType
		MAX-ACCESS			 read-write
		STATUS					 current
		DESCRIPTION			 " -- "
		::=  { omLinkEntry  4 }


	omLinkLocalIPAddress		 OBJECT-TYPE
		SYNTAX					 InetAddress
		MAX-ACCESS			 read-write
		STATUS					 current
		DESCRIPTION			 " -- "
		::=  { omLinkEntry  5 }


	omLinkLocalIpMask		 OBJECT-TYPE
		SYNTAX					 InetAddress
		MAX-ACCESS			 read-write
		STATUS					 current
		DESCRIPTION			 " -- "
		::=  { omLinkEntry  6 }


	omLinkDefaultGWIpAddr		 OBJECT-TYPE
		SYNTAX					 InetAddress
		MAX-ACCESS			 read-write
		STATUS					 current
		DESCRIPTION			 " -- "
		::=  { omLinkEntry  7 }


	omLinkPeerIpAddrType		 OBJECT-TYPE
		SYNTAX					 InetAddressType
		MAX-ACCESS			 read-write
		STATUS					 current
		DESCRIPTION			 " -- "
		::=  { omLinkEntry  8 }


	omLinkPeerIpAddr		 OBJECT-TYPE
		SYNTAX					 InetAddress
		MAX-ACCESS			 read-write
		STATUS					 current
		DESCRIPTION			 " -- "
		::=  { omLinkEntry  9 }


	omLinkMaxTxBandwidth		 OBJECT-TYPE
		SYNTAX					 Integer32( 32 .. 100000 )
		MAX-ACCESS			 read-write
		STATUS					 current
		DESCRIPTION			 " -- "
		::=  { omLinkEntry  10 }


	omLinkMaxRxBandwidth		 OBJECT-TYPE
		SYNTAX					 Integer32( 0 .. 100000 )
		MAX-ACCESS			 read-write
		STATUS					 current
		DESCRIPTION			 " -- "
		::=  { omLinkEntry  11 }


	omLinkDSCP		 OBJECT-TYPE
		SYNTAX					 Integer32( 0 .. 63|-1 )
		MAX-ACCESS			 read-write
		STATUS					 current
		DESCRIPTION			 " -- "
		::=  { omLinkEntry  12 }


	omLinkEnableMacQos		 OBJECT-TYPE
		SYNTAX					 INTEGER{ disabled(0),enabled(1)  }
		MAX-ACCESS			 read-write
		STATUS					 current
		DESCRIPTION			 " -- "
		::=  { omLinkEntry  13 }


	omLinkMacPri		 OBJECT-TYPE
		SYNTAX					 Integer32( 0 .. 7 )
		MAX-ACCESS			 read-write
		STATUS					 current
		DESCRIPTION			 " -- "
		::=  { omLinkEntry  14 }


	omLinkVlanId		 OBJECT-TYPE
		SYNTAX					 Integer32( 0|1 .. 4095 )
		MAX-ACCESS			 read-write
		STATUS					 current
		DESCRIPTION			 " -- "
		::=  { omLinkEntry  15 }


	omLinkPhyType		 OBJECT-TYPE
		SYNTAX					 INTEGER{ eth(0),e1(1),ops(2)  }
		MAX-ACCESS			 read-write
		STATUS					 current
		DESCRIPTION			 " -- "
		::=  { omLinkEntry  16 }


	omLinkRackNo		 OBJECT-TYPE
		SYNTAX					 Integer32( 0 .. 0 )
		MAX-ACCESS			 read-write
		STATUS					 current
		DESCRIPTION			 " -- "
		::=  { omLinkEntry  17 }


	omLinkShelfNo		 OBJECT-TYPE
		SYNTAX					 Integer32( 0 .. 0 )
		MAX-ACCESS			 read-write
		STATUS					 current
		DESCRIPTION			 " -- "
		::=  { omLinkEntry  18 }


	omLinkSlotNo		 OBJECT-TYPE
		SYNTAX					 Integer32( 0 .. 16 )
		MAX-ACCESS			 read-write
		STATUS					 current
		DESCRIPTION			 " -- "
		::=  { omLinkEntry  19 }


	omLinkPhyPortId		 OBJECT-TYPE
		SYNTAX					 Integer32( 0 .. 1 )
		MAX-ACCESS			 read-write
		STATUS					 current
		DESCRIPTION			 " -- "
		::=  { omLinkEntry  20 }


	omLinkRecoverTimer		 OBJECT-TYPE
		SYNTAX					 Unsigned32( 1 .. 86400 )
		MAX-ACCESS			 read-write
		STATUS					 current
		DESCRIPTION			 " -- "
		::=  { omLinkEntry  21 }


	omLinkIsRealTimeValid		 OBJECT-TYPE
		SYNTAX					 INTEGER{ off(0),on(1)  }
		MAX-ACCESS			 read-write
		STATUS					 current
		DESCRIPTION			 " -- "
		::=  { omLinkEntry  22 }


	omLinkNetworkAttribute		 OBJECT-TYPE
		SYNTAX					 INTEGER{ linkTDS(0),lnkTDL(1),linkSingle(2)  }
		MAX-ACCESS			 read-write
		STATUS					 current
		DESCRIPTION			 " -- "
		::=  { omLinkEntry  23 }


	trafficCategory		 OBJECT IDENTIFIER
		::=  { eNb  6 }


	trafficCategoryTable		 OBJECT-TYPE
		SYNTAX					 SEQUENCE  OF	 TrafficCategoryEntry
		MAX-ACCESS			 not-accessible
		STATUS					 current
		DESCRIPTION			 " -- "
		::=  { trafficCategory  1 }


	trafficCategoryEntry		 OBJECT-TYPE
		SYNTAX					 TrafficCategoryEntry
		MAX-ACCESS			 not-accessible
		STATUS					 current
		DESCRIPTION			 " -- "
		INDEX						{ trafficCategoryIndex }
		::=  { trafficCategoryTable  1 }


	TrafficCategoryEntry		 ::=  SEQUENCE {
		trafficCategoryIndex					Integer32,
		trafficCategoryRowStatus					RowStatus,
		trafficCategoryServiceType					INTEGER,
		trafficCategoryQCI					Integer32,
		trafficCategoryDSCP					Integer32,
		trafficCategoryEnableMacQos					INTEGER,
		trafficCategoryMacPri					Integer32
		}


	trafficCategoryIndex		 OBJECT-TYPE
		SYNTAX					 Integer32( 0 .. 15 )
		MAX-ACCESS			 not-accessible
		STATUS					 current
		DESCRIPTION			 " -- "
		::=  { trafficCategoryEntry  1 }


	trafficCategoryRowStatus		 OBJECT-TYPE
		SYNTAX					 RowStatus
		MAX-ACCESS			 read-create
		STATUS					 current
		DESCRIPTION			 " -- "
		::=  { trafficCategoryEntry  2 }


	trafficCategoryServiceType		 OBJECT-TYPE
		SYNTAX					 INTEGER{ unknown(0),userPlane(1),signal(5),handOver(6)  }
		MAX-ACCESS			 read-create
		STATUS					 current
		DESCRIPTION			 " -- "
		::=  { trafficCategoryEntry  3 }


	trafficCategoryQCI		 OBJECT-TYPE
		SYNTAX					 Integer32( 0 .. 255|-1 )
		MAX-ACCESS			 read-create
		STATUS					 current
		DESCRIPTION			 " -- "
		::=  { trafficCategoryEntry  4 }


	trafficCategoryDSCP		 OBJECT-TYPE
		SYNTAX					 Integer32( 0 .. 63|-1 )
		MAX-ACCESS			 read-create
		STATUS					 current
		DESCRIPTION			 " -- "
		::=  { trafficCategoryEntry  5 }


	trafficCategoryEnableMacQos		 OBJECT-TYPE
		SYNTAX					 INTEGER{ disabled(0),enabled(1)  }
		MAX-ACCESS			 read-create
		STATUS					 current
		DESCRIPTION			 " -- "
		::=  { trafficCategoryEntry  6 }


	trafficCategoryMacPri		 OBJECT-TYPE
		SYNTAX					 Integer32( 0 .. 7 )
		MAX-ACCESS			 read-create
		STATUS					 current
		DESCRIPTION			 " -- "
		::=  { trafficCategoryEntry  7 }


	iubTrafficCategoryTypeTable		 OBJECT-TYPE
		SYNTAX					 SEQUENCE  OF	 IubTrafficCategoryTypeEntry
		MAX-ACCESS			 not-accessible
		STATUS					 current
		DESCRIPTION			 " -- "
		::=  { trafficCategory  2 }


	iubTrafficCategoryTypeEntry		 OBJECT-TYPE
		SYNTAX					 IubTrafficCategoryTypeEntry
		MAX-ACCESS			 not-accessible
		STATUS					 current
		DESCRIPTION			 " -- "
		INDEX						{ iubTrafficCategoryTypeIndex }
		::=  { iubTrafficCategoryTypeTable  1 }


	IubTrafficCategoryTypeEntry		 ::=  SEQUENCE {
		iubTrafficCategoryTypeIndex					Integer32,
		iubTrafficCategoryTypeRowStatus					RowStatus,
		iubTrafficCategoryServiceType					INTEGER,
		iubTrafficCategoryType					Integer32,
		iubTrafficCategoryDSCP					Integer32
		}


	iubTrafficCategoryTypeIndex		 OBJECT-TYPE
		SYNTAX					 Integer32( 1 .. 19 )
		MAX-ACCESS			 not-accessible
		STATUS					 current
		DESCRIPTION			 " -- "
		::=  { iubTrafficCategoryTypeEntry  1 }


	iubTrafficCategoryTypeRowStatus		 OBJECT-TYPE
		SYNTAX					 RowStatus
		MAX-ACCESS			 read-create
		STATUS					 current
		DESCRIPTION			 " -- "
		::=  { iubTrafficCategoryTypeEntry  2 }


	iubTrafficCategoryServiceType		 OBJECT-TYPE
		SYNTAX					 INTEGER{ unknown(0),csSpeech(1),csStreaming(2),csConversational(3),hsdpaStreaming(4),hsdpaInteractive(5),hsdpaBackground(6),hsupaStreaming(7),hsupaInteractive(8),hsupaBackground(9),hsupaConversational(10),r4psStreaming(11),r4psInteractive(12),r4psBackground(13),r4psConversational(14),signaling(15),nbapSignal(16),cch(17),om(18),default(19)  }
		MAX-ACCESS			 read-create
		STATUS					 current
		DESCRIPTION			 " -- "
		::=  { iubTrafficCategoryTypeEntry  3 }


	iubTrafficCategoryType		 OBJECT-TYPE
		SYNTAX					 Integer32( -1|0 .. 255 )
		MAX-ACCESS			 read-create
		STATUS					 current
		DESCRIPTION			 " -- "
		::=  { iubTrafficCategoryTypeEntry  4 }


	iubTrafficCategoryDSCP		 OBJECT-TYPE
		SYNTAX					 Integer32( -1|255|0 .. 63 )
		MAX-ACCESS			 read-create
		STATUS					 current
		DESCRIPTION			 " -- "
		::=  { iubTrafficCategoryTypeEntry  5 }


	transCutOver		 OBJECT IDENTIFIER
		::=  { eNb  7 }


	transCutOverTrigger		 OBJECT-TYPE
		SYNTAX					 INTEGER{ off(0),on(1)  }
		MAX-ACCESS			 read-write
		STATUS					 current
		DESCRIPTION			 " -- "
		::=  { transCutOver  1 }


	transCutOverTdsTrigger		 OBJECT-TYPE
		SYNTAX					 INTEGER{ off(0),on(1)  }
		MAX-ACCESS			 read-write
		STATUS					 current
		DESCRIPTION			 " -- "
		::=  { transCutOver  2 }


	reverseOperation		 OBJECT IDENTIFIER
		::=  { eNb  8 }


	reverseOperationTable		 OBJECT-TYPE
		SYNTAX					 SEQUENCE  OF	 ReverseOperationEntry
		MAX-ACCESS			 not-accessible
		STATUS					 current
		DESCRIPTION			 " -- "
		::=  { reverseOperation  1 }


	reverseOperationEntry		 OBJECT-TYPE
		SYNTAX					 ReverseOperationEntry
		MAX-ACCESS			 not-accessible
		STATUS					 current
		DESCRIPTION			 " -- "
		INDEX						{ reverseOperationIndex }
		::=  { reverseOperationTable  1 }


	ReverseOperationEntry		 ::=  SEQUENCE {
		reverseOperationIndex					Integer32,
		reverseOperationRowStatus					RowStatus,
		reverseOperationSrcIPAddress					InetAddress,
		reverseOperationDesIPAddress					InetAddress
		}


	reverseOperationIndex		 OBJECT-TYPE
		SYNTAX					 Integer32( 0 .. 9 )
		MAX-ACCESS			 not-accessible
		STATUS					 current
		DESCRIPTION			 " -- "
		::=  { reverseOperationEntry  1 }


	reverseOperationRowStatus		 OBJECT-TYPE
		SYNTAX					 RowStatus
		MAX-ACCESS			 read-create
		STATUS					 current
		DESCRIPTION			 " -- "
		::=  { reverseOperationEntry  2 }


	reverseOperationSrcIPAddress		 OBJECT-TYPE
		SYNTAX					 InetAddress
		MAX-ACCESS			 read-create
		STATUS					 current
		DESCRIPTION			 " -- "
		::=  { reverseOperationEntry  3 }


	reverseOperationDesIPAddress		 OBJECT-TYPE
		SYNTAX					 InetAddress
		MAX-ACCESS			 read-create
		STATUS					 current
		DESCRIPTION			 " -- "
		::=  { reverseOperationEntry  4 }


	mirrorFunction		 OBJECT IDENTIFIER
		::=  { eNb  9 }


	mirrorSwitch		 OBJECT-TYPE
		SYNTAX					 INTEGER{ off(0),on(1)  }
		MAX-ACCESS			 read-write
		STATUS					 current
		DESCRIPTION			 " -- "
		::=  { mirrorFunction  1 }


	linkAggregation		 OBJECT IDENTIFIER
		::=  { eNb  10 }


	linkAgationSwitch		 OBJECT-TYPE
		SYNTAX					 INTEGER{ off(0),on(1)  }
		MAX-ACCESS			 read-write
		STATUS					 current
		DESCRIPTION			 " -- "
		::=  { linkAggregation  1 }


	routeRelation		 OBJECT IDENTIFIER
		::=  { transport  2 }


	routeRelationTable		 OBJECT-TYPE
		SYNTAX					 SEQUENCE  OF	 RouteRelationEntry
		MAX-ACCESS			 not-accessible
		STATUS					 current
		DESCRIPTION			 " -- "
		::=  { routeRelation  1 }


	routeRelationEntry		 OBJECT-TYPE
		SYNTAX					 RouteRelationEntry
		MAX-ACCESS			 not-accessible
		STATUS					 current
		DESCRIPTION			 " -- "
		INDEX						{ rtRelatIndex }
		::=  { routeRelationTable  1 }


	RouteRelationEntry		 ::=  SEQUENCE {
		rtRelatIndex					Integer32,
		rtRelatRowStatus					RowStatus,
		rtRelatPeerIpType					InetAddressType,
		rtRelatPeerIp					InetAddress,
		rtRelatPeerIpMask					InetAddress,
		rtRelatGatewayIpAddress					InetAddress
		}


	rtRelatIndex		 OBJECT-TYPE
		SYNTAX					 Integer32( 0 .. 199 )
		MAX-ACCESS			 not-accessible
		STATUS					 current
		DESCRIPTION			 " -- "
		::=  { routeRelationEntry  1 }


	rtRelatRowStatus		 OBJECT-TYPE
		SYNTAX					 RowStatus
		MAX-ACCESS			 read-create
		STATUS					 current
		DESCRIPTION			 " -- "
		::=  { routeRelationEntry  2 }


	rtRelatPeerIpType		 OBJECT-TYPE
		SYNTAX					 InetAddressType
		MAX-ACCESS			 read-create
		STATUS					 current
		DESCRIPTION			 " -- "
		::=  { routeRelationEntry  3 }


	rtRelatPeerIp		 OBJECT-TYPE
		SYNTAX					 InetAddress
		MAX-ACCESS			 read-create
		STATUS					 current
		DESCRIPTION			 " -- "
		::=  { routeRelationEntry  4 }


	rtRelatPeerIpMask		 OBJECT-TYPE
		SYNTAX					 InetAddress
		MAX-ACCESS			 read-create
		STATUS					 current
		DESCRIPTION			 " -- "
		::=  { routeRelationEntry  5 }


	rtRelatGatewayIpAddress		 OBJECT-TYPE
		SYNTAX					 InetAddress
		MAX-ACCESS			 read-create
		STATUS					 current
		DESCRIPTION			 " -- "
		::=  { routeRelationEntry  6 }


	vlanConfig		 OBJECT IDENTIFIER
		::=  { transport  3 }


	vlanIdTable		 OBJECT-TYPE
		SYNTAX					 SEQUENCE  OF	 VlanIdEntry
		MAX-ACCESS			 not-accessible
		STATUS					 current
		DESCRIPTION			 " -- "
		::=  { vlanConfig  1 }


	vlanIdEntry		 OBJECT-TYPE
		SYNTAX					 VlanIdEntry
		MAX-ACCESS			 not-accessible
		STATUS					 current
		DESCRIPTION			 " -- "
		INDEX						{ vlanConfigIndex }
		::=  { vlanIdTable  1 }


	VlanIdEntry		 ::=  SEQUENCE {
		vlanConfigIndex					Integer32,
		vlanConfigRowStatus					RowStatus,
		vlanConfigVlanId					Integer32,
		vlanConfigType					INTEGER,
		vlanConfigIpAddressType					InetAddressType,
		vlanConfigNtHpIpAddress					InetAddress
		}


	vlanConfigIndex		 OBJECT-TYPE
		SYNTAX					 Integer32( 0 .. 7 )
		MAX-ACCESS			 not-accessible
		STATUS					 current
		DESCRIPTION			 " -- "
		::=  { vlanIdEntry  1 }


	vlanConfigRowStatus		 OBJECT-TYPE
		SYNTAX					 RowStatus
		MAX-ACCESS			 read-create
		STATUS					 current
		DESCRIPTION			 " -- "
		::=  { vlanIdEntry  2 }


	vlanConfigVlanId		 OBJECT-TYPE
		SYNTAX					 Integer32( 0|1 .. 4095 )
		MAX-ACCESS			 read-create
		STATUS					 current
		DESCRIPTION			 " -- "
		::=  { vlanIdEntry  3 }


	vlanConfigType		 OBJECT-TYPE
		SYNTAX					 INTEGER{ x2(0),s1Mme(1),s1User(2),x2User(3),default(100)  }
		MAX-ACCESS			 read-create
		STATUS					 current
		DESCRIPTION			 " -- "
		::=  { vlanIdEntry  4 }


	vlanConfigIpAddressType		 OBJECT-TYPE
		SYNTAX					 InetAddressType
		MAX-ACCESS			 read-create
		STATUS					 current
		DESCRIPTION			 " -- "
		::=  { vlanIdEntry  5 }


	vlanConfigNtHpIpAddress		 OBJECT-TYPE
		SYNTAX					 InetAddress
		MAX-ACCESS			 read-create
		STATUS					 current
		DESCRIPTION			 " -- "
		::=  { vlanIdEntry  6 }


	detection		 OBJECT IDENTIFIER
		::=  { transport  4 }


	ethernetOAMTable		 OBJECT-TYPE
		SYNTAX					 SEQUENCE  OF	 EthernetOAMEntry
		MAX-ACCESS			 not-accessible
		STATUS					 current
		DESCRIPTION			 " -- "
		::=  { detection  1 }


	ethernetOAMEntry		 OBJECT-TYPE
		SYNTAX					 EthernetOAMEntry
		MAX-ACCESS			 not-accessible
		STATUS					 current
		DESCRIPTION			 " -- "
		INDEX						{ ethernetOAMIndex }
		::=  { ethernetOAMTable  1 }


	EthernetOAMEntry		 ::=  SEQUENCE {
		ethernetOAMIndex					Integer32,
		ethernetOAMRowStatus					RowStatus,
		ethernetOAMEnable					INTEGER,
		ethernetOAMMode					INTEGER,
		ethernetOAMLoopbackEnable					INTEGER,
		ethernetOAMUnitPerSec					Integer32,
		ethernetOAMPDUMaxLength					Integer32,
		ethernetOAMPeerMac					MacAddress,
		ethernetOAMDiscoveryState					INTEGER,
		ethernetOAMSendLinkState					INTEGER,
		ethernetOAMReceiveLinkState					INTEGER,
		ethernetOAMLoopbackCounts					Unsigned32,
		ethernetOAMShelfNo					Integer32,
		ethernetOAMSlotNo					Integer32,
		ethernetOAMPhyPortId					Integer32,
		ethernetOAMLoopbackTxCounts					Unsigned32
		}


	ethernetOAMIndex		 OBJECT-TYPE
		SYNTAX					 Integer32( 0 .. 2 )
		MAX-ACCESS			 not-accessible
		STATUS					 current
		DESCRIPTION			 " -- "
		::=  { ethernetOAMEntry  1 }


	ethernetOAMRowStatus		 OBJECT-TYPE
		SYNTAX					 RowStatus
		MAX-ACCESS			 read-create
		STATUS					 current
		DESCRIPTION			 " -- "
		::=  { ethernetOAMEntry  2 }


	ethernetOAMEnable		 OBJECT-TYPE
		SYNTAX					 INTEGER{ disabled(0),enabled(1)  }
		MAX-ACCESS			 read-create
		STATUS					 current
		DESCRIPTION			 " -- "
		::=  { ethernetOAMEntry  3 }


	ethernetOAMMode		 OBJECT-TYPE
		SYNTAX					 INTEGER{ active(0),passive(1)  }
		MAX-ACCESS			 read-create
		STATUS					 current
		DESCRIPTION			 " -- "
		::=  { ethernetOAMEntry  4 }


	ethernetOAMLoopbackEnable		 OBJECT-TYPE
		SYNTAX					 INTEGER{ disabled(0),enabled(1)  }
		MAX-ACCESS			 read-create
		STATUS					 current
		DESCRIPTION			 " -- "
		::=  { ethernetOAMEntry  5 }


	ethernetOAMUnitPerSec		 OBJECT-TYPE
		SYNTAX					 Integer32( 1 .. 10 )
		MAX-ACCESS			 read-create
		STATUS					 current
		DESCRIPTION			 " -- "
		::=  { ethernetOAMEntry  6 }


	ethernetOAMPDUMaxLength		 OBJECT-TYPE
		SYNTAX					 Integer32( 64 .. 2047 )
		MAX-ACCESS			 read-create
		STATUS					 current
		DESCRIPTION			 " -- "
		::=  { ethernetOAMEntry  7 }


	ethernetOAMPeerMac		 OBJECT-TYPE
		SYNTAX					 MacAddress
		MAX-ACCESS			 read-only
		STATUS					 current
		DESCRIPTION			 " -- "
		::=  { ethernetOAMEntry  8 }


	ethernetOAMDiscoveryState		 OBJECT-TYPE
		SYNTAX					 INTEGER{ beign(0),fault(1),activeSendLocal(2),passiveWait(3),localUnsatisfied(4),remoteUnsatisfied(5),sendANY(6)  }
		MAX-ACCESS			 read-only
		STATUS					 current
		DESCRIPTION			 " -- "
		::=  { ethernetOAMEntry  9 }


	ethernetOAMSendLinkState		 OBJECT-TYPE
		SYNTAX					 INTEGER{ well(0),fault(1)  }
		MAX-ACCESS			 read-only
		STATUS					 current
		DESCRIPTION			 " -- "
		::=  { ethernetOAMEntry  10 }


	ethernetOAMReceiveLinkState		 OBJECT-TYPE
		SYNTAX					 INTEGER{ well(0),fault(1)  }
		MAX-ACCESS			 read-only
		STATUS					 current
		DESCRIPTION			 " -- "
		::=  { ethernetOAMEntry  11 }


	ethernetOAMLoopbackCounts		 OBJECT-TYPE
		SYNTAX					 Unsigned32( 0 .. 4294967295 )
		MAX-ACCESS			 read-only
		STATUS					 current
		DESCRIPTION			 " -- "
		::=  { ethernetOAMEntry  12 }


	ethernetOAMShelfNo		 OBJECT-TYPE
		SYNTAX					 Integer32( 0 .. 0 )
		MAX-ACCESS			 read-create
		STATUS					 current
		DESCRIPTION			 " -- "
		::=  { ethernetOAMEntry  13 }


	ethernetOAMSlotNo		 OBJECT-TYPE
		SYNTAX					 Integer32( 0 .. 7 )
		MAX-ACCESS			 read-create
		STATUS					 current
		DESCRIPTION			 " -- "
		::=  { ethernetOAMEntry  14 }


	ethernetOAMPhyPortId		 OBJECT-TYPE
		SYNTAX					 Integer32( 0 .. 2 )
		MAX-ACCESS			 read-create
		STATUS					 current
		DESCRIPTION			 " -- "
		::=  { ethernetOAMEntry  15 }


	ethernetOAMLoopbackTxCounts		 OBJECT-TYPE
		SYNTAX					 Unsigned32( 0 .. 4294967295 )
		MAX-ACCESS			 read-only
		STATUS					 current
		DESCRIPTION			 " -- "
		::=  { ethernetOAMEntry  16 }


	bfdTable		 OBJECT-TYPE
		SYNTAX					 SEQUENCE  OF	 BfdEntry
		MAX-ACCESS			 not-accessible
		STATUS					 current
		DESCRIPTION			 " -- "
		::=  { detection  2 }


	bfdEntry		 OBJECT-TYPE
		SYNTAX					 BfdEntry
		MAX-ACCESS			 not-accessible
		STATUS					 current
		DESCRIPTION			 " -- "
		INDEX						{ bfdIndex }
		::=  { bfdTable  1 }


	BfdEntry		 ::=  SEQUENCE {
		bfdIndex					Integer32,
		bfdRowStatus					RowStatus,
		bfdLocalIpAddrIndex					Integer32,
		bfdPeerIPAddressType					InetAddressType,
		bfdPeerIPAddress					InetAddress,
		bfdDetectMulti					Unsigned32,
		bfdMode					INTEGER,
		bfdWorkMode					INTEGER,
		bfdMinTxInterval					Unsigned32,
		bfdMinRxInterval					Unsigned32,
		bfdEchoInterval					Unsigned32,
		bfdEchoTimes					Unsigned32
		}


	bfdIndex		 OBJECT-TYPE
		SYNTAX					 Integer32( 0 .. 31 )
		MAX-ACCESS			 not-accessible
		STATUS					 current
		DESCRIPTION			 " -- "
		::=  { bfdEntry  1 }


	bfdRowStatus		 OBJECT-TYPE
		SYNTAX					 RowStatus
		MAX-ACCESS			 read-create
		STATUS					 current
		DESCRIPTION			 " -- "
		::=  { bfdEntry  2 }


	bfdLocalIpAddrIndex		 OBJECT-TYPE
		SYNTAX					 Integer32( 0 .. 3|-1 )
		MAX-ACCESS			 read-create
		STATUS					 current
		DESCRIPTION			 " -- "
		::=  { bfdEntry  3 }


	bfdPeerIPAddressType		 OBJECT-TYPE
		SYNTAX					 InetAddressType
		MAX-ACCESS			 read-write
		STATUS					 current
		DESCRIPTION			 " -- "
		::=  { bfdEntry  4 }


	bfdPeerIPAddress		 OBJECT-TYPE
		SYNTAX					 InetAddress
		MAX-ACCESS			 read-write
		STATUS					 current
		DESCRIPTION			 " -- "
		::=  { bfdEntry  5 }


	bfdDetectMulti		 OBJECT-TYPE
		SYNTAX					 Unsigned32( 1 .. 255 )
		MAX-ACCESS			 read-write
		STATUS					 current
		DESCRIPTION			 " -- "
		::=  { bfdEntry  6 }


	bfdMode		 OBJECT-TYPE
		SYNTAX					 INTEGER{ selfdetect(0),manudetect(1)  }
		MAX-ACCESS			 read-write
		STATUS					 current
		DESCRIPTION			 " -- "
		::=  { bfdEntry  7 }


	bfdWorkMode		 OBJECT-TYPE
		SYNTAX					 INTEGER{ async(1),demand(2)  }
		MAX-ACCESS			 read-write
		STATUS					 current
		DESCRIPTION			 " -- "
		::=  { bfdEntry  8 }


	bfdMinTxInterval		 OBJECT-TYPE
		SYNTAX					 Unsigned32( 100 .. 10000 )
		MAX-ACCESS			 read-write
		STATUS					 current
		DESCRIPTION			 " -- "
		::=  { bfdEntry  9 }


	bfdMinRxInterval		 OBJECT-TYPE
		SYNTAX					 Unsigned32( 100 .. 10000 )
		MAX-ACCESS			 read-write
		STATUS					 current
		DESCRIPTION			 " -- "
		::=  { bfdEntry  10 }


	bfdEchoInterval		 OBJECT-TYPE
		SYNTAX					 Unsigned32( 100 .. 10000 )
		MAX-ACCESS			 read-write
		STATUS					 current
		DESCRIPTION			 " -- "
		::=  { bfdEntry  11 }


	bfdEchoTimes		 OBJECT-TYPE
		SYNTAX					 Unsigned32( 0 .. 4294967295 )
		MAX-ACCESS			 read-write
		STATUS					 current
		DESCRIPTION			 " -- "
		::=  { bfdEntry  12 }


	qolTable		 OBJECT-TYPE
		SYNTAX					 SEQUENCE  OF	 QolEntry
		MAX-ACCESS			 not-accessible
		STATUS					 current
		DESCRIPTION			 " -- "
		::=  { detection  3 }


	qolEntry		 OBJECT-TYPE
		SYNTAX					 QolEntry
		MAX-ACCESS			 not-accessible
		STATUS					 current
		DESCRIPTION			 " -- "
		INDEX						{ qolIndex }
		::=  { qolTable  1 }


	QolEntry		 ::=  SEQUENCE {
		qolIndex					Integer32,
		qolRowStatus					RowStatus,
		qolLocalIpAddrIndex					Integer32,
		qolPeerIPAddressType					InetAddressType,
		qolPeerIPAddress					InetAddress,
		qolMode					INTEGER,
		qolEchoTimes					Unsigned32,
		qolEchoMaxDelay					Unsigned32,
		qolEchoMinDelay					Unsigned32,
		qolEchoAvgDelay					Unsigned32,
		qolEchoLoss					Unsigned32
		}


	qolIndex		 OBJECT-TYPE
		SYNTAX					 Integer32( 0 .. 31 )
		MAX-ACCESS			 not-accessible
		STATUS					 current
		DESCRIPTION			 " -- "
		::=  { qolEntry  1 }


	qolRowStatus		 OBJECT-TYPE
		SYNTAX					 RowStatus
		MAX-ACCESS			 read-create
		STATUS					 current
		DESCRIPTION			 " -- "
		::=  { qolEntry  2 }


	qolLocalIpAddrIndex		 OBJECT-TYPE
		SYNTAX					 Integer32( 0 .. 3|-1 )
		MAX-ACCESS			 read-create
		STATUS					 current
		DESCRIPTION			 " -- "
		::=  { qolEntry  3 }


	qolPeerIPAddressType		 OBJECT-TYPE
		SYNTAX					 InetAddressType
		MAX-ACCESS			 read-create
		STATUS					 current
		DESCRIPTION			 " -- "
		::=  { qolEntry  4 }


	qolPeerIPAddress		 OBJECT-TYPE
		SYNTAX					 InetAddress
		MAX-ACCESS			 read-create
		STATUS					 current
		DESCRIPTION			 " -- "
		::=  { qolEntry  5 }


	qolMode		 OBJECT-TYPE
		SYNTAX					 INTEGER{ bfd(0),ping(1)  }
		MAX-ACCESS			 read-create
		STATUS					 current
		DESCRIPTION			 " -- "
		::=  { qolEntry  6 }


	qolEchoTimes		 OBJECT-TYPE
		SYNTAX					 Unsigned32( 0 .. 4294967295 )
		MAX-ACCESS			 read-create
		STATUS					 current
		DESCRIPTION			 " -- "
		::=  { qolEntry  7 }


	qolEchoMaxDelay		 OBJECT-TYPE
		SYNTAX					 Unsigned32( 0 .. 4294967295 )
		MAX-ACCESS			 read-only
		STATUS					 current
		DESCRIPTION			 " -- "
		::=  { qolEntry  8 }


	qolEchoMinDelay		 OBJECT-TYPE
		SYNTAX					 Unsigned32( 0 .. 4294967295 )
		MAX-ACCESS			 read-only
		STATUS					 current
		DESCRIPTION			 " -- "
		::=  { qolEntry  9 }


	qolEchoAvgDelay		 OBJECT-TYPE
		SYNTAX					 Unsigned32( 0 .. 4294967295 )
		MAX-ACCESS			 read-only
		STATUS					 current
		DESCRIPTION			 " -- "
		::=  { qolEntry  10 }


	qolEchoLoss		 OBJECT-TYPE
		SYNTAX					 Unsigned32( 0 .. 4294967295 )
		MAX-ACCESS			 read-only
		STATUS					 current
		DESCRIPTION			 " -- "
		::=  { qolEntry  11 }


	gtpuFailInfoTable		 OBJECT-TYPE
		SYNTAX					 SEQUENCE  OF	 GtpuFailInfoEntry
		MAX-ACCESS			 not-accessible
		STATUS					 current
		DESCRIPTION			 " -- "
		::=  { detection  4 }


	gtpuFailInfoEntry		 OBJECT-TYPE
		SYNTAX					 GtpuFailInfoEntry
		MAX-ACCESS			 not-accessible
		STATUS					 current
		DESCRIPTION			 " -- "
		INDEX						{ gfiIndex }
		::=  { gtpuFailInfoTable  1 }


	GtpuFailInfoEntry		 ::=  SEQUENCE {
		gfiIndex					Integer32,
		gfiRowStatus					RowStatus,
		gfiEnbIPAddress					InetAddress,
		gfiSgwIPAddress					InetAddress,
		gfiTimeStamp					Unsigned32
		}


	gfiIndex		 OBJECT-TYPE
		SYNTAX					 Integer32( 0 .. 99 )
		MAX-ACCESS			 not-accessible
		STATUS					 current
		DESCRIPTION			 " -- "
		::=  { gtpuFailInfoEntry  1 }


	gfiRowStatus		 OBJECT-TYPE
		SYNTAX					 RowStatus
		MAX-ACCESS			 read-only
		STATUS					 current
		DESCRIPTION			 " -- "
		::=  { gtpuFailInfoEntry  2 }


	gfiEnbIPAddress		 OBJECT-TYPE
		SYNTAX					 InetAddress
		MAX-ACCESS			 read-only
		STATUS					 current
		DESCRIPTION			 " -- "
		::=  { gtpuFailInfoEntry  3 }


	gfiSgwIPAddress		 OBJECT-TYPE
		SYNTAX					 InetAddress
		MAX-ACCESS			 read-only
		STATUS					 current
		DESCRIPTION			 " -- "
		::=  { gtpuFailInfoEntry  4 }


	gfiTimeStamp		 OBJECT-TYPE
		SYNTAX					 Unsigned32( 0 .. 4294967295 )
		MAX-ACCESS			 read-only
		STATUS					 current
		DESCRIPTION			 " -- "
		::=  { gtpuFailInfoEntry  5 }


	twampLinkTable		 OBJECT-TYPE
		SYNTAX					 SEQUENCE  OF	 TwampLinkEntry
		MAX-ACCESS			 not-accessible
		STATUS					 current
		DESCRIPTION			 " -- "
		::=  { detection  5 }


	twampLinkEntry		 OBJECT-TYPE
		SYNTAX					 TwampLinkEntry
		MAX-ACCESS			 not-accessible
		STATUS					 current
		DESCRIPTION			 " -- "
		INDEX						{ twampLinkIndex }
		::=  { twampLinkTable  1 }


	TwampLinkEntry		 ::=  SEQUENCE {
		twampLinkIndex					Integer32,
		twampRowStatus					RowStatus,
		twampLinkType					INTEGER,
		twampLinkIPAddressType					InetAddressType,
		twampRemoteIPAddr					InetAddress,
		twampLocalIPAddrIndex					Integer32,
		twampLocalPort					Integer32
		}


	twampLinkIndex		 OBJECT-TYPE
		SYNTAX					 Integer32( 0 .. 15 )
		MAX-ACCESS			 not-accessible
		STATUS					 current
		DESCRIPTION			 " -- "
		::=  { twampLinkEntry  1 }


	twampRowStatus		 OBJECT-TYPE
		SYNTAX					 RowStatus
		MAX-ACCESS			 read-create
		STATUS					 current
		DESCRIPTION			 " -- "
		::=  { twampLinkEntry  2 }


	twampLinkType		 OBJECT-TYPE
		SYNTAX					 INTEGER{ responderLight(0),responderFull(1)  }
		MAX-ACCESS			 read-create
		STATUS					 current
		DESCRIPTION			 " -- "
		::=  { twampLinkEntry  3 }


	twampLinkIPAddressType		 OBJECT-TYPE
		SYNTAX					 InetAddressType
		MAX-ACCESS			 read-create
		STATUS					 current
		DESCRIPTION			 " -- "
		::=  { twampLinkEntry  4 }


	twampRemoteIPAddr		 OBJECT-TYPE
		SYNTAX					 InetAddress
		MAX-ACCESS			 read-create
		STATUS					 current
		DESCRIPTION			 " -- "
		::=  { twampLinkEntry  5 }


	twampLocalIPAddrIndex		 OBJECT-TYPE
		SYNTAX					 Integer32( 0 .. 5 )
		MAX-ACCESS			 read-create
		STATUS					 current
		DESCRIPTION			 " -- "
		::=  { twampLinkEntry  6 }


	twampLocalPort		 OBJECT-TYPE
		SYNTAX					 Integer32( 0 .. 65535 )
		MAX-ACCESS			 read-create
		STATUS					 current
		DESCRIPTION			 " -- "
		::=  { twampLinkEntry  7 }


	arpStatus		 OBJECT IDENTIFIER
		::=  { transport  5 }


	arpStatusTable		 OBJECT-TYPE
		SYNTAX					 SEQUENCE  OF	 ArpStatusEntry
		MAX-ACCESS			 not-accessible
		STATUS					 current
		DESCRIPTION			 " -- "
		::=  { arpStatus  1 }


	arpStatusEntry		 OBJECT-TYPE
		SYNTAX					 ArpStatusEntry
		MAX-ACCESS			 not-accessible
		STATUS					 current
		DESCRIPTION			 " -- "
		INDEX						{ arpStatusIndex }
		::=  { arpStatusTable  1 }


	ArpStatusEntry		 ::=  SEQUENCE {
		arpStatusIndex					Integer32,
		arpStatusRowStatus					RowStatus,
		arpStatusDstIp					InetAddress,
		arpStatusDstMac					MacAddress,
		arpStatusVlanId					Integer32,
		arpStatusMacStatus					INTEGER
		}


	arpStatusIndex		 OBJECT-TYPE
		SYNTAX					 Integer32( 0 .. 100 )
		MAX-ACCESS			 not-accessible
		STATUS					 current
		DESCRIPTION			 " -- "
		::=  { arpStatusEntry  1 }


	arpStatusRowStatus		 OBJECT-TYPE
		SYNTAX					 RowStatus
		MAX-ACCESS			 read-only
		STATUS					 current
		DESCRIPTION			 " -- "
		::=  { arpStatusEntry  2 }


	arpStatusDstIp		 OBJECT-TYPE
		SYNTAX					 InetAddress
		MAX-ACCESS			 read-only
		STATUS					 current
		DESCRIPTION			 " -- "
		::=  { arpStatusEntry  4 }


	arpStatusDstMac		 OBJECT-TYPE
		SYNTAX					 MacAddress
		MAX-ACCESS			 read-only
		STATUS					 current
		DESCRIPTION			 " -- "
		::=  { arpStatusEntry  5 }


	arpStatusVlanId		 OBJECT-TYPE
		SYNTAX					 Integer32( 0|1 .. 4095 )
		MAX-ACCESS			 read-only
		STATUS					 current
		DESCRIPTION			 " -- "
		::=  { arpStatusEntry  6 }


	arpStatusMacStatus		 OBJECT-TYPE
		SYNTAX					 INTEGER{ valid(0),learning(1),aged(2)  }
		MAX-ACCESS			 read-only
		STATUS					 current
		DESCRIPTION			 " -- "
		::=  { arpStatusEntry  7 }


	arpConfigInfo		 OBJECT IDENTIFIER
		::=  { arpStatus  2 }


	arpAgedPeriod		 OBJECT-TYPE
		SYNTAX					 Unsigned32( 1 .. 3600 )
		MAX-ACCESS			 read-write
		STATUS					 current
		DESCRIPTION			 " -- "
		::=  { arpConfigInfo  1 }


	arpLearningPeriod		 OBJECT-TYPE
		SYNTAX					 Unsigned32( 1 .. 60 )
		MAX-ACCESS			 read-write
		STATUS					 current
		DESCRIPTION			 " -- "
		::=  { arpConfigInfo  2 }


	saal		 OBJECT IDENTIFIER
		::=  { transport  6 }


	saalStatisticInfo		 OBJECT IDENTIFIER
		::=  { saal  1 }


	saalPeakRate		 OBJECT-TYPE
		SYNTAX					 Unsigned32( 0 .. 4294967295 )
		MAX-ACCESS			 read-only
		STATUS					 current
		DESCRIPTION			 " -- "
		::=  { saalStatisticInfo  1 }


	saalValleyRate		 OBJECT-TYPE
		SYNTAX					 Unsigned32( 0 .. 4294967295 )
		MAX-ACCESS			 read-only
		STATUS					 current
		DESCRIPTION			 " -- "
		::=  { saalStatisticInfo  2 }


	saalAverageRate		 OBJECT-TYPE
		SYNTAX					 Unsigned32( 0 .. 4294967295 )
		MAX-ACCESS			 read-only
		STATUS					 current
		DESCRIPTION			 " -- "
		::=  { saalStatisticInfo  3 }


	saalRateStatisticPeriod		 OBJECT-TYPE
		SYNTAX					 Integer32( 0|5 .. 1440 )
		MAX-ACCESS			 read-write
		STATUS					 current
		DESCRIPTION			 " -- "
		::=  { saalStatisticInfo  4 }


	atmTransport		 OBJECT IDENTIFIER
		::=  { transport  7 }


	atmTransportInfo		 OBJECT IDENTIFIER
		::=  { atmTransport  1 }


	iubImaGrpTable		 OBJECT-TYPE
		SYNTAX					 SEQUENCE  OF	 IubImaGrpEntry
		MAX-ACCESS			 not-accessible
		STATUS					 current
		DESCRIPTION			 " -- "
		::=  { atmTransportInfo  1 }


	iubImaGrpEntry		 OBJECT-TYPE
		SYNTAX					 IubImaGrpEntry
		MAX-ACCESS			 not-accessible
		STATUS					 current
		DESCRIPTION			 " -- "
		INDEX						{ iubImaGrpSlotId,iubImaGrpIndex }
		::=  { iubImaGrpTable  1 }


	IubImaGrpEntry		 ::=  SEQUENCE {
		iubImaGrpSlotId					Integer32,
		iubImaGrpIndex					Integer32,
		iubImaGrpRowStatus					RowStatus,
		iubImaGrpId					Integer32,
		iubImaGrpActiveStatus					INTEGER,
		iubImaGrpIsIpoa					INTEGER
		}


	iubImaGrpSlotId		 OBJECT-TYPE
		SYNTAX					 Integer32( 0 .. 5 )
		MAX-ACCESS			 not-accessible
		STATUS					 current
		DESCRIPTION			 " -- "
		::=  { iubImaGrpEntry  1 }


	iubImaGrpIndex		 OBJECT-TYPE
		SYNTAX					 Integer32( 0 .. 1 )
		MAX-ACCESS			 not-accessible
		STATUS					 current
		DESCRIPTION			 " -- "
		::=  { iubImaGrpEntry  2 }


	iubImaGrpRowStatus		 OBJECT-TYPE
		SYNTAX					 RowStatus
		MAX-ACCESS			 read-only
		STATUS					 current
		DESCRIPTION			 " -- "
		::=  { iubImaGrpEntry  3 }


	iubImaGrpId		 OBJECT-TYPE
		SYNTAX					 Integer32( -1|0 .. 3 )
		MAX-ACCESS			 read-only
		STATUS					 current
		DESCRIPTION			 " -- "
		::=  { iubImaGrpEntry  4 }


	iubImaGrpActiveStatus		 OBJECT-TYPE
		SYNTAX					 INTEGER{ inactive(0),active(1),invalid(2)  }
		MAX-ACCESS			 read-only
		STATUS					 current
		DESCRIPTION			 " -- "
		::=  { iubImaGrpEntry  5 }


	iubImaGrpIsIpoa		 OBJECT-TYPE
		SYNTAX					 INTEGER{ notIpoa(0),isIpoa(1)  }
		MAX-ACCESS			 read-only
		STATUS					 current
		DESCRIPTION			 " -- "
		::=  { iubImaGrpEntry  6 }


	iubOFPortTable		 OBJECT-TYPE
		SYNTAX					 SEQUENCE  OF	 IubOFPortEntry
		MAX-ACCESS			 not-accessible
		STATUS					 current
		DESCRIPTION			 " -- "
		::=  { atmTransportInfo  2 }


	iubOFPortEntry		 OBJECT-TYPE
		SYNTAX					 IubOFPortEntry
		MAX-ACCESS			 not-accessible
		STATUS					 current
		DESCRIPTION			 " -- "
		INDEX						{ iubOFPortSlotId,iubOFPortPhyPortId }
		::=  { iubOFPortTable  1 }


	IubOFPortEntry		 ::=  SEQUENCE {
		iubOFPortSlotId					Integer32,
		iubOFPortPhyPortId					Integer32,
		iubOFPortRowStatus					RowStatus,
		iubOFPortActiveStatus					INTEGER,
		iubOFPortPortId					Integer32,
		iubOFPortIsOMLink					INTEGER
		}


	iubOFPortSlotId		 OBJECT-TYPE
		SYNTAX					 Integer32( 0 .. 5 )
		MAX-ACCESS			 not-accessible
		STATUS					 current
		DESCRIPTION			 " -- "
		::=  { iubOFPortEntry  1 }


	iubOFPortPhyPortId		 OBJECT-TYPE
		SYNTAX					 Integer32( 0 .. 1 )
		MAX-ACCESS			 not-accessible
		STATUS					 current
		DESCRIPTION			 " -- "
		::=  { iubOFPortEntry  2 }


	iubOFPortRowStatus		 OBJECT-TYPE
		SYNTAX					 RowStatus
		MAX-ACCESS			 read-only
		STATUS					 current
		DESCRIPTION			 " -- "
		::=  { iubOFPortEntry  3 }


	iubOFPortActiveStatus		 OBJECT-TYPE
		SYNTAX					 INTEGER{ inactive(0),active(1)  }
		MAX-ACCESS			 read-only
		STATUS					 current
		DESCRIPTION			 " -- "
		::=  { iubOFPortEntry  4 }


	iubOFPortPortId		 OBJECT-TYPE
		SYNTAX					 Integer32( -1|0 .. 1 )
		MAX-ACCESS			 read-only
		STATUS					 current
		DESCRIPTION			 " -- "
		::=  { iubOFPortEntry  5 }


	iubOFPortIsOMLink		 OBJECT-TYPE
		SYNTAX					 INTEGER{ notOMLink(0),isOMLink(1)  }
		MAX-ACCESS			 read-only
		STATUS					 current
		DESCRIPTION			 " -- "
		::=  { iubOFPortEntry  6 }


	ipoaChannel		 OBJECT IDENTIFIER
		::=  { atmTransportInfo  3 }


	ipoaChVPI		 OBJECT-TYPE
		SYNTAX					 Integer32( 0 .. 65535 )
		MAX-ACCESS			 read-only
		STATUS					 current
		DESCRIPTION			 " -- "
		::=  { ipoaChannel  1 }


	ipoaChVCI		 OBJECT-TYPE
		SYNTAX					 Integer32( 0 .. 65535 )
		MAX-ACCESS			 read-only
		STATUS					 current
		DESCRIPTION			 " -- "
		::=  { ipoaChannel  2 }


	ipoaChPortId		 OBJECT-TYPE
		SYNTAX					 Integer32( 0 .. 3 )
		MAX-ACCESS			 read-only
		STATUS					 current
		DESCRIPTION			 " -- "
		::=  { ipoaChannel  3 }


	ipoaChActiveState		 OBJECT-TYPE
		SYNTAX					 INTEGER{ inactive(0),active(1)  }
		MAX-ACCESS			 read-write
		STATUS					 current
		DESCRIPTION			 " -- "
		::=  { ipoaChannel  4 }


	ipoaChActiveCheckPeriod		 OBJECT-TYPE
		SYNTAX					 Integer32( 1 .. 3600 )
		MAX-ACCESS			 read-write
		STATUS					 current
		DESCRIPTION			 " -- "
		::=  { ipoaChannel  5 }


	ipoaChLinkType		 OBJECT-TYPE
		SYNTAX					 INTEGER{ cbr(0),rtVbr(1),nrtVbr(2),ubr(3),ubrPlus(4)  }
		MAX-ACCESS			 read-only
		STATUS					 current
		DESCRIPTION			 " -- "
		::=  { ipoaChannel  6 }


	ipoaChRnc2NbPcr		 OBJECT-TYPE
		SYNTAX					 Integer32( 0|20 .. 24000 )
		MAX-ACCESS			 read-only
		STATUS					 current
		DESCRIPTION			 " -- "
		::=  { ipoaChannel  7 }


	ipoaChRnc2NbScrMcr		 OBJECT-TYPE
		SYNTAX					 Integer32( 0|20 .. 24000 )
		MAX-ACCESS			 read-only
		STATUS					 current
		DESCRIPTION			 " -- "
		::=  { ipoaChannel  8 }


	ipoaChRnc2NbMbs		 OBJECT-TYPE
		SYNTAX					 Integer32( 0|1 .. 65535 )
		MAX-ACCESS			 read-only
		STATUS					 current
		DESCRIPTION			 " -- "
		::=  { ipoaChannel  9 }


	ipoaChRnc2NbCdvt		 OBJECT-TYPE
		SYNTAX					 Integer32( 0|1 .. 65535 )
		MAX-ACCESS			 read-only
		STATUS					 current
		DESCRIPTION			 " -- "
		::=  { ipoaChannel  10 }


	ipoaChRnc2NbMaxCTD		 OBJECT-TYPE
		SYNTAX					 Integer32( 0|1 .. 65535 )
		MAX-ACCESS			 read-only
		STATUS					 current
		DESCRIPTION			 " -- "
		::=  { ipoaChannel  11 }


	ipoaChRnc2NbClr		 OBJECT-TYPE
		SYNTAX					 Integer32( 0|1 .. 65535 )
		MAX-ACCESS			 read-only
		STATUS					 current
		DESCRIPTION			 " -- "
		::=  { ipoaChannel  12 }


	ipoaChNb2RncPcr		 OBJECT-TYPE
		SYNTAX					 Integer32( 0|20 .. 24000 )
		MAX-ACCESS			 read-only
		STATUS					 current
		DESCRIPTION			 " -- "
		::=  { ipoaChannel  13 }


	ipoaChNb2RncScrMcr		 OBJECT-TYPE
		SYNTAX					 Integer32( 0|20 .. 24000 )
		MAX-ACCESS			 read-only
		STATUS					 current
		DESCRIPTION			 " -- "
		::=  { ipoaChannel  14 }


	ipoaChNb2RncMbs		 OBJECT-TYPE
		SYNTAX					 Integer32( 0|1 .. 65535 )
		MAX-ACCESS			 read-only
		STATUS					 current
		DESCRIPTION			 " -- "
		::=  { ipoaChannel  15 }


	ipoaChNb2RncCdvt		 OBJECT-TYPE
		SYNTAX					 Integer32( 0|1 .. 65535 )
		MAX-ACCESS			 read-only
		STATUS					 current
		DESCRIPTION			 " -- "
		::=  { ipoaChannel  16 }


	ipoaChNb2RncMaxCTD		 OBJECT-TYPE
		SYNTAX					 Integer32( 0|1 .. 65535 )
		MAX-ACCESS			 read-only
		STATUS					 current
		DESCRIPTION			 " -- "
		::=  { ipoaChannel  17 }


	ipoaChNb2RncCcr		 OBJECT-TYPE
		SYNTAX					 Integer32( 0|1 .. 65535 )
		MAX-ACCESS			 read-only
		STATUS					 current
		DESCRIPTION			 " -- "
		::=  { ipoaChannel  18 }


	ipoaChPolicingAction		 OBJECT-TYPE
		SYNTAX					 INTEGER{ off(0),policy1(1),policy2(2),policy3(3),policy4(4),policy5(5),policy6(6)  }
		MAX-ACCESS			 read-only
		STATUS					 current
		DESCRIPTION			 " -- "
		::=  { ipoaChannel  19 }


	ipoaChInactiveTolerance		 OBJECT-TYPE
		SYNTAX					 Integer32( 5 .. 1440 )
		MAX-ACCESS			 read-write
		STATUS					 current
		DESCRIPTION			 " -- "
		::=  { ipoaChannel  20 }


	ipoaChLastErrReason		 OBJECT-TYPE
		SYNTAX					 INTEGER{ ok(0),loopback(1),unknown(255)  }
		MAX-ACCESS			 read-only
		STATUS					 current
		DESCRIPTION			 " -- "
		::=  { ipoaChannel  21 }


	saalConnTable		 OBJECT-TYPE
		SYNTAX					 SEQUENCE  OF	 SaalConnEntry
		MAX-ACCESS			 not-accessible
		STATUS					 current
		DESCRIPTION			 " -- "
		::=  { atmTransportInfo  4 }


	saalConnEntry		 OBJECT-TYPE
		SYNTAX					 SaalConnEntry
		MAX-ACCESS			 not-accessible
		STATUS					 current
		DESCRIPTION			 " -- "
		INDEX						{ saalConnId }
		::=  { saalConnTable  1 }


	SaalConnEntry		 ::=  SEQUENCE {
		saalConnId					INTEGER,
		saalConnRowStatus					RowStatus,
		saalConnType					INTEGER,
		saalConnVpi					Integer32,
		saalConnVci					Integer32,
		saalConnPortId					Integer32,
		saalConnStatus					INTEGER,
		saalConnNmbRxBufs					Integer32,
		saalConnMaxTxCredit					Integer32,
		saalConnIsMaster					INTEGER,
		saalConnAsxIntState					Integer32,
		saalConnAalIntState					Integer32,
		saalConnSscfState					Integer32,
		saalConnSscopState					Integer32,
		saalConnTxDiscardedSdus					Integer32,
		saalConnRxErrorPdus					Integer32,
		saalConnRxDiscardedPdus					Integer32,
		saalConnTxErrorPdus					Integer32,
		saalConnTxDiscardedPdus					Integer32,
		saalConnRxBgnPdus					Integer32,
		saalConnTxBgnPdus					Integer32,
		saalConnRxBgAkPdus					Integer32,
		saalConnTxBgAkPdus					Integer32,
		saalConnRxBgRejPdus					Integer32,
		saalConnTxBgRejPdus					Integer32,
		saalConnRxEndPdus					Integer32,
		saalConnTxEndPdus					Integer32,
		saalConnRxEndAkPdus					Integer32,
		saalConnTxEndAkPdus					Integer32,
		saalConnRxRsPdus					Integer32,
		saalConnTxRsPdus					Integer32,
		saalConnRxRsAkPdus					Integer32,
		saalConnTxRsAkPdus					Integer32,
		saalConnRxErPdus					Integer32,
		saalConnTxErPdus					Integer32,
		saalConnRxErAkPdus					Integer32,
		saalConnTxErAkPdus					Integer32,
		saalConnRxSdPdus					Integer32,
		saalConnTxSdPdus					Integer32,
		saalConnRxPollPdus					Integer32,
		saalConnTxPollPdus					Integer32,
		saalConnRxStatPdus					Integer32,
		saalConnTxStatPdus					Integer32,
		saalConnRxUstatPdus					Integer32,
		saalConnTxUstatPdus					Integer32,
		saalConnRxUdPdus					Integer32,
		saalConnTxUdPdus					Integer32,
		saalConnRxMdPdus					Integer32,
		saalConnTxMdPdus					Integer32,
		saalConnRxBufferInUseCntr					Integer32,
		saalConnRxBufferInUseGauge					Integer32,
		saalConnTxBufferInUseCntr					Integer32,
		saalConnTxBufferInUseGauge					Integer32,
		saalConnDelTrigger					INTEGER,
		saalConnLinkType					INTEGER,
		saalConnRnc2NbPcr					Integer32,
		saalConnRnc2NbScrMcr					Integer32,
		saalConnRnc2NbMbs					Integer32,
		saalConnRnc2NbCdvt					Integer32,
		saalConnRnc2NbMaxCTD					Integer32,
		saalConnRnc2NbClr					Integer32,
		saalConnNb2RncPcr					Integer32,
		saalConnNb2RncScrMcr					Integer32,
		saalConnNb2RncMbs					Integer32,
		saalConnNb2RncCdvt					Integer32,
		saalConnNb2RncMaxCTD					Integer32,
		saalConnNb2RncCcr					Integer32,
		saalConnPolicingAction					INTEGER
		}


	saalConnId		 OBJECT-TYPE
		SYNTAX					 INTEGER{ ten(10),eleven(11),one(1),two(2)  }
		MAX-ACCESS			 not-accessible
		STATUS					 current
		DESCRIPTION			 " -- "
		::=  { saalConnEntry  1 }


	saalConnRowStatus		 OBJECT-TYPE
		SYNTAX					 RowStatus
		MAX-ACCESS			 read-write
		STATUS					 current
		DESCRIPTION			 " -- "
		::=  { saalConnEntry  2 }


	saalConnType		 OBJECT-TYPE
		SYNTAX					 INTEGER{ undetermined(0),nbap(1),alcap(2)  }
		MAX-ACCESS			 read-write
		STATUS					 current
		DESCRIPTION			 " -- "
		::=  { saalConnEntry  3 }


	saalConnVpi		 OBJECT-TYPE
		SYNTAX					 Integer32( 0 .. 65535 )
		MAX-ACCESS			 read-write
		STATUS					 current
		DESCRIPTION			 " -- "
		::=  { saalConnEntry  4 }


	saalConnVci		 OBJECT-TYPE
		SYNTAX					 Integer32( 0 .. 65535 )
		MAX-ACCESS			 read-write
		STATUS					 current
		DESCRIPTION			 " -- "
		::=  { saalConnEntry  5 }


	saalConnPortId		 OBJECT-TYPE
		SYNTAX					 Integer32( 0 .. 3 )
		MAX-ACCESS			 read-write
		STATUS					 current
		DESCRIPTION			 " -- "
		::=  { saalConnEntry  6 }


	saalConnStatus		 OBJECT-TYPE
		SYNTAX					 INTEGER{ unknown(0),aal5Ok(1),localSetup(2),ok(3)  }
		MAX-ACCESS			 read-only
		STATUS					 current
		DESCRIPTION			 " -- "
		::=  { saalConnEntry  7 }


	saalConnNmbRxBufs		 OBJECT-TYPE
		SYNTAX					 Integer32( 32 .. 16777216 )
		MAX-ACCESS			 read-only
		STATUS					 current
		DESCRIPTION			 " -- "
		::=  { saalConnEntry  8 }


	saalConnMaxTxCredit		 OBJECT-TYPE
		SYNTAX					 Integer32( 32 .. 16777216 )
		MAX-ACCESS			 read-only
		STATUS					 current
		DESCRIPTION			 " -- "
		::=  { saalConnEntry  9 }


	saalConnIsMaster		 OBJECT-TYPE
		SYNTAX					 INTEGER{ master(0),slave(1)  }
		MAX-ACCESS			 read-only
		STATUS					 current
		DESCRIPTION			 " -- "
		::=  { saalConnEntry  10 }


	saalConnAsxIntState		 OBJECT-TYPE
		SYNTAX					 Integer32( 0 .. 3 )
		MAX-ACCESS			 read-only
		STATUS					 current
		DESCRIPTION			 " -- "
		::=  { saalConnEntry  11 }


	saalConnAalIntState		 OBJECT-TYPE
		SYNTAX					 Integer32( 0 .. 3 )
		MAX-ACCESS			 read-only
		STATUS					 current
		DESCRIPTION			 " -- "
		::=  { saalConnEntry  12 }


	saalConnSscfState		 OBJECT-TYPE
		SYNTAX					 Integer32( 0 .. 4 )
		MAX-ACCESS			 read-only
		STATUS					 current
		DESCRIPTION			 " -- "
		::=  { saalConnEntry  13 }


	saalConnSscopState		 OBJECT-TYPE
		SYNTAX					 Integer32( 0 .. 9 )
		MAX-ACCESS			 read-only
		STATUS					 current
		DESCRIPTION			 " -- "
		::=  { saalConnEntry  14 }


	saalConnTxDiscardedSdus		 OBJECT-TYPE
		SYNTAX					 Integer32( -2147483648 .. 2147483647 )
		MAX-ACCESS			 read-only
		STATUS					 current
		DESCRIPTION			 " -- "
		::=  { saalConnEntry  15 }


	saalConnRxErrorPdus		 OBJECT-TYPE
		SYNTAX					 Integer32( -2147483648 .. 2147483647 )
		MAX-ACCESS			 read-only
		STATUS					 current
		DESCRIPTION			 " -- "
		::=  { saalConnEntry  16 }


	saalConnRxDiscardedPdus		 OBJECT-TYPE
		SYNTAX					 Integer32( -2147483648 .. 2147483647 )
		MAX-ACCESS			 read-only
		STATUS					 current
		DESCRIPTION			 " -- "
		::=  { saalConnEntry  17 }


	saalConnTxErrorPdus		 OBJECT-TYPE
		SYNTAX					 Integer32( -2147483648 .. 2147483647 )
		MAX-ACCESS			 read-only
		STATUS					 current
		DESCRIPTION			 " -- "
		::=  { saalConnEntry  18 }


	saalConnTxDiscardedPdus		 OBJECT-TYPE
		SYNTAX					 Integer32( -2147483648 .. 2147483647 )
		MAX-ACCESS			 read-only
		STATUS					 current
		DESCRIPTION			 " -- "
		::=  { saalConnEntry  19 }


	saalConnRxBgnPdus		 OBJECT-TYPE
		SYNTAX					 Integer32( -2147483648 .. 2147483647 )
		MAX-ACCESS			 read-only
		STATUS					 current
		DESCRIPTION			 " -- "
		::=  { saalConnEntry  20 }


	saalConnTxBgnPdus		 OBJECT-TYPE
		SYNTAX					 Integer32( -2147483648 .. 2147483647 )
		MAX-ACCESS			 read-only
		STATUS					 current
		DESCRIPTION			 " -- "
		::=  { saalConnEntry  21 }


	saalConnRxBgAkPdus		 OBJECT-TYPE
		SYNTAX					 Integer32( -2147483648 .. 2147483647 )
		MAX-ACCESS			 read-only
		STATUS					 current
		DESCRIPTION			 " -- "
		::=  { saalConnEntry  22 }


	saalConnTxBgAkPdus		 OBJECT-TYPE
		SYNTAX					 Integer32( -2147483648 .. 2147483647 )
		MAX-ACCESS			 read-only
		STATUS					 current
		DESCRIPTION			 " -- "
		::=  { saalConnEntry  23 }


	saalConnRxBgRejPdus		 OBJECT-TYPE
		SYNTAX					 Integer32( -2147483648 .. 2147483647 )
		MAX-ACCESS			 read-only
		STATUS					 current
		DESCRIPTION			 " -- "
		::=  { saalConnEntry  24 }


	saalConnTxBgRejPdus		 OBJECT-TYPE
		SYNTAX					 Integer32( -2147483648 .. 2147483647 )
		MAX-ACCESS			 read-only
		STATUS					 current
		DESCRIPTION			 " -- "
		::=  { saalConnEntry  25 }


	saalConnRxEndPdus		 OBJECT-TYPE
		SYNTAX					 Integer32( -2147483648 .. 2147483647 )
		MAX-ACCESS			 read-only
		STATUS					 current
		DESCRIPTION			 " -- "
		::=  { saalConnEntry  26 }


	saalConnTxEndPdus		 OBJECT-TYPE
		SYNTAX					 Integer32( -2147483648 .. 2147483647 )
		MAX-ACCESS			 read-only
		STATUS					 current
		DESCRIPTION			 " -- "
		::=  { saalConnEntry  27 }


	saalConnRxEndAkPdus		 OBJECT-TYPE
		SYNTAX					 Integer32( -2147483648 .. 2147483647 )
		MAX-ACCESS			 read-only
		STATUS					 current
		DESCRIPTION			 " -- "
		::=  { saalConnEntry  28 }


	saalConnTxEndAkPdus		 OBJECT-TYPE
		SYNTAX					 Integer32( -2147483648 .. 2147483647 )
		MAX-ACCESS			 read-only
		STATUS					 current
		DESCRIPTION			 " -- "
		::=  { saalConnEntry  29 }


	saalConnRxRsPdus		 OBJECT-TYPE
		SYNTAX					 Integer32( -2147483648 .. 2147483647 )
		MAX-ACCESS			 read-only
		STATUS					 current
		DESCRIPTION			 " -- "
		::=  { saalConnEntry  30 }


	saalConnTxRsPdus		 OBJECT-TYPE
		SYNTAX					 Integer32( -2147483648 .. 2147483647 )
		MAX-ACCESS			 read-only
		STATUS					 current
		DESCRIPTION			 " -- "
		::=  { saalConnEntry  31 }


	saalConnRxRsAkPdus		 OBJECT-TYPE
		SYNTAX					 Integer32( -2147483648 .. 2147483647 )
		MAX-ACCESS			 read-only
		STATUS					 current
		DESCRIPTION			 " -- "
		::=  { saalConnEntry  32 }


	saalConnTxRsAkPdus		 OBJECT-TYPE
		SYNTAX					 Integer32( -2147483648 .. 2147483647 )
		MAX-ACCESS			 read-only
		STATUS					 current
		DESCRIPTION			 " -- "
		::=  { saalConnEntry  33 }


	saalConnRxErPdus		 OBJECT-TYPE
		SYNTAX					 Integer32( -2147483648 .. 2147483647 )
		MAX-ACCESS			 read-only
		STATUS					 current
		DESCRIPTION			 " -- "
		::=  { saalConnEntry  34 }


	saalConnTxErPdus		 OBJECT-TYPE
		SYNTAX					 Integer32( -2147483648 .. 2147483647 )
		MAX-ACCESS			 read-only
		STATUS					 current
		DESCRIPTION			 " -- "
		::=  { saalConnEntry  35 }


	saalConnRxErAkPdus		 OBJECT-TYPE
		SYNTAX					 Integer32( -2147483648 .. 2147483647 )
		MAX-ACCESS			 read-only
		STATUS					 current
		DESCRIPTION			 " -- "
		::=  { saalConnEntry  36 }


	saalConnTxErAkPdus		 OBJECT-TYPE
		SYNTAX					 Integer32( -2147483648 .. 2147483647 )
		MAX-ACCESS			 read-only
		STATUS					 current
		DESCRIPTION			 " -- "
		::=  { saalConnEntry  37 }


	saalConnRxSdPdus		 OBJECT-TYPE
		SYNTAX					 Integer32( -2147483648 .. 2147483647 )
		MAX-ACCESS			 read-only
		STATUS					 current
		DESCRIPTION			 " -- "
		::=  { saalConnEntry  38 }


	saalConnTxSdPdus		 OBJECT-TYPE
		SYNTAX					 Integer32( -2147483648 .. 2147483647 )
		MAX-ACCESS			 read-only
		STATUS					 current
		DESCRIPTION			 " -- "
		::=  { saalConnEntry  39 }


	saalConnRxPollPdus		 OBJECT-TYPE
		SYNTAX					 Integer32( -2147483648 .. 2147483647 )
		MAX-ACCESS			 read-only
		STATUS					 current
		DESCRIPTION			 " -- "
		::=  { saalConnEntry  40 }


	saalConnTxPollPdus		 OBJECT-TYPE
		SYNTAX					 Integer32( -2147483648 .. 2147483647 )
		MAX-ACCESS			 read-only
		STATUS					 current
		DESCRIPTION			 " -- "
		::=  { saalConnEntry  41 }


	saalConnRxStatPdus		 OBJECT-TYPE
		SYNTAX					 Integer32( -2147483648 .. 2147483647 )
		MAX-ACCESS			 read-only
		STATUS					 current
		DESCRIPTION			 " -- "
		::=  { saalConnEntry  42 }


	saalConnTxStatPdus		 OBJECT-TYPE
		SYNTAX					 Integer32( -2147483648 .. 2147483647 )
		MAX-ACCESS			 read-only
		STATUS					 current
		DESCRIPTION			 " -- "
		::=  { saalConnEntry  43 }


	saalConnRxUstatPdus		 OBJECT-TYPE
		SYNTAX					 Integer32( -2147483648 .. 2147483647 )
		MAX-ACCESS			 read-only
		STATUS					 current
		DESCRIPTION			 " -- "
		::=  { saalConnEntry  44 }


	saalConnTxUstatPdus		 OBJECT-TYPE
		SYNTAX					 Integer32( -2147483648 .. 2147483647 )
		MAX-ACCESS			 read-only
		STATUS					 current
		DESCRIPTION			 " -- "
		::=  { saalConnEntry  45 }


	saalConnRxUdPdus		 OBJECT-TYPE
		SYNTAX					 Integer32( -2147483648 .. 2147483647 )
		MAX-ACCESS			 read-only
		STATUS					 current
		DESCRIPTION			 " -- "
		::=  { saalConnEntry  46 }


	saalConnTxUdPdus		 OBJECT-TYPE
		SYNTAX					 Integer32( -2147483648 .. 2147483647 )
		MAX-ACCESS			 read-only
		STATUS					 current
		DESCRIPTION			 " -- "
		::=  { saalConnEntry  47 }


	saalConnRxMdPdus		 OBJECT-TYPE
		SYNTAX					 Integer32( -2147483648 .. 2147483647 )
		MAX-ACCESS			 read-only
		STATUS					 current
		DESCRIPTION			 " -- "
		::=  { saalConnEntry  48 }


	saalConnTxMdPdus		 OBJECT-TYPE
		SYNTAX					 Integer32( -2147483648 .. 2147483647 )
		MAX-ACCESS			 read-only
		STATUS					 current
		DESCRIPTION			 " -- "
		::=  { saalConnEntry  49 }


	saalConnRxBufferInUseCntr		 OBJECT-TYPE
		SYNTAX					 Integer32( -2147483648 .. 2147483647 )
		MAX-ACCESS			 read-only
		STATUS					 current
		DESCRIPTION			 " -- "
		::=  { saalConnEntry  50 }


	saalConnRxBufferInUseGauge		 OBJECT-TYPE
		SYNTAX					 Integer32( -2147483648 .. 2147483647 )
		MAX-ACCESS			 read-only
		STATUS					 current
		DESCRIPTION			 " -- "
		::=  { saalConnEntry  51 }


	saalConnTxBufferInUseCntr		 OBJECT-TYPE
		SYNTAX					 Integer32( -2147483648 .. 2147483647 )
		MAX-ACCESS			 read-only
		STATUS					 current
		DESCRIPTION			 " -- "
		::=  { saalConnEntry  52 }


	saalConnTxBufferInUseGauge		 OBJECT-TYPE
		SYNTAX					 Integer32( -2147483648 .. 2147483647 )
		MAX-ACCESS			 read-only
		STATUS					 current
		DESCRIPTION			 " -- "
		::=  { saalConnEntry  53 }


	saalConnDelTrigger		 OBJECT-TYPE
		SYNTAX					 INTEGER{ off(0),on(1)  }
		MAX-ACCESS			 read-write
		STATUS					 current
		DESCRIPTION			 " -- "
		::=  { saalConnEntry  54 }


	saalConnLinkType		 OBJECT-TYPE
		SYNTAX					 INTEGER{ cbr(0),rtVbr(1),nrtVbr(2),ubr(3),ubrPlus(4)  }
		MAX-ACCESS			 read-write
		STATUS					 current
		DESCRIPTION			 " -- "
		::=  { saalConnEntry  55 }


	saalConnRnc2NbPcr		 OBJECT-TYPE
		SYNTAX					 Integer32( 0|20 .. 24000 )
		MAX-ACCESS			 read-write
		STATUS					 current
		DESCRIPTION			 " -- "
		::=  { saalConnEntry  56 }


	saalConnRnc2NbScrMcr		 OBJECT-TYPE
		SYNTAX					 Integer32( 0|20 .. 24000 )
		MAX-ACCESS			 read-write
		STATUS					 current
		DESCRIPTION			 " -- "
		::=  { saalConnEntry  57 }


	saalConnRnc2NbMbs		 OBJECT-TYPE
		SYNTAX					 Integer32( 0|1 .. 65535 )
		MAX-ACCESS			 read-write
		STATUS					 current
		DESCRIPTION			 " -- "
		::=  { saalConnEntry  58 }


	saalConnRnc2NbCdvt		 OBJECT-TYPE
		SYNTAX					 Integer32( 0|1 .. 65535 )
		MAX-ACCESS			 read-write
		STATUS					 current
		DESCRIPTION			 " -- "
		::=  { saalConnEntry  59 }


	saalConnRnc2NbMaxCTD		 OBJECT-TYPE
		SYNTAX					 Integer32( 0|1 .. 65535 )
		MAX-ACCESS			 read-write
		STATUS					 current
		DESCRIPTION			 " -- "
		::=  { saalConnEntry  60 }


	saalConnRnc2NbClr		 OBJECT-TYPE
		SYNTAX					 Integer32( 0|1 .. 65535 )
		MAX-ACCESS			 read-write
		STATUS					 current
		DESCRIPTION			 " -- "
		::=  { saalConnEntry  61 }


	saalConnNb2RncPcr		 OBJECT-TYPE
		SYNTAX					 Integer32( 0|20 .. 24000 )
		MAX-ACCESS			 read-write
		STATUS					 current
		DESCRIPTION			 " -- "
		::=  { saalConnEntry  62 }


	saalConnNb2RncScrMcr		 OBJECT-TYPE
		SYNTAX					 Integer32( 0|20 .. 24000 )
		MAX-ACCESS			 read-write
		STATUS					 current
		DESCRIPTION			 " -- "
		::=  { saalConnEntry  63 }


	saalConnNb2RncMbs		 OBJECT-TYPE
		SYNTAX					 Integer32( 0|1 .. 65535 )
		MAX-ACCESS			 read-write
		STATUS					 current
		DESCRIPTION			 " -- "
		::=  { saalConnEntry  64 }


	saalConnNb2RncCdvt		 OBJECT-TYPE
		SYNTAX					 Integer32( 0|1 .. 65535 )
		MAX-ACCESS			 read-write
		STATUS					 current
		DESCRIPTION			 " -- "
		::=  { saalConnEntry  65 }


	saalConnNb2RncMaxCTD		 OBJECT-TYPE
		SYNTAX					 Integer32( 0|1 .. 65535 )
		MAX-ACCESS			 read-write
		STATUS					 current
		DESCRIPTION			 " -- "
		::=  { saalConnEntry  66 }


	saalConnNb2RncCcr		 OBJECT-TYPE
		SYNTAX					 Integer32( 0|1 .. 65535 )
		MAX-ACCESS			 read-write
		STATUS					 current
		DESCRIPTION			 " -- "
		::=  { saalConnEntry  67 }


	saalConnPolicingAction		 OBJECT-TYPE
		SYNTAX					 INTEGER{ off(0),policy1(1),policy2(2),policy3(3),policy4(4),policy5(5),policy6(6)  }
		MAX-ACCESS			 read-write
		STATUS					 current
		DESCRIPTION			 " -- "
		::=  { saalConnEntry  68 }


	saalCommon		 OBJECT IDENTIFIER
		::=  { atmTransportInfo  5 }


	saalMaxNmbBufs		 OBJECT-TYPE
		SYNTAX					 Unsigned32( 2 .. 65535 )
		MAX-ACCESS			 read-only
		STATUS					 current
		DESCRIPTION			 " -- "
		::=  { saalCommon  1 }


	saalNmbDlcs		 OBJECT-TYPE
		SYNTAX					 Unsigned32( 4 .. 64 )
		MAX-ACCESS			 read-only
		STATUS					 current
		DESCRIPTION			 " -- "
		::=  { saalCommon  2 }


	saalTmrPollVal		 OBJECT-TYPE
		SYNTAX					 Unsigned32( 1 .. 19 )
		MAX-ACCESS			 read-write
		STATUS					 current
		DESCRIPTION			 " -- "
		::=  { saalCommon  3 }


	saalTmrKeepAliveVal		 OBJECT-TYPE
		SYNTAX					 Unsigned32( 10 .. 100 )
		MAX-ACCESS			 read-only
		STATUS					 current
		DESCRIPTION			 " -- "
		::=  { saalCommon  4 }


	saalTmrNoResponseVal		 OBJECT-TYPE
		SYNTAX					 Unsigned32( 21 .. 300 )
		MAX-ACCESS			 read-write
		STATUS					 current
		DESCRIPTION			 " -- "
		::=  { saalCommon  5 }


	saalTmrCcVal		 OBJECT-TYPE
		SYNTAX					 Unsigned32( 10 .. 50 )
		MAX-ACCESS			 read-only
		STATUS					 current
		DESCRIPTION			 " -- "
		::=  { saalCommon  6 }


	saalTmrIdleVal		 OBJECT-TYPE
		SYNTAX					 Unsigned32( 10 .. 500 )
		MAX-ACCESS			 read-only
		STATUS					 current
		DESCRIPTION			 " -- "
		::=  { saalCommon  7 }


	saalSscopMaxCC		 OBJECT-TYPE
		SYNTAX					 Unsigned32( 4 .. 10 )
		MAX-ACCESS			 read-only
		STATUS					 current
		DESCRIPTION			 " -- "
		::=  { saalCommon  8 }


	saalSscopMaxPD		 OBJECT-TYPE
		SYNTAX					 Unsigned32( 1 .. 100 )
		MAX-ACCESS			 read-only
		STATUS					 current
		DESCRIPTION			 " -- "
		::=  { saalCommon  9 }


	saalSscopMaxSTAT		 OBJECT-TYPE
		SYNTAX					 Unsigned32( 1 .. 80 )
		MAX-ACCESS			 read-only
		STATUS					 current
		DESCRIPTION			 " -- "
		::=  { saalCommon  10 }


	saalAllNbapAlarmState		 OBJECT-TYPE
		SYNTAX					 INTEGER{ clear(0),notClear(1)  }
		MAX-ACCESS			 read-only
		STATUS					 current
		DESCRIPTION			 " -- "
		::=  { saalCommon  11 }


	saalAllAlcapAlarmState		 OBJECT-TYPE
		SYNTAX					 INTEGER{ clear(0),notClear(1)  }
		MAX-ACCESS			 read-only
		STATUS					 current
		DESCRIPTION			 " -- "
		::=  { saalCommon  12 }


	pathTable		 OBJECT-TYPE
		SYNTAX					 SEQUENCE  OF	 PathEntry
		MAX-ACCESS			 not-accessible
		STATUS					 current
		DESCRIPTION			 " -- "
		::=  { atmTransportInfo  6 }


	pathEntry		 OBJECT-TYPE
		SYNTAX					 PathEntry
		MAX-ACCESS			 not-accessible
		STATUS					 current
		DESCRIPTION			 " -- "
		INDEX						{ pathIndex }
		::=  { pathTable  1 }


	PathEntry		 ::=  SEQUENCE {
		pathIndex					Integer32,
		pathRowStatus					RowStatus,
		pathId					Unsigned32,
		pathVpi					Integer32,
		pathVci					Integer32,
		pathPortId					Integer32,
		pathStatus					INTEGER,
		pathCheckEnableSwitch					INTEGER,
		pathConns					Unsigned32,
		pathDelTrigger					INTEGER,
		pathLinkType					INTEGER,
		pathRnc2NbPcr					Integer32,
		pathRnc2NbScrMcr					Integer32,
		pathRnc2NbMbs					Integer32,
		pathRnc2NbCdvt					Integer32,
		pathRnc2NbMaxCTD					Integer32,
		pathRnc2NbClr					Integer32,
		pathNb2RncPcr					Integer32,
		pathNb2RncScrMcr					Integer32,
		pathNb2RncMbs					Integer32,
		pathNb2RncCdvt					Integer32,
		pathNb2RncMaxCTD					Integer32,
		pathNb2RncCcr					Integer32,
		pathPolicingAction					INTEGER
		}


	pathIndex		 OBJECT-TYPE
		SYNTAX					 Integer32( 0 .. 95 )
		MAX-ACCESS			 not-accessible
		STATUS					 current
		DESCRIPTION			 " -- "
		::=  { pathEntry  1 }


	pathRowStatus		 OBJECT-TYPE
		SYNTAX					 RowStatus
		MAX-ACCESS			 read-write
		STATUS					 current
		DESCRIPTION			 " -- "
		::=  { pathEntry  2 }


	pathId		 OBJECT-TYPE
		SYNTAX					 Unsigned32( 0 .. 4294967295 )
		MAX-ACCESS			 read-write
		STATUS					 current
		DESCRIPTION			 " -- "
		::=  { pathEntry  3 }


	pathVpi		 OBJECT-TYPE
		SYNTAX					 Integer32( 0 .. 65535 )
		MAX-ACCESS			 read-write
		STATUS					 current
		DESCRIPTION			 " -- "
		::=  { pathEntry  4 }


	pathVci		 OBJECT-TYPE
		SYNTAX					 Integer32( 0 .. 65535 )
		MAX-ACCESS			 read-write
		STATUS					 current
		DESCRIPTION			 " -- "
		::=  { pathEntry  5 }


	pathPortId		 OBJECT-TYPE
		SYNTAX					 Integer32( 0 .. 3 )
		MAX-ACCESS			 read-write
		STATUS					 current
		DESCRIPTION			 " -- "
		::=  { pathEntry  6 }


	pathStatus		 OBJECT-TYPE
		SYNTAX					 INTEGER{ unknown(0),aal2Ok(1),ok(3)  }
		MAX-ACCESS			 read-only
		STATUS					 current
		DESCRIPTION			 " -- "
		::=  { pathEntry  7 }


	pathCheckEnableSwitch		 OBJECT-TYPE
		SYNTAX					 INTEGER{ off(0),on(1)  }
		MAX-ACCESS			 read-write
		STATUS					 current
		DESCRIPTION			 " -- "
		::=  { pathEntry  8 }


	pathConns		 OBJECT-TYPE
		SYNTAX					 Unsigned32( 0 .. 4294967295 )
		MAX-ACCESS			 read-only
		STATUS					 current
		DESCRIPTION			 " -- "
		::=  { pathEntry  9 }


	pathDelTrigger		 OBJECT-TYPE
		SYNTAX					 INTEGER{ off(0),on(1)  }
		MAX-ACCESS			 read-write
		STATUS					 current
		DESCRIPTION			 " -- "
		::=  { pathEntry  10 }


	pathLinkType		 OBJECT-TYPE
		SYNTAX					 INTEGER{ cbr(0),rtVbr(1),nrtVbr(2),ubr(3),ubrPlus(4)  }
		MAX-ACCESS			 read-write
		STATUS					 current
		DESCRIPTION			 " -- "
		::=  { pathEntry  11 }


	pathRnc2NbPcr		 OBJECT-TYPE
		SYNTAX					 Integer32( 0|20 .. 24000 )
		MAX-ACCESS			 read-write
		STATUS					 current
		DESCRIPTION			 " -- "
		::=  { pathEntry  12 }


	pathRnc2NbScrMcr		 OBJECT-TYPE
		SYNTAX					 Integer32( 0|20 .. 24000 )
		MAX-ACCESS			 read-write
		STATUS					 current
		DESCRIPTION			 " -- "
		::=  { pathEntry  13 }


	pathRnc2NbMbs		 OBJECT-TYPE
		SYNTAX					 Integer32( 0|1 .. 65535 )
		MAX-ACCESS			 read-write
		STATUS					 current
		DESCRIPTION			 " -- "
		::=  { pathEntry  14 }


	pathRnc2NbCdvt		 OBJECT-TYPE
		SYNTAX					 Integer32( 0|1 .. 65535 )
		MAX-ACCESS			 read-write
		STATUS					 current
		DESCRIPTION			 " -- "
		::=  { pathEntry  15 }


	pathRnc2NbMaxCTD		 OBJECT-TYPE
		SYNTAX					 Integer32( 0|1 .. 65535 )
		MAX-ACCESS			 read-write
		STATUS					 current
		DESCRIPTION			 " -- "
		::=  { pathEntry  16 }


	pathRnc2NbClr		 OBJECT-TYPE
		SYNTAX					 Integer32( 0|1 .. 65535 )
		MAX-ACCESS			 read-write
		STATUS					 current
		DESCRIPTION			 " -- "
		::=  { pathEntry  17 }


	pathNb2RncPcr		 OBJECT-TYPE
		SYNTAX					 Integer32( 0|20 .. 24000 )
		MAX-ACCESS			 read-write
		STATUS					 current
		DESCRIPTION			 " -- "
		::=  { pathEntry  18 }


	pathNb2RncScrMcr		 OBJECT-TYPE
		SYNTAX					 Integer32( 0|20 .. 24000 )
		MAX-ACCESS			 read-write
		STATUS					 current
		DESCRIPTION			 " -- "
		::=  { pathEntry  19 }


	pathNb2RncMbs		 OBJECT-TYPE
		SYNTAX					 Integer32( 0|1 .. 65535 )
		MAX-ACCESS			 read-write
		STATUS					 current
		DESCRIPTION			 " -- "
		::=  { pathEntry  20 }


	pathNb2RncCdvt		 OBJECT-TYPE
		SYNTAX					 Integer32( 0|1 .. 65535 )
		MAX-ACCESS			 read-write
		STATUS					 current
		DESCRIPTION			 " -- "
		::=  { pathEntry  21 }


	pathNb2RncMaxCTD		 OBJECT-TYPE
		SYNTAX					 Integer32( 0|1 .. 65535 )
		MAX-ACCESS			 read-write
		STATUS					 current
		DESCRIPTION			 " -- "
		::=  { pathEntry  22 }


	pathNb2RncCcr		 OBJECT-TYPE
		SYNTAX					 Integer32( 0|1 .. 65535 )
		MAX-ACCESS			 read-write
		STATUS					 current
		DESCRIPTION			 " -- "
		::=  { pathEntry  23 }


	pathPolicingAction		 OBJECT-TYPE
		SYNTAX					 INTEGER{ off(0),policy1(1),policy2(2),policy3(3),policy4(4),policy5(5),policy6(6)  }
		MAX-ACCESS			 read-write
		STATUS					 current
		DESCRIPTION			 " -- "
		::=  { pathEntry  24 }


	imaGroupInfo		 OBJECT IDENTIFIER
		::=  { atmTransport  2 }


	imaGroupTable		 OBJECT-TYPE
		SYNTAX					 SEQUENCE  OF	 ImaGroupEntry
		MAX-ACCESS			 not-accessible
		STATUS					 current
		DESCRIPTION			 " -- "
		::=  { imaGroupInfo  1 }


	imaGroupEntry		 OBJECT-TYPE
		SYNTAX					 ImaGroupEntry
		MAX-ACCESS			 not-accessible
		STATUS					 current
		DESCRIPTION			 " -- "
		INDEX						{ imaGrpSlotId,imaGrpIndex }
		::=  { imaGroupTable  1 }


	ImaGroupEntry		 ::=  SEQUENCE {
		imaGrpSlotId					Integer32,
		imaGrpIndex					Integer32,
		imaGrpRowStatus					RowStatus,
		imaGrpInitMode					INTEGER,
		imaGrpVersion					INTEGER,
		imaGrpFrameLength					INTEGER,
		imaGrpClockMode					INTEGER,
		imaGrpE1LinkOhm					INTEGER,
		imaGrpTxSigLevel					Integer32,
		imaGrpRxDetectThreshold					INTEGER,
		imaGrpStartLinkId					Integer32,
		imaGrpActiveThreshold					Integer32,
		imaGrpLinkNum					Integer32,
		imaGrpGtsmState					INTEGER,
		imaGrpNeGsmState					INTEGER,
		imaGrpFeGsmState					INTEGER,
		imaGrpRxFrameLen					INTEGER,
		imaGrpTxTrlPhyLink					Integer32,
		imaGrpRxTrlPhyLink					Integer32,
		imaGrpRxTrlLid					Integer32,
		imaGrpNumTxLinks					Integer32,
		imaGrpNumTxLinksActv					Integer32,
		imaGrpNumRxLinks					Integer32,
		imaGrpNumRxLinksActv					Integer32
		}


	imaGrpSlotId		 OBJECT-TYPE
		SYNTAX					 Integer32( 0 .. 5 )
		MAX-ACCESS			 not-accessible
		STATUS					 current
		DESCRIPTION			 " -- "
		::=  { imaGroupEntry  1 }


	imaGrpIndex		 OBJECT-TYPE
		SYNTAX					 Integer32( 0 .. 1 )
		MAX-ACCESS			 not-accessible
		STATUS					 current
		DESCRIPTION			 " -- "
		::=  { imaGroupEntry  2 }


	imaGrpRowStatus		 OBJECT-TYPE
		SYNTAX					 RowStatus
		MAX-ACCESS			 read-write
		STATUS					 current
		DESCRIPTION			 " -- "
		::=  { imaGroupEntry  3 }


	imaGrpInitMode		 OBJECT-TYPE
		SYNTAX					 INTEGER{ ima(0),uni(1)  }
		MAX-ACCESS			 read-write
		STATUS					 current
		DESCRIPTION			 " -- "
		::=  { imaGroupEntry  4 }


	imaGrpVersion		 OBJECT-TYPE
		SYNTAX					 INTEGER{ ver10(0),ver11(1),invalid(15)  }
		MAX-ACCESS			 read-write
		STATUS					 current
		DESCRIPTION			 " -- "
		::=  { imaGroupEntry  5 }


	imaGrpFrameLength		 OBJECT-TYPE
		SYNTAX					 INTEGER{ len32(0),len64(1),len128(2),len256(3),invalid(15)  }
		MAX-ACCESS			 read-write
		STATUS					 current
		DESCRIPTION			 " -- "
		::=  { imaGroupEntry  6 }


	imaGrpClockMode		 OBJECT-TYPE
		SYNTAX					 INTEGER{ itc(0),ctc(1),invalid(15)  }
		MAX-ACCESS			 read-write
		STATUS					 current
		DESCRIPTION			 " -- "
		::=  { imaGroupEntry  7 }


	imaGrpE1LinkOhm		 OBJECT-TYPE
		SYNTAX					 INTEGER{ ohm75(0),ohm120(1)  }
		MAX-ACCESS			 read-write
		STATUS					 current
		DESCRIPTION			 " -- "
		::=  { imaGroupEntry  8 }


	imaGrpTxSigLevel		 OBJECT-TYPE
		SYNTAX					 Integer32( 0 .. 255 )
		MAX-ACCESS			 read-write
		STATUS					 current
		DESCRIPTION			 " -- "
		::=  { imaGroupEntry  9 }


	imaGrpRxDetectThreshold		 OBJECT-TYPE
		SYNTAX					 INTEGER{ db8(0),db9(1),db10(2),db11(3),db20(4),db21(5)  }
		MAX-ACCESS			 read-write
		STATUS					 current
		DESCRIPTION			 " -- "
		::=  { imaGroupEntry  10 }


	imaGrpStartLinkId		 OBJECT-TYPE
		SYNTAX					 Integer32( 0 .. 255 )
		MAX-ACCESS			 read-write
		STATUS					 current
		DESCRIPTION			 " -- "
		::=  { imaGroupEntry  11 }


	imaGrpActiveThreshold		 OBJECT-TYPE
		SYNTAX					 Integer32( 1 .. 16|255 )
		MAX-ACCESS			 read-write
		STATUS					 current
		DESCRIPTION			 " -- "
		::=  { imaGroupEntry  12 }


	imaGrpLinkNum		 OBJECT-TYPE
		SYNTAX					 Integer32( 1 .. 16 )
		MAX-ACCESS			 read-write
		STATUS					 current
		DESCRIPTION			 " -- "
		::=  { imaGroupEntry  13 }


	imaGrpGtsmState		 OBJECT-TYPE
		SYNTAX					 INTEGER{ inactive(0),active(1),invalid(255)  }
		MAX-ACCESS			 read-only
		STATUS					 current
		DESCRIPTION			 " -- "
		::=  { imaGroupEntry  14 }


	imaGrpNeGsmState		 OBJECT-TYPE
		SYNTAX					 INTEGER{ startUp(0),startUpAck(1),configAbort(2),insufficientLinks(8),block(9),operational(10),invalid(255)  }
		MAX-ACCESS			 read-only
		STATUS					 current
		DESCRIPTION			 " -- "
		::=  { imaGroupEntry  15 }


	imaGrpFeGsmState		 OBJECT-TYPE
		SYNTAX					 INTEGER{ startUp(0),startUpAck(1),configAbort(2),insufficientLinks(8),block(9),operational(10),invalid(255)  }
		MAX-ACCESS			 read-only
		STATUS					 current
		DESCRIPTION			 " -- "
		::=  { imaGroupEntry  16 }


	imaGrpRxFrameLen		 OBJECT-TYPE
		SYNTAX					 INTEGER{ len32(0),len64(1),len128(2),len256(3),invalid(255)  }
		MAX-ACCESS			 read-only
		STATUS					 current
		DESCRIPTION			 " -- "
		::=  { imaGroupEntry  17 }


	imaGrpTxTrlPhyLink		 OBJECT-TYPE
		SYNTAX					 Integer32( 0 .. 65535 )
		MAX-ACCESS			 read-only
		STATUS					 current
		DESCRIPTION			 " -- "
		::=  { imaGroupEntry  18 }


	imaGrpRxTrlPhyLink		 OBJECT-TYPE
		SYNTAX					 Integer32( 0 .. 65535 )
		MAX-ACCESS			 read-only
		STATUS					 current
		DESCRIPTION			 " -- "
		::=  { imaGroupEntry  19 }


	imaGrpRxTrlLid		 OBJECT-TYPE
		SYNTAX					 Integer32( 0 .. 31|255 )
		MAX-ACCESS			 read-only
		STATUS					 current
		DESCRIPTION			 " -- "
		::=  { imaGroupEntry  20 }


	imaGrpNumTxLinks		 OBJECT-TYPE
		SYNTAX					 Integer32( 0 .. 65535 )
		MAX-ACCESS			 read-only
		STATUS					 current
		DESCRIPTION			 " -- "
		::=  { imaGroupEntry  21 }


	imaGrpNumTxLinksActv		 OBJECT-TYPE
		SYNTAX					 Integer32( 0 .. 65535 )
		MAX-ACCESS			 read-only
		STATUS					 current
		DESCRIPTION			 " -- "
		::=  { imaGroupEntry  22 }


	imaGrpNumRxLinks		 OBJECT-TYPE
		SYNTAX					 Integer32( 0 .. 65535 )
		MAX-ACCESS			 read-only
		STATUS					 current
		DESCRIPTION			 " -- "
		::=  { imaGroupEntry  23 }


	imaGrpNumRxLinksActv		 OBJECT-TYPE
		SYNTAX					 Integer32( 0 .. 65535 )
		MAX-ACCESS			 read-only
		STATUS					 current
		DESCRIPTION			 " -- "
		::=  { imaGroupEntry  24 }


	e1LinkInformation		 OBJECT IDENTIFIER
		::=  { atmTransport  3 }


	e1LinkTable		 OBJECT-TYPE
		SYNTAX					 SEQUENCE  OF	 E1LinkEntry
		MAX-ACCESS			 not-accessible
		STATUS					 current
		DESCRIPTION			 " -- "
		::=  { e1LinkInformation  1 }


	e1LinkEntry		 OBJECT-TYPE
		SYNTAX					 E1LinkEntry
		MAX-ACCESS			 not-accessible
		STATUS					 current
		DESCRIPTION			 " -- "
		INDEX						{ e1LinkSlotId,e1LinkId }
		::=  { e1LinkTable  1 }


	E1LinkEntry		 ::=  SEQUENCE {
		e1LinkSlotId					Integer32,
		e1LinkId					Integer32,
		e1LinkSignalState					INTEGER,
		e1LinkLof					INTEGER,
		e1LinkLocMf					INTEGER,
		e1LinkTcLcd					INTEGER,
		e1LinkImaNeLif					INTEGER,
		e1LinkImaFeLcd					INTEGER,
		e1LinkImaFeLif					INTEGER,
		e1LinkRxLid					Integer32,
		e1LinkImaNeTxState					INTEGER,
		e1LinkImaNeRxState					INTEGER,
		e1LinkImaFeTxState					INTEGER,
		e1LinkImaFeRxState					INTEGER,
		e1LinkImaDCBDepth					Unsigned32,
		e1LinkRxVersion					INTEGER,
		e1LinkRxOpMode					INTEGER,
		e1LinkRxClkMode					INTEGER,
		e1LinkRxFrameLen					INTEGER,
		e1LinkRxImaId					Integer32,
		e1LinkRxIcpOffset					Integer32,
		e1LinkRxTrlId					Integer32,
		e1LinkFrmErrCnt					Unsigned32,
		e1LinkE1FEBECnt					Unsigned32,
		e1LinkE1CRCErrCnt					Unsigned32,
		e1LinkLcvCnt					Unsigned32,
		e1LinkTxUserCells					Unsigned32,
		e1LinkRxUserCells					Unsigned32,
		e1LinkRxHcsErrs					Unsigned32,
		e1LinkRxFilteredCells					Unsigned32,
		e1LinkRxDroppedCells					Unsigned32,
		e1LinkRxOifAnomalies					Unsigned32,
		e1LinkRxIcpViolations					Unsigned32,
		e1LinkTxStuffCells					Unsigned32,
		e1LinkRxStuffCells					Unsigned32,
		e1LinkRxIcpCells					Unsigned32,
		e1LinkRxFillerCells					Unsigned32,
		e1LinkLoopbackState					INTEGER,
		e1LinkType					INTEGER
		}


	e1LinkSlotId		 OBJECT-TYPE
		SYNTAX					 Integer32( 0 .. 5 )
		MAX-ACCESS			 not-accessible
		STATUS					 current
		DESCRIPTION			 " -- "
		::=  { e1LinkEntry  1 }


	e1LinkId		 OBJECT-TYPE
		SYNTAX					 Integer32( 0 .. 15 )
		MAX-ACCESS			 not-accessible
		STATUS					 current
		DESCRIPTION			 " -- "
		::=  { e1LinkEntry  2 }


	e1LinkSignalState		 OBJECT-TYPE
		SYNTAX					 INTEGER{ sigOk(0),sigLos(1),invalid(255)  }
		MAX-ACCESS			 read-only
		STATUS					 current
		DESCRIPTION			 " -- "
		::=  { e1LinkEntry  3 }


	e1LinkLof		 OBJECT-TYPE
		SYNTAX					 INTEGER{ sFrmSyn(0),sFrmLos(1),invalid(255)  }
		MAX-ACCESS			 read-only
		STATUS					 current
		DESCRIPTION			 " -- "
		::=  { e1LinkEntry  4 }


	e1LinkLocMf		 OBJECT-TYPE
		SYNTAX					 INTEGER{ cFrmSyn(0),cFrmLos(1),invalid(255)  }
		MAX-ACCESS			 read-only
		STATUS					 current
		DESCRIPTION			 " -- "
		::=  { e1LinkEntry  5 }


	e1LinkTcLcd		 OBJECT-TYPE
		SYNTAX					 INTEGER{ tcCellSyn(0),tcCellLos(1),invalid(255)  }
		MAX-ACCESS			 read-only
		STATUS					 current
		DESCRIPTION			 " -- "
		::=  { e1LinkEntry  6 }


	e1LinkImaNeLif		 OBJECT-TYPE
		SYNTAX					 INTEGER{ imaFrmSyn(0),imaFrmLos(1),invalid(255)  }
		MAX-ACCESS			 read-only
		STATUS					 current
		DESCRIPTION			 " -- "
		::=  { e1LinkEntry  7 }


	e1LinkImaFeLcd		 OBJECT-TYPE
		SYNTAX					 INTEGER{ tcCellSyn(0),tcCellLos(1),invalid(255)  }
		MAX-ACCESS			 read-only
		STATUS					 current
		DESCRIPTION			 " -- "
		::=  { e1LinkEntry  8 }


	e1LinkImaFeLif		 OBJECT-TYPE
		SYNTAX					 INTEGER{ imaFrmSyn(0),imaFrmLos(1),invalid(255)  }
		MAX-ACCESS			 read-only
		STATUS					 current
		DESCRIPTION			 " -- "
		::=  { e1LinkEntry  9 }


	e1LinkRxLid		 OBJECT-TYPE
		SYNTAX					 Integer32( 0 .. 31|255 )
		MAX-ACCESS			 read-only
		STATUS					 current
		DESCRIPTION			 " -- "
		::=  { e1LinkEntry  10 }


	e1LinkImaNeTxState		 OBJECT-TYPE
		SYNTAX					 INTEGER{ outOfGroup(0),disable(2),enable(6),active(7),invalid(255)  }
		MAX-ACCESS			 read-only
		STATUS					 current
		DESCRIPTION			 " -- "
		::=  { e1LinkEntry  11 }


	e1LinkImaNeRxState		 OBJECT-TYPE
		SYNTAX					 INTEGER{ outOfGroup(0),disable(2),enable(6),active(7),invalid(255)  }
		MAX-ACCESS			 read-only
		STATUS					 current
		DESCRIPTION			 " -- "
		::=  { e1LinkEntry  12 }


	e1LinkImaFeTxState		 OBJECT-TYPE
		SYNTAX					 INTEGER{ outOfGroup(0),disable(2),enable(6),active(7),invalid(255)  }
		MAX-ACCESS			 read-only
		STATUS					 current
		DESCRIPTION			 " -- "
		::=  { e1LinkEntry  13 }


	e1LinkImaFeRxState		 OBJECT-TYPE
		SYNTAX					 INTEGER{ outOfGroup(0),disable(2),enable(6),active(7),invalid(255)  }
		MAX-ACCESS			 read-only
		STATUS					 current
		DESCRIPTION			 " -- "
		::=  { e1LinkEntry  14 }


	e1LinkImaDCBDepth		 OBJECT-TYPE
		SYNTAX					 Unsigned32( 0 .. 4294967294|4294967295 )
		MAX-ACCESS			 read-only
		STATUS					 current
		DESCRIPTION			 " -- "
		::=  { e1LinkEntry  15 }


	e1LinkRxVersion		 OBJECT-TYPE
		SYNTAX					 INTEGER{ ver10(0),ver11(1),invalid(255)  }
		MAX-ACCESS			 read-only
		STATUS					 current
		DESCRIPTION			 " -- "
		::=  { e1LinkEntry  16 }


	e1LinkRxOpMode		 OBJECT-TYPE
		SYNTAX					 INTEGER{ sym(0),asym(1),invalid(255)  }
		MAX-ACCESS			 read-only
		STATUS					 current
		DESCRIPTION			 " -- "
		::=  { e1LinkEntry  17 }


	e1LinkRxClkMode		 OBJECT-TYPE
		SYNTAX					 INTEGER{ itc(0),ctc(1),invalid(255)  }
		MAX-ACCESS			 read-only
		STATUS					 current
		DESCRIPTION			 " -- "
		::=  { e1LinkEntry  18 }


	e1LinkRxFrameLen		 OBJECT-TYPE
		SYNTAX					 INTEGER{ len32(0),len64(1),len128(2),len256(3),invalid(255)  }
		MAX-ACCESS			 read-only
		STATUS					 current
		DESCRIPTION			 " -- "
		::=  { e1LinkEntry  19 }


	e1LinkRxImaId		 OBJECT-TYPE
		SYNTAX					 Integer32( 0 .. 254|255 )
		MAX-ACCESS			 read-only
		STATUS					 current
		DESCRIPTION			 " -- "
		::=  { e1LinkEntry  20 }


	e1LinkRxIcpOffset		 OBJECT-TYPE
		SYNTAX					 Integer32( 0 .. 254|255 )
		MAX-ACCESS			 read-only
		STATUS					 current
		DESCRIPTION			 " -- "
		::=  { e1LinkEntry  21 }


	e1LinkRxTrlId		 OBJECT-TYPE
		SYNTAX					 Integer32( 0 .. 31|255 )
		MAX-ACCESS			 read-only
		STATUS					 current
		DESCRIPTION			 " -- "
		::=  { e1LinkEntry  22 }


	e1LinkFrmErrCnt		 OBJECT-TYPE
		SYNTAX					 Unsigned32( 0 .. 4294967295 )
		MAX-ACCESS			 read-only
		STATUS					 current
		DESCRIPTION			 " -- "
		::=  { e1LinkEntry  23 }


	e1LinkE1FEBECnt		 OBJECT-TYPE
		SYNTAX					 Unsigned32( 0 .. 65535 )
		MAX-ACCESS			 read-only
		STATUS					 current
		DESCRIPTION			 " -- "
		::=  { e1LinkEntry  24 }


	e1LinkE1CRCErrCnt		 OBJECT-TYPE
		SYNTAX					 Unsigned32( 0 .. 65535 )
		MAX-ACCESS			 read-only
		STATUS					 current
		DESCRIPTION			 " -- "
		::=  { e1LinkEntry  25 }


	e1LinkLcvCnt		 OBJECT-TYPE
		SYNTAX					 Unsigned32( 0 .. 65535 )
		MAX-ACCESS			 read-only
		STATUS					 current
		DESCRIPTION			 " -- "
		::=  { e1LinkEntry  26 }


	e1LinkTxUserCells		 OBJECT-TYPE
		SYNTAX					 Unsigned32( 0 .. 65535 )
		MAX-ACCESS			 read-only
		STATUS					 current
		DESCRIPTION			 " -- "
		::=  { e1LinkEntry  27 }


	e1LinkRxUserCells		 OBJECT-TYPE
		SYNTAX					 Unsigned32( 0 .. 65535 )
		MAX-ACCESS			 read-only
		STATUS					 current
		DESCRIPTION			 " -- "
		::=  { e1LinkEntry  28 }


	e1LinkRxHcsErrs		 OBJECT-TYPE
		SYNTAX					 Unsigned32( 0 .. 65535 )
		MAX-ACCESS			 read-only
		STATUS					 current
		DESCRIPTION			 " -- "
		::=  { e1LinkEntry  29 }


	e1LinkRxFilteredCells		 OBJECT-TYPE
		SYNTAX					 Unsigned32( 0 .. 65535 )
		MAX-ACCESS			 read-only
		STATUS					 current
		DESCRIPTION			 " -- "
		::=  { e1LinkEntry  30 }


	e1LinkRxDroppedCells		 OBJECT-TYPE
		SYNTAX					 Unsigned32( 0 .. 65535 )
		MAX-ACCESS			 read-only
		STATUS					 current
		DESCRIPTION			 " -- "
		::=  { e1LinkEntry  31 }


	e1LinkRxOifAnomalies		 OBJECT-TYPE
		SYNTAX					 Unsigned32( 0 .. 65535 )
		MAX-ACCESS			 read-only
		STATUS					 current
		DESCRIPTION			 " -- "
		::=  { e1LinkEntry  32 }


	e1LinkRxIcpViolations		 OBJECT-TYPE
		SYNTAX					 Unsigned32( 0 .. 65535 )
		MAX-ACCESS			 read-only
		STATUS					 current
		DESCRIPTION			 " -- "
		::=  { e1LinkEntry  33 }


	e1LinkTxStuffCells		 OBJECT-TYPE
		SYNTAX					 Unsigned32( 0 .. 65535 )
		MAX-ACCESS			 read-only
		STATUS					 current
		DESCRIPTION			 " -- "
		::=  { e1LinkEntry  34 }


	e1LinkRxStuffCells		 OBJECT-TYPE
		SYNTAX					 Unsigned32( 0 .. 65535 )
		MAX-ACCESS			 read-only
		STATUS					 current
		DESCRIPTION			 " -- "
		::=  { e1LinkEntry  35 }


	e1LinkRxIcpCells		 OBJECT-TYPE
		SYNTAX					 Unsigned32( 0 .. 65535 )
		MAX-ACCESS			 read-only
		STATUS					 current
		DESCRIPTION			 " -- "
		::=  { e1LinkEntry  36 }


	e1LinkRxFillerCells		 OBJECT-TYPE
		SYNTAX					 Unsigned32( 0 .. 65535 )
		MAX-ACCESS			 read-only
		STATUS					 current
		DESCRIPTION			 " -- "
		::=  { e1LinkEntry  37 }


	e1LinkLoopbackState		 OBJECT-TYPE
		SYNTAX					 INTEGER{ normal(0),loopback(1),invalid(255)  }
		MAX-ACCESS			 read-only
		STATUS					 current
		DESCRIPTION			 " -- "
		::=  { e1LinkEntry  38 }


	e1LinkType		 OBJECT-TYPE
		SYNTAX					 INTEGER{ electric(0),optical(1)  }
		MAX-ACCESS			 read-only
		STATUS					 current
		DESCRIPTION			 " -- "
		::=  { e1LinkEntry  39 }


	e1ErrorRateAlarmParam		 OBJECT IDENTIFIER
		::=  { e1LinkInformation  2 }


	e1FrameErrorAlarmGenThreshold		 OBJECT-TYPE
		SYNTAX					 Unsigned32( 1 .. 4294967295 )
		MAX-ACCESS			 read-write
		STATUS					 current
		DESCRIPTION			 " -- "
		::=  { e1ErrorRateAlarmParam  1 }


	e1FrameErrorAlarmClearThreshold		 OBJECT-TYPE
		SYNTAX					 Unsigned32( 0 .. 4294967295 )
		MAX-ACCESS			 read-write
		STATUS					 current
		DESCRIPTION			 " -- "
		::=  { e1ErrorRateAlarmParam  2 }


	e1CRCErrorAlarmGenThreshold		 OBJECT-TYPE
		SYNTAX					 Unsigned32( 1 .. 4294967295 )
		MAX-ACCESS			 read-write
		STATUS					 current
		DESCRIPTION			 " -- "
		::=  { e1ErrorRateAlarmParam  3 }


	e1CRCErrorAlarmClearThreshold		 OBJECT-TYPE
		SYNTAX					 Unsigned32( 0 .. 4294967295 )
		MAX-ACCESS			 read-write
		STATUS					 current
		DESCRIPTION			 " -- "
		::=  { e1ErrorRateAlarmParam  4 }


	e1FEBEErrorAlarmGenThreshold		 OBJECT-TYPE
		SYNTAX					 Unsigned32( 1 .. 4294967295 )
		MAX-ACCESS			 read-write
		STATUS					 current
		DESCRIPTION			 " -- "
		::=  { e1ErrorRateAlarmParam  5 }


	e1FEBEErrorAlarmClearThreshold		 OBJECT-TYPE
		SYNTAX					 Unsigned32( 0 .. 4294967295 )
		MAX-ACCESS			 read-write
		STATUS					 current
		DESCRIPTION			 " -- "
		::=  { e1ErrorRateAlarmParam  6 }


	e1ErrorDetectPeriod		 OBJECT-TYPE
		SYNTAX					 Unsigned32( 0 .. 3600 )
		MAX-ACCESS			 read-write
		STATUS					 current
		DESCRIPTION			 " -- "
		::=  { e1ErrorRateAlarmParam  7 }


	remoteLmtRoute		 OBJECT IDENTIFIER
		::=  { transport  8 }


	remoteLmtRouteTable		 OBJECT-TYPE
		SYNTAX					 SEQUENCE  OF	 RemoteLmtRouteEntry
		MAX-ACCESS			 not-accessible
		STATUS					 current
		DESCRIPTION			 " -- "
		::=  { remoteLmtRoute  1 }


	remoteLmtRouteEntry		 OBJECT-TYPE
		SYNTAX					 RemoteLmtRouteEntry
		MAX-ACCESS			 not-accessible
		STATUS					 current
		DESCRIPTION			 " -- "
		INDEX						{ remoteLmtRouteIndex }
		::=  { remoteLmtRouteTable  1 }


	RemoteLmtRouteEntry		 ::=  SEQUENCE {
		remoteLmtRouteIndex					Integer32,
		remoteLmtRouteRowStatus					RowStatus,
		remoteLmtRoutePeerIpType					InetAddressType,
		remoteLmtRoutePeerIp					InetAddress,
		remoteLmtRoutePeerIpMask					InetAddress,
		remoteLmtRouteGatewayIpAddress					InetAddress,
		remoteLmtRoutePhyType					INTEGER,
		remoteLmtRouteRackNo					Integer32,
		remoteLmtRouteShelfNo					Integer32,
		remoteLmtRouteSlotNo					Integer32,
		remoteLmtRoutePhyPortId					Integer32
		}


	remoteLmtRouteIndex		 OBJECT-TYPE
		SYNTAX					 Integer32( 0 .. 9 )
		MAX-ACCESS			 not-accessible
		STATUS					 current
		DESCRIPTION			 " -- "
		::=  { remoteLmtRouteEntry  1 }


	remoteLmtRouteRowStatus		 OBJECT-TYPE
		SYNTAX					 RowStatus
		MAX-ACCESS			 read-create
		STATUS					 current
		DESCRIPTION			 " -- "
		::=  { remoteLmtRouteEntry  2 }


	remoteLmtRoutePeerIpType		 OBJECT-TYPE
		SYNTAX					 InetAddressType
		MAX-ACCESS			 read-create
		STATUS					 current
		DESCRIPTION			 " -- "
		::=  { remoteLmtRouteEntry  3 }


	remoteLmtRoutePeerIp		 OBJECT-TYPE
		SYNTAX					 InetAddress
		MAX-ACCESS			 read-create
		STATUS					 current
		DESCRIPTION			 " -- "
		::=  { remoteLmtRouteEntry  4 }


	remoteLmtRoutePeerIpMask		 OBJECT-TYPE
		SYNTAX					 InetAddress
		MAX-ACCESS			 read-create
		STATUS					 current
		DESCRIPTION			 " -- "
		::=  { remoteLmtRouteEntry  5 }


	remoteLmtRouteGatewayIpAddress		 OBJECT-TYPE
		SYNTAX					 InetAddress
		MAX-ACCESS			 read-create
		STATUS					 current
		DESCRIPTION			 " -- "
		::=  { remoteLmtRouteEntry  6 }


	remoteLmtRoutePhyType		 OBJECT-TYPE
		SYNTAX					 INTEGER{ eth(0),e1(1),ops(2)  }
		MAX-ACCESS			 read-create
		STATUS					 current
		DESCRIPTION			 " -- "
		::=  { remoteLmtRouteEntry  7 }


	remoteLmtRouteRackNo		 OBJECT-TYPE
		SYNTAX					 Integer32( 0 .. 0 )
		MAX-ACCESS			 read-create
		STATUS					 current
		DESCRIPTION			 " -- "
		::=  { remoteLmtRouteEntry  8 }


	remoteLmtRouteShelfNo		 OBJECT-TYPE
		SYNTAX					 Integer32( 0 .. 0 )
		MAX-ACCESS			 read-create
		STATUS					 current
		DESCRIPTION			 " -- "
		::=  { remoteLmtRouteEntry  9 }


	remoteLmtRouteSlotNo		 OBJECT-TYPE
		SYNTAX					 Integer32( 0 .. 16 )
		MAX-ACCESS			 read-create
		STATUS					 current
		DESCRIPTION			 " -- "
		::=  { remoteLmtRouteEntry  10 }


	remoteLmtRoutePhyPortId		 OBJECT-TYPE
		SYNTAX					 Integer32( 0 .. 1 )
		MAX-ACCESS			 read-create
		STATUS					 current
		DESCRIPTION			 " -- "
		::=  { remoteLmtRouteEntry  11 }


	localCell		 OBJECT IDENTIFIER
		::=  { eNBConfig  4 }


	localCellTable		 OBJECT-TYPE
		SYNTAX					 SEQUENCE  OF	 LocalCellEntry
		MAX-ACCESS			 not-accessible
		STATUS					 current
		DESCRIPTION			 " -- "
		::=  { localCell  1 }


	localCellEntry		 OBJECT-TYPE
		SYNTAX					 LocalCellEntry
		MAX-ACCESS			 not-accessible
		STATUS					 current
		DESCRIPTION			 " -- "
		INDEX						{ lcId }
		::=  { localCellTable  1 }


	LocalCellEntry		 ::=  SEQUENCE {
		lcId					Integer32,
		lcRowStatus					RowStatus,
		lcCellMode					INTEGER,
		lcAntArrayMode					INTEGER,
		lcProcedureStatus					INTEGER,
		lcOperationalState					INTEGER,
		lcDisableReason					BITS,
		lcMaxDlPower					Integer32,
		lcMinDlPower					Integer32,
		lcConfigTrigger					INTEGER,
		lcHlProcId					Integer32
		}


	lcId		 OBJECT-TYPE
		SYNTAX					 Integer32( 0 .. 23 )
		MAX-ACCESS			 not-accessible
		STATUS					 current
		DESCRIPTION			 " -- "
		::=  { localCellEntry  1 }


	lcRowStatus		 OBJECT-TYPE
		SYNTAX					 RowStatus
		MAX-ACCESS			 read-only
		STATUS					 current
		DESCRIPTION			 " -- "
		::=  { localCellEntry  2 }


	lcCellMode		 OBJECT-TYPE
		SYNTAX					 INTEGER{ tdscdma(1),tdlte(2),fddlte(3)  }
		MAX-ACCESS			 read-only
		STATUS					 current
		DESCRIPTION			 " -- "
		::=  { localCellEntry  3 }


	lcAntArrayMode		 OBJECT-TYPE
		SYNTAX					 INTEGER{ unknown(0),smartAnt(1),nonSmartAnt(2),mixedAnt(3)  }
		MAX-ACCESS			 read-only
		STATUS					 current
		DESCRIPTION			 " -- "
		::=  { localCellEntry  4 }


	lcProcedureStatus		 OBJECT-TYPE
		SYNTAX					 INTEGER{ invalid(0),notReady(1),loadSoftware(2),iqPathCfg(4),setuped(5),inDelete(6)  }
		MAX-ACCESS			 read-only
		STATUS					 current
		DESCRIPTION			 " -- "
		::=  { localCellEntry  5 }


	lcOperationalState		 OBJECT-TYPE
		SYNTAX					 INTEGER{ enabled(0),disabled(1),invalid(2)  }
		MAX-ACCESS			 read-only
		STATUS					 current
		DESCRIPTION			 " -- "
		::=  { localCellEntry  6 }


	lcDisableReason		 OBJECT-TYPE
		SYNTAX					 BITS{ clockErr(0),transErr(1)  }
		MAX-ACCESS			 read-only
		STATUS					 current
		DESCRIPTION			 " -- "
		::=  { localCellEntry  7 }


	lcMaxDlPower		 OBJECT-TYPE
		SYNTAX					 Integer32( 0 .. 600 )
		MAX-ACCESS			 read-only
		STATUS					 current
		DESCRIPTION			 " -- "
		::=  { localCellEntry  8 }


	lcMinDlPower		 OBJECT-TYPE
		SYNTAX					 Integer32( 0 .. 600 )
		MAX-ACCESS			 read-only
		STATUS					 current
		DESCRIPTION			 " -- "
		::=  { localCellEntry  9 }


	lcConfigTrigger		 OBJECT-TYPE
		SYNTAX					 INTEGER{ add(0),delete(1),reconfig(2)  }
		MAX-ACCESS			 read-write
		STATUS					 current
		DESCRIPTION			 " -- "
		::=  { localCellEntry  10 }


	lcHlProcId		 OBJECT-TYPE
		SYNTAX					 Integer32( 0 .. 10 )
		MAX-ACCESS			 read-only
		STATUS					 current
		DESCRIPTION			 " -- "
		::=  { localCellEntry  11 }


	baseBandwidthTable		 OBJECT-TYPE
		SYNTAX					 SEQUENCE  OF	 BaseBandwidthEntry
		MAX-ACCESS			 not-accessible
		STATUS					 current
		DESCRIPTION			 " -- "
		::=  { localCell  2 }


	baseBandwidthEntry		 OBJECT-TYPE
		SYNTAX					 BaseBandwidthEntry
		MAX-ACCESS			 not-accessible
		STATUS					 current
		DESCRIPTION			 " -- "
		INDEX						{ baseBandwidthRackNo,baseBandwidthShelfNo,baseBandwidthSlotNo,baseBandwidthIndexOnBoard }
		::=  { baseBandwidthTable  1 }


	BaseBandwidthEntry		 ::=  SEQUENCE {
		baseBandwidthRackNo					Integer32,
		baseBandwidthShelfNo					Integer32,
		baseBandwidthSlotNo					Integer32,
		baseBandwidthIndexOnBoard					Integer32,
		baseBandwidthRowStatus					RowStatus,
		baseBandwidthOperationalState					INTEGER,
		baseBandwidthEngagedState					INTEGER,
		baseBandwidthLcId					Integer32,
		baseBandwidthLoadState					INTEGER,
		baseBandwidthSwType					INTEGER,
		baseBandwidthMainDspFlag					INTEGER,
		baseBandwidthL1CoreList					Unsigned32Array,
		baseBandwidthSocIndex					Integer32
		}


	baseBandwidthRackNo		 OBJECT-TYPE
		SYNTAX					 Integer32( 0 .. 0 )
		MAX-ACCESS			 not-accessible
		STATUS					 current
		DESCRIPTION			 " -- "
		::=  { baseBandwidthEntry  1 }


	baseBandwidthShelfNo		 OBJECT-TYPE
		SYNTAX					 Integer32( 0 .. 0 )
		MAX-ACCESS			 not-accessible
		STATUS					 current
		DESCRIPTION			 " -- "
		::=  { baseBandwidthEntry  2 }


	baseBandwidthSlotNo		 OBJECT-TYPE
		SYNTAX					 Integer32( 1 .. 7 )
		MAX-ACCESS			 not-accessible
		STATUS					 current
		DESCRIPTION			 " -- "
		::=  { baseBandwidthEntry  3 }


	baseBandwidthIndexOnBoard		 OBJECT-TYPE
		SYNTAX					 Integer32( 0 .. 47 )
		MAX-ACCESS			 not-accessible
		STATUS					 current
		DESCRIPTION			 " -- "
		::=  { baseBandwidthEntry  4 }


	baseBandwidthRowStatus		 OBJECT-TYPE
		SYNTAX					 RowStatus
		MAX-ACCESS			 read-only
		STATUS					 current
		DESCRIPTION			 " -- "
		::=  { baseBandwidthEntry  5 }


	baseBandwidthOperationalState		 OBJECT-TYPE
		SYNTAX					 INTEGER{ enabled(0),disabled(1),invalid(2)  }
		MAX-ACCESS			 read-only
		STATUS					 current
		DESCRIPTION			 " -- "
		::=  { baseBandwidthEntry  6 }


	baseBandwidthEngagedState		 OBJECT-TYPE
		SYNTAX					 INTEGER{ free(0),preengage(1),engaging(2),engaged(3)  }
		MAX-ACCESS			 read-only
		STATUS					 current
		DESCRIPTION			 " -- "
		::=  { baseBandwidthEntry  7 }


	baseBandwidthLcId		 OBJECT-TYPE
		SYNTAX					 Integer32( 0 .. 23|-1 )
		MAX-ACCESS			 read-only
		STATUS					 current
		DESCRIPTION			 " -- "
		::=  { baseBandwidthEntry  8 }


	baseBandwidthLoadState		 OBJECT-TYPE
		SYNTAX					 INTEGER{ notLoad(0),loading(1),loaded(2)  }
		MAX-ACCESS			 read-only
		STATUS					 current
		DESCRIPTION			 " -- "
		::=  { baseBandwidthEntry  9 }


	baseBandwidthSwType		 OBJECT-TYPE
		SYNTAX					 INTEGER{ lte2a(0),lte8a(1),fdd(2),unknown(-1)  }
		MAX-ACCESS			 read-only
		STATUS					 current
		DESCRIPTION			 " -- "
		::=  { baseBandwidthEntry  10 }


	baseBandwidthMainDspFlag		 OBJECT-TYPE
		SYNTAX					 INTEGER{ main(0),assistant(1)  }
		MAX-ACCESS			 read-only
		STATUS					 current
		DESCRIPTION			 " -- "
		::=  { baseBandwidthEntry  11 }


	baseBandwidthL1CoreList		 OBJECT-TYPE
		SYNTAX					 Unsigned32Array
		MAX-ACCESS			 read-only
		STATUS					 current
		DESCRIPTION			 " -- "
		::=  { baseBandwidthEntry  12 }


	baseBandwidthSocIndex		 OBJECT-TYPE
		SYNTAX					 Integer32( 0 .. 1|-1 )
		MAX-ACCESS			 read-only
		STATUS					 current
		DESCRIPTION			 " -- "
		::=  { baseBandwidthEntry  13 }


	cellTable		 OBJECT-TYPE
		SYNTAX					 SEQUENCE  OF	 CellEntry
		MAX-ACCESS			 not-accessible
		STATUS					 current
		DESCRIPTION			 " -- "
		::=  { localCell  3 }


	cellEntry		 OBJECT-TYPE
		SYNTAX					 CellEntry
		MAX-ACCESS			 not-accessible
		STATUS					 current
		DESCRIPTION			 " -- "
		INDEX						{ cellId }
		::=  { cellTable  1 }


	CellEntry		 ::=  SEQUENCE {
		cellId					Integer32,
		cellRowStatus					RowStatus,
		cellOperationalState					INTEGER,
		cellAvailbilityStatus					INTEGER,
		cellProcedureStatus					INTEGER,
		cellActiveTrigger					INTEGER,
		cellAntCalPeriod					Unsigned32,
		cellAntCalTrigger					INTEGER,
		cellBlockSwitch					INTEGER,
		cellBlockTime					Integer32,
		cellBlockStatus					INTEGER,
		cellActTime					DateAndTime,
		cellDeactDelayTime					Integer32,
		cellRrcConnectNum					Integer32,
		cellUlIot					Unsigned32Array,
		cellPathShutdownState					INTEGER,
		cellCellShutdownState					INTEGER,
		cellSymbolState					DisplayString,
		cellMBSFNState					DisplayString,
		cellFrameType					INTEGER,
		cellPrbAcStatus					INTEGER,
		cellActiveUeAcStatus					INTEGER,
		cellPrbStatus					INTEGER
		}


	cellId		 OBJECT-TYPE
		SYNTAX					 Integer32( 0 .. 23 )
		MAX-ACCESS			 not-accessible
		STATUS					 current
		DESCRIPTION			 " -- "
		::=  { cellEntry  1 }


	cellRowStatus		 OBJECT-TYPE
		SYNTAX					 RowStatus
		MAX-ACCESS			 read-only
		STATUS					 current
		DESCRIPTION			 " -- "
		::=  { cellEntry  2 }


	cellOperationalState		 OBJECT-TYPE
		SYNTAX					 INTEGER{ enabled(0),disabled(1),invalid(2)  }
		MAX-ACCESS			 read-only
		STATUS					 current
		DESCRIPTION			 " -- "
		::=  { cellEntry  3 }


	cellAvailbilityStatus		 OBJECT-TYPE
		SYNTAX					 INTEGER{ empty(0),failed(2),degraded(7)  }
		MAX-ACCESS			 read-only
		STATUS					 current
		DESCRIPTION			 " -- "
		::=  { cellEntry  4 }


	cellProcedureStatus		 OBJECT-TYPE
		SYNTAX					 INTEGER{ invalid(0),inSetup(1),inDelete(2),inRecfg(3),inShuttingDown(4)  }
		MAX-ACCESS			 read-only
		STATUS					 current
		DESCRIPTION			 " -- "
		::=  { cellEntry  5 }


	cellActiveTrigger		 OBJECT-TYPE
		SYNTAX					 INTEGER{ active(0),deactive(1),shuttingDown(2)  }
		MAX-ACCESS			 read-write
		STATUS					 current
		DESCRIPTION			 " -- "
		::=  { cellEntry  6 }


	cellAntCalPeriod		 OBJECT-TYPE
		SYNTAX					 Unsigned32( 60 .. 2100000|0 )
		MAX-ACCESS			 read-write
		STATUS					 current
		DESCRIPTION			 " -- "
		::=  { cellEntry  8 }


	cellAntCalTrigger		 OBJECT-TYPE
		SYNTAX					 INTEGER{ txPath(0),rxPath(1),rtxPath(2)  }
		MAX-ACCESS			 read-write
		STATUS					 current
		DESCRIPTION			 " -- "
		::=  { cellEntry  9 }


	cellBlockSwitch		 OBJECT-TYPE
		SYNTAX					 INTEGER{ off(0),unblock(1),blockHigh(2),blockNormal(3),blockLow(4)  }
		MAX-ACCESS			 read-write
		STATUS					 current
		DESCRIPTION			 " -- "
		::=  { cellEntry  10 }


	cellBlockTime		 OBJECT-TYPE
		SYNTAX					 Integer32( 1 .. 3600 )
		MAX-ACCESS			 read-write
		STATUS					 current
		DESCRIPTION			 " -- "
		::=  { cellEntry  11 }


	cellBlockStatus		 OBJECT-TYPE
		SYNTAX					 INTEGER{ unblocked(0),blocking(1),blocked(2),invalid(3)  }
		MAX-ACCESS			 read-only
		STATUS					 current
		DESCRIPTION			 " -- "
		::=  { cellEntry  12 }


	cellActTime		 OBJECT-TYPE
		SYNTAX					 DateAndTime
		MAX-ACCESS			 read-only
		STATUS					 current
		DESCRIPTION			 " -- "
		::=  { cellEntry  13 }


	cellDeactDelayTime		 OBJECT-TYPE
		SYNTAX					 Integer32( 1 .. 3600 )
		MAX-ACCESS			 read-write
		STATUS					 current
		DESCRIPTION			 " -- "
		::=  { cellEntry  14 }


	cellRrcConnectNum		 OBJECT-TYPE
		SYNTAX					 Integer32( -2147483648 .. 2147483647 )
		MAX-ACCESS			 read-only
		STATUS					 current
		DESCRIPTION			 " -- "
		::=  { cellEntry  15 }


	cellUlIot		 OBJECT-TYPE
		SYNTAX					 Unsigned32Array
		MAX-ACCESS			 read-only
		STATUS					 current
		DESCRIPTION			 " -- "
		::=  { cellEntry  16 }


	cellPathShutdownState		 OBJECT-TYPE
		SYNTAX					 INTEGER{ normal(0),conservation(1)  }
		MAX-ACCESS			 read-only
		STATUS					 current
		DESCRIPTION			 " -- "
		::=  { cellEntry  18 }


	cellCellShutdownState		 OBJECT-TYPE
		SYNTAX					 INTEGER{ normal(0),conservation(1)  }
		MAX-ACCESS			 read-only
		STATUS					 current
		DESCRIPTION			 " -- "
		::=  { cellEntry  19 }


	cellSymbolState		 OBJECT-TYPE
		SYNTAX					 DisplayString( SIZE ( 1 .. 255 ) )
		MAX-ACCESS			 read-only
		STATUS					 current
		DESCRIPTION			 " -- "
		::=  { cellEntry  20 }


	cellMBSFNState		 OBJECT-TYPE
		SYNTAX					 DisplayString( SIZE ( 1 .. 255 ) )
		MAX-ACCESS			 read-only
		STATUS					 current
		DESCRIPTION			 " -- "
		::=  { cellEntry  21 }


	cellFrameType		 OBJECT-TYPE
		SYNTAX					 INTEGER{ fdd(0),tdd(1)  }
		MAX-ACCESS			 read-only
		STATUS					 current
		DESCRIPTION			 " -- "
		::=  { cellEntry  22 }


	cellPrbAcStatus		 OBJECT-TYPE
		SYNTAX					 INTEGER{ normal(0),highLoad(1)  }
		MAX-ACCESS			 read-only
		STATUS					 current
		DESCRIPTION			 " -- "
		::=  { cellEntry  24 }


	cellActiveUeAcStatus		 OBJECT-TYPE
		SYNTAX					 INTEGER{ normal(0),highLoad(1),superHighLoad(2),limitHighLoad(3)  }
		MAX-ACCESS			 read-only
		STATUS					 current
		DESCRIPTION			 " -- "
		::=  { cellEntry  25 }


	cellPrbStatus		 OBJECT-TYPE
		SYNTAX					 INTEGER{ normal(0),prbCongest(1)  }
		MAX-ACCESS			 read-only
		STATUS					 current
		DESCRIPTION			 " -- "
		::=  { cellEntry  26 }


	cellUlIotTable		 OBJECT-TYPE
		SYNTAX					 SEQUENCE  OF	 CellUlIotEntry
		MAX-ACCESS			 not-accessible
		STATUS					 current
		DESCRIPTION			 " -- "
		::=  { localCell  4 }


	cellUlIotEntry		 OBJECT-TYPE
		SYNTAX					 CellUlIotEntry
		MAX-ACCESS			 not-accessible
		STATUS					 current
		DESCRIPTION			 " -- "
		INDEX						{ cellUlIotId,cellUlIotSubSfn }
		::=  { cellUlIotTable  1 }


	CellUlIotEntry		 ::=  SEQUENCE {
		cellUlIotId					Integer32,
		cellUlIotSubSfn					Integer32,
		cellUlIotRowStatus					RowStatus,
		cellUlIotValue					Unsigned32Array,
		cellUlAnteRSSIValue					Integer32Array,
		cellUlNoUserAnteRSSIValue					Integer32Array
		}


	cellUlIotId		 OBJECT-TYPE
		SYNTAX					 Integer32( 0 .. 23 )
		MAX-ACCESS			 not-accessible
		STATUS					 current
		DESCRIPTION			 " -- "
		::=  { cellUlIotEntry  1 }


	cellUlIotSubSfn		 OBJECT-TYPE
		SYNTAX					 Integer32( 0 .. 9 )
		MAX-ACCESS			 not-accessible
		STATUS					 current
		DESCRIPTION			 " -- "
		::=  { cellUlIotEntry  2 }


	cellUlIotRowStatus		 OBJECT-TYPE
		SYNTAX					 RowStatus
		MAX-ACCESS			 read-only
		STATUS					 current
		DESCRIPTION			 " -- "
		::=  { cellUlIotEntry  3 }


	cellUlIotValue		 OBJECT-TYPE
		SYNTAX					 Unsigned32Array
		MAX-ACCESS			 read-only
		STATUS					 current
		DESCRIPTION			 " -- "
		::=  { cellUlIotEntry  4 }


	cellUlAnteRSSIValue		 OBJECT-TYPE
		SYNTAX					 Integer32Array
		MAX-ACCESS			 read-only
		STATUS					 current
		DESCRIPTION			 " -- "
		::=  { cellUlIotEntry  5 }


	cellUlNoUserAnteRSSIValue		 OBJECT-TYPE
		SYNTAX					 Integer32Array
		MAX-ACCESS			 read-only
		STATUS					 current
		DESCRIPTION			 " -- "
		::=  { cellUlIotEntry  6 }


	radioBandTable		 OBJECT-TYPE
		SYNTAX					 SEQUENCE  OF	 RadioBandEntry
		MAX-ACCESS			 not-accessible
		STATUS					 current
		DESCRIPTION			 " -- "
		::=  { localCell  5 }


	radioBandEntry		 OBJECT-TYPE
		SYNTAX					 RadioBandEntry
		MAX-ACCESS			 not-accessible
		STATUS					 current
		DESCRIPTION			 " -- "
		INDEX						{ radioBandRRUNo,radioBandRRUPathNo,radioBandIndexOnRRUPath,radioBandEngagedLcIndex }
		::=  { radioBandTable  1 }


	RadioBandEntry		 ::=  SEQUENCE {
		radioBandRRUNo					Integer32,
		radioBandRRUPathNo					Integer32,
		radioBandIndexOnRRUPath					Integer32,
		radioBandEngagedLcIndex					Integer32,
		radioBandRowStatus					RowStatus,
		radioBandEngagedState					INTEGER,
		radioBandCellStatus					INTEGER,
		radioBandLcId					Integer32,
		radioBandBaseBandAntNo					Integer32,
		radioBandBaseBandPortNo					Integer32
		}


	radioBandRRUNo		 OBJECT-TYPE
		SYNTAX					 Integer32( 0 .. 191 )
		MAX-ACCESS			 not-accessible
		STATUS					 current
		DESCRIPTION			 " -- "
		::=  { radioBandEntry  1 }


	radioBandRRUPathNo		 OBJECT-TYPE
		SYNTAX					 Integer32( 1 .. 16 )
		MAX-ACCESS			 not-accessible
		STATUS					 current
		DESCRIPTION			 " -- "
		::=  { radioBandEntry  2 }


	radioBandIndexOnRRUPath		 OBJECT-TYPE
		SYNTAX					 Integer32( 1 .. 1 )
		MAX-ACCESS			 not-accessible
		STATUS					 current
		DESCRIPTION			 " -- "
		::=  { radioBandEntry  3 }


	radioBandEngagedLcIndex		 OBJECT-TYPE
		SYNTAX					 Integer32( 1 .. 4 )
		MAX-ACCESS			 not-accessible
		STATUS					 current
		DESCRIPTION			 " -- "
		::=  { radioBandEntry  4 }


	radioBandRowStatus		 OBJECT-TYPE
		SYNTAX					 RowStatus
		MAX-ACCESS			 read-only
		STATUS					 current
		DESCRIPTION			 " -- "
		::=  { radioBandEntry  5 }


	radioBandEngagedState		 OBJECT-TYPE
		SYNTAX					 INTEGER{ free(0),preengage(1),engaging(2),engaged(3)  }
		MAX-ACCESS			 read-only
		STATUS					 current
		DESCRIPTION			 " -- "
		::=  { radioBandEntry  6 }


	radioBandCellStatus		 OBJECT-TYPE
		SYNTAX					 INTEGER{ unknown(0),cellActiving(1),cellActived(2),cellSetupFail(3)  }
		MAX-ACCESS			 read-only
		STATUS					 current
		DESCRIPTION			 " -- "
		::=  { radioBandEntry  7 }


	radioBandLcId		 OBJECT-TYPE
		SYNTAX					 Integer32( 0 .. 23|-1 )
		MAX-ACCESS			 read-only
		STATUS					 current
		DESCRIPTION			 " -- "
		::=  { radioBandEntry  8 }


	radioBandBaseBandAntNo		 OBJECT-TYPE
		SYNTAX					 Integer32( 0 .. 23|-1 )
		MAX-ACCESS			 read-only
		STATUS					 current
		DESCRIPTION			 " -- "
		::=  { radioBandEntry  9 }


	radioBandBaseBandPortNo		 OBJECT-TYPE
		SYNTAX					 Integer32( 0 .. 3|-1 )
		MAX-ACCESS			 read-only
		STATUS					 current
		DESCRIPTION			 " -- "
		::=  { radioBandEntry  10 }


	cellLccTable		 OBJECT-TYPE
		SYNTAX					 SEQUENCE  OF	 CellLccEntry
		MAX-ACCESS			 not-accessible
		STATUS					 current
		DESCRIPTION			 " -- "
		::=  { localCell  6 }


	cellLccEntry		 OBJECT-TYPE
		SYNTAX					 CellLccEntry
		MAX-ACCESS			 not-accessible
		STATUS					 current
		DESCRIPTION			 " -- "
		INDEX						{ cellLccId }
		::=  { cellLccTable  1 }


	CellLccEntry		 ::=  SEQUENCE {
		cellLccId					Integer32,
		cellLccRowStatus					RowStatus,
		cellLccStatus					INTEGER,
		cellLccUlLoadValue					Integer32,
		cellLccDlLoadValue					Integer32
		}


	cellLccId		 OBJECT-TYPE
		SYNTAX					 Integer32( 0 .. 23 )
		MAX-ACCESS			 not-accessible
		STATUS					 current
		DESCRIPTION			 " -- "
		::=  { cellLccEntry  1 }


	cellLccRowStatus		 OBJECT-TYPE
		SYNTAX					 RowStatus
		MAX-ACCESS			 read-only
		STATUS					 current
		DESCRIPTION			 " -- "
		::=  { cellLccEntry  2 }


	cellLccStatus		 OBJECT-TYPE
		SYNTAX					 INTEGER{ normal(0),congestion(1),highloag(2),alarm(3)  }
		MAX-ACCESS			 read-only
		STATUS					 current
		DESCRIPTION			 " -- "
		::=  { cellLccEntry  3 }


	cellLccUlLoadValue		 OBJECT-TYPE
		SYNTAX					 Integer32( 0 .. 100 )
		MAX-ACCESS			 read-only
		STATUS					 current
		DESCRIPTION			 " -- "
		::=  { cellLccEntry  4 }


	cellLccDlLoadValue		 OBJECT-TYPE
		SYNTAX					 Integer32( 0 .. 100 )
		MAX-ACCESS			 read-only
		STATUS					 current
		DESCRIPTION			 " -- "
		::=  { cellLccEntry  5 }


	cellUlIotRTMonitorTaskTable		 OBJECT-TYPE
		SYNTAX					 SEQUENCE  OF	 CellUlIotRTMonitorTaskEntry
		MAX-ACCESS			 not-accessible
		STATUS					 current
		DESCRIPTION			 " -- "
		::=  { localCell  7 }


	cellUlIotRTMonitorTaskEntry		 OBJECT-TYPE
		SYNTAX					 CellUlIotRTMonitorTaskEntry
		MAX-ACCESS			 not-accessible
		STATUS					 current
		DESCRIPTION			 " -- "
		INDEX						{ cellUlIotRTMonitorTaskLcId,cellUlIotRTMonitorTaskSubSfn }
		::=  { cellUlIotRTMonitorTaskTable  1 }


	CellUlIotRTMonitorTaskEntry		 ::=  SEQUENCE {
		cellUlIotRTMonitorTaskLcId					Integer32,
		cellUlIotRTMonitorTaskSubSfn					Integer32,
		cellUlIotRTMonitorTaskRowStatus					RowStatus,
		cellUlIotRTMonitorTaskPeriod					INTEGER
		}


	cellUlIotRTMonitorTaskLcId		 OBJECT-TYPE
		SYNTAX					 Integer32( 0 .. 23 )
		MAX-ACCESS			 not-accessible
		STATUS					 current
		DESCRIPTION			 " -- "
		::=  { cellUlIotRTMonitorTaskEntry  1 }


	cellUlIotRTMonitorTaskSubSfn		 OBJECT-TYPE
		SYNTAX					 Integer32( 0 .. 9 )
		MAX-ACCESS			 not-accessible
		STATUS					 current
		DESCRIPTION			 " -- "
		::=  { cellUlIotRTMonitorTaskEntry  2 }


	cellUlIotRTMonitorTaskRowStatus		 OBJECT-TYPE
		SYNTAX					 RowStatus
		MAX-ACCESS			 read-create
		STATUS					 current
		DESCRIPTION			 " -- "
		::=  { cellUlIotRTMonitorTaskEntry  3 }


	cellUlIotRTMonitorTaskPeriod		 OBJECT-TYPE
		SYNTAX					 INTEGER{ value1s(0),value2s(1),value5s(2),value10s(3),value30s(4),value1m(5),value2m(6),value5m(7)  }
		MAX-ACCESS			 read-create
		STATUS					 current
		DESCRIPTION			 " -- "
		::=  { cellUlIotRTMonitorTaskEntry  4 }


	cellIotNotificationNode		 OBJECT IDENTIFIER
		::=  { localCell  8 }


	cellIotNotifications		 OBJECT IDENTIFIER
		::=  { cellIotNotificationNode  1 }


	cellIotNotification		 NOTIFICATION-TYPE
		OBJECTS					 { cellIotNotiNEType,cellIotNotiNEID,cellIotNotiCellId,cellIotNotiSubSfn,cellIotNotiTime,cellIotNotiValue }
		STATUS					 current
		DESCRIPTION			 " -- "
		::=  { cellIotNotifications  1 }


	cellIotObjects		 OBJECT IDENTIFIER
		::=  { cellIotNotificationNode  2 }


	cellIotNotiNEType		 OBJECT-TYPE
		SYNTAX					 INTEGER{ unknown(0),tlb60a(2),emb5116tdlte(3),epc(21),ims(41)  }
		MAX-ACCESS			 accessible-for-notify
		STATUS					 current
		DESCRIPTION			 " -- "
		::=  { cellIotObjects  1 }


	cellIotNotiNEID		 OBJECT-TYPE
		SYNTAX					 Unsigned32( 0 .. 4294967295 )
		MAX-ACCESS			 accessible-for-notify
		STATUS					 current
		DESCRIPTION			 " -- "
		::=  { cellIotObjects  2 }


	cellIotNotiCellId		 OBJECT-TYPE
		SYNTAX					 Integer32( 0 .. 23 )
		MAX-ACCESS			 accessible-for-notify
		STATUS					 current
		DESCRIPTION			 " -- "
		::=  { cellIotObjects  3 }


	cellIotNotiSubSfn		 OBJECT-TYPE
		SYNTAX					 Integer32( 0 .. 9 )
		MAX-ACCESS			 accessible-for-notify
		STATUS					 current
		DESCRIPTION			 " -- "
		::=  { cellIotObjects  4 }


	cellIotNotiTime		 OBJECT-TYPE
		SYNTAX					 DateAndTime
		MAX-ACCESS			 accessible-for-notify
		STATUS					 current
		DESCRIPTION			 " -- "
		::=  { cellIotObjects  5 }


	cellIotNotiValue		 OBJECT-TYPE
		SYNTAX					 Integer32Array
		MAX-ACCESS			 accessible-for-notify
		STATUS					 current
		DESCRIPTION			 " -- "
		::=  { cellIotObjects  6 }


	cellSpecialCalCfgTable		 OBJECT-TYPE
		SYNTAX					 SEQUENCE  OF	 CellSpecialCalCfgEntry
		MAX-ACCESS			 not-accessible
		STATUS					 current
		DESCRIPTION			 " -- "
		::=  { localCell  9 }


	cellSpecialCalCfgEntry		 OBJECT-TYPE
		SYNTAX					 CellSpecialCalCfgEntry
		MAX-ACCESS			 not-accessible
		STATUS					 current
		DESCRIPTION			 " -- "
		INDEX						{ cellSpeCalCfgLcId }
		::=  { cellSpecialCalCfgTable  1 }


	CellSpecialCalCfgEntry		 ::=  SEQUENCE {
		cellSpeCalCfgLcId					Integer32,
		cellSpeCalCfgRowStatus					RowStatus,
		cellSpeCalCfgDwptsTruncateLength					Integer32,
		cellSpeCalCfgDwptsMcsLimit					Integer32,
		cellSpeCalCfgDwptsMcsSingleLimit					Integer32,
		cellSpeCalCfgDwptsCqiFlag					INTEGER,
		cellSpeCalCfgDwptsRetxFlag					INTEGER,
		cellSpeCalCfgDwptsTransFlag					Integer32,
		cellSpeCalCfgMacAckCollideMcsThr					Integer32,
		cellSpeCalCfgOffsetArray					Unsigned32Array
		}


	cellSpeCalCfgLcId		 OBJECT-TYPE
		SYNTAX					 Integer32( 0 .. 23 )
		MAX-ACCESS			 not-accessible
		STATUS					 current
		DESCRIPTION			 " -- "
		::=  { cellSpecialCalCfgEntry  1 }


	cellSpeCalCfgRowStatus		 OBJECT-TYPE
		SYNTAX					 RowStatus
		MAX-ACCESS			 read-create
		STATUS					 current
		DESCRIPTION			 " -- "
		::=  { cellSpecialCalCfgEntry  2 }


	cellSpeCalCfgDwptsTruncateLength		 OBJECT-TYPE
		SYNTAX					 Integer32( 0 .. 20 )
		MAX-ACCESS			 read-create
		STATUS					 current
		DESCRIPTION			 " -- "
		::=  { cellSpecialCalCfgEntry  3 }


	cellSpeCalCfgDwptsMcsLimit		 OBJECT-TYPE
		SYNTAX					 Integer32( 0 .. 28 )
		MAX-ACCESS			 read-create
		STATUS					 current
		DESCRIPTION			 " -- "
		::=  { cellSpecialCalCfgEntry  4 }


	cellSpeCalCfgDwptsMcsSingleLimit		 OBJECT-TYPE
		SYNTAX					 Integer32( 0 .. 28 )
		MAX-ACCESS			 read-create
		STATUS					 current
		DESCRIPTION			 " -- "
		::=  { cellSpecialCalCfgEntry  5 }


	cellSpeCalCfgDwptsCqiFlag		 OBJECT-TYPE
		SYNTAX					 INTEGER{ close(0),nopartake(1)  }
		MAX-ACCESS			 read-create
		STATUS					 current
		DESCRIPTION			 " -- "
		::=  { cellSpecialCalCfgEntry  6 }


	cellSpeCalCfgDwptsRetxFlag		 OBJECT-TYPE
		SYNTAX					 INTEGER{ nolimit(0),noretx(1)  }
		MAX-ACCESS			 read-create
		STATUS					 current
		DESCRIPTION			 " -- "
		::=  { cellSpecialCalCfgEntry  7 }


	cellSpeCalCfgDwptsTransFlag		 OBJECT-TYPE
		SYNTAX					 Integer32( 0 .. 1 )
		MAX-ACCESS			 read-create
		STATUS					 current
		DESCRIPTION			 " -- "
		::=  { cellSpecialCalCfgEntry  9 }


	cellSpeCalCfgMacAckCollideMcsThr		 OBJECT-TYPE
		SYNTAX					 Integer32( 0 .. 28 )
		MAX-ACCESS			 read-create
		STATUS					 current
		DESCRIPTION			 " -- "
		::=  { cellSpecialCalCfgEntry  10 }


	cellSpeCalCfgOffsetArray		 OBJECT-TYPE
		SYNTAX					 Unsigned32Array
		MAX-ACCESS			 read-create
		STATUS					 current
		DESCRIPTION			 " -- "
		::=  { cellSpecialCalCfgEntry  11 }


	hlSctSourceTable		 OBJECT-TYPE
		SYNTAX					 SEQUENCE  OF	 HlSctSourceEntry
		MAX-ACCESS			 not-accessible
		STATUS					 current
		DESCRIPTION			 " -- "
		::=  { localCell  11 }


	hlSctSourceEntry		 OBJECT-TYPE
		SYNTAX					 HlSctSourceEntry
		MAX-ACCESS			 not-accessible
		STATUS					 current
		DESCRIPTION			 " -- "
		INDEX						{ hlSctSourceRackNo,hlSctSourceShelfNo,hlSctSourceSlotNo,hlSctSourceCoreIndex,hlSctSourceCellIndexOnCore }
		::=  { hlSctSourceTable  1 }


	HlSctSourceEntry		 ::=  SEQUENCE {
		hlSctSourceRackNo					Integer32,
		hlSctSourceShelfNo					Integer32,
		hlSctSourceSlotNo					Integer32,
		hlSctSourceCoreIndex					Integer32,
		hlSctSourceCellIndexOnCore					Integer32,
		hlSctSourceRowStatus					RowStatus,
		hlSctSourceLcId					Integer32,
		hlSctSourceEngagedState					INTEGER,
		hlSctSourceUsableState					INTEGER
		}


	hlSctSourceRackNo		 OBJECT-TYPE
		SYNTAX					 Integer32( 0 .. 0 )
		MAX-ACCESS			 not-accessible
		STATUS					 current
		DESCRIPTION			 " -- "
		::=  { hlSctSourceEntry  1 }


	hlSctSourceShelfNo		 OBJECT-TYPE
		SYNTAX					 Integer32( 0 .. 0 )
		MAX-ACCESS			 not-accessible
		STATUS					 current
		DESCRIPTION			 " -- "
		::=  { hlSctSourceEntry  2 }


	hlSctSourceSlotNo		 OBJECT-TYPE
		SYNTAX					 Integer32( 1 .. 1 )
		MAX-ACCESS			 not-accessible
		STATUS					 current
		DESCRIPTION			 " -- "
		::=  { hlSctSourceEntry  3 }


	hlSctSourceCoreIndex		 OBJECT-TYPE
		SYNTAX					 Integer32( 0 .. 10 )
		MAX-ACCESS			 not-accessible
		STATUS					 current
		DESCRIPTION			 " -- "
		::=  { hlSctSourceEntry  4 }


	hlSctSourceCellIndexOnCore		 OBJECT-TYPE
		SYNTAX					 Integer32( 0 .. 23 )
		MAX-ACCESS			 not-accessible
		STATUS					 current
		DESCRIPTION			 " -- "
		::=  { hlSctSourceEntry  5 }


	hlSctSourceRowStatus		 OBJECT-TYPE
		SYNTAX					 RowStatus
		MAX-ACCESS			 read-only
		STATUS					 current
		DESCRIPTION			 " -- "
		::=  { hlSctSourceEntry  6 }


	hlSctSourceLcId		 OBJECT-TYPE
		SYNTAX					 Integer32( 0 .. 71|-1 )
		MAX-ACCESS			 read-only
		STATUS					 current
		DESCRIPTION			 " -- "
		::=  { hlSctSourceEntry  7 }


	hlSctSourceEngagedState		 OBJECT-TYPE
		SYNTAX					 INTEGER{ free(0),preengage(1),engaging(2),engaged(3)  }
		MAX-ACCESS			 read-only
		STATUS					 current
		DESCRIPTION			 " -- "
		::=  { hlSctSourceEntry  8 }


	hlSctSourceUsableState		 OBJECT-TYPE
		SYNTAX					 INTEGER{ enable(0),disable(1)  }
		MAX-ACCESS			 read-only
		STATUS					 current
		DESCRIPTION			 " -- "
		::=  { hlSctSourceEntry  9 }


	macBbuSourceTable		 OBJECT-TYPE
		SYNTAX					 SEQUENCE  OF	 MacBbuSourceEntry
		MAX-ACCESS			 not-accessible
		STATUS					 current
		DESCRIPTION			 " -- "
		::=  { localCell  12 }


	macBbuSourceEntry		 OBJECT-TYPE
		SYNTAX					 MacBbuSourceEntry
		MAX-ACCESS			 not-accessible
		STATUS					 current
		DESCRIPTION			 " -- "
		INDEX						{ macBbuSourceRackNo,macBbuSourceShelfNo,macBbuSourceSlotNo,macBbuSourceIndex }
		::=  { macBbuSourceTable  1 }


	MacBbuSourceEntry		 ::=  SEQUENCE {
		macBbuSourceRackNo					Integer32,
		macBbuSourceShelfNo					Integer32,
		macBbuSourceSlotNo					Integer32,
		macBbuSourceIndex					Integer32,
		macBbuSourceRowStatus					RowStatus,
		macBbuSourceCoreIndex					Integer32,
		macBbuSourceLcId					Integer32,
		macBbuSourceEngagedState					INTEGER,
		macBbuSourceOperationalState					INTEGER,
		macBbuRlcCoreIndex					Integer32,
		macBbuSocIndex					Integer32
		}


	macBbuSourceRackNo		 OBJECT-TYPE
		SYNTAX					 Integer32( 0 .. 0 )
		MAX-ACCESS			 not-accessible
		STATUS					 current
		DESCRIPTION			 " -- "
		::=  { macBbuSourceEntry  1 }


	macBbuSourceShelfNo		 OBJECT-TYPE
		SYNTAX					 Integer32( 0 .. 0 )
		MAX-ACCESS			 not-accessible
		STATUS					 current
		DESCRIPTION			 " -- "
		::=  { macBbuSourceEntry  2 }


	macBbuSourceSlotNo		 OBJECT-TYPE
		SYNTAX					 Integer32( 2 .. 7 )
		MAX-ACCESS			 not-accessible
		STATUS					 current
		DESCRIPTION			 " -- "
		::=  { macBbuSourceEntry  3 }


	macBbuSourceIndex		 OBJECT-TYPE
		SYNTAX					 Integer32( 0 .. 5 )
		MAX-ACCESS			 not-accessible
		STATUS					 current
		DESCRIPTION			 " -- "
		::=  { macBbuSourceEntry  4 }


	macBbuSourceRowStatus		 OBJECT-TYPE
		SYNTAX					 RowStatus
		MAX-ACCESS			 read-only
		STATUS					 current
		DESCRIPTION			 " -- "
		::=  { macBbuSourceEntry  5 }


	macBbuSourceCoreIndex		 OBJECT-TYPE
		SYNTAX					 Integer32( 0 .. 21 )
		MAX-ACCESS			 read-only
		STATUS					 current
		DESCRIPTION			 " -- "
		::=  { macBbuSourceEntry  6 }


	macBbuSourceLcId		 OBJECT-TYPE
		SYNTAX					 Integer32( 0 .. 11|-1 )
		MAX-ACCESS			 read-only
		STATUS					 current
		DESCRIPTION			 " -- "
		::=  { macBbuSourceEntry  7 }


	macBbuSourceEngagedState		 OBJECT-TYPE
		SYNTAX					 INTEGER{ free(0),engaging(2),engaged(3)  }
		MAX-ACCESS			 read-only
		STATUS					 current
		DESCRIPTION			 " -- "
		::=  { macBbuSourceEntry  8 }


	macBbuSourceOperationalState		 OBJECT-TYPE
		SYNTAX					 INTEGER{ enabled(0),disabled(1),invalid(2)  }
		MAX-ACCESS			 read-only
		STATUS					 current
		DESCRIPTION			 " -- "
		::=  { macBbuSourceEntry  9 }


	macBbuRlcCoreIndex		 OBJECT-TYPE
		SYNTAX					 Integer32( 0 .. 21 )
		MAX-ACCESS			 read-only
		STATUS					 current
		DESCRIPTION			 " -- "
		::=  { macBbuSourceEntry  10 }


	macBbuSocIndex		 OBJECT-TYPE
		SYNTAX					 Integer32( 0 .. 1|-1 )
		MAX-ACCESS			 read-only
		STATUS					 current
		DESCRIPTION			 " -- "
		::=  { macBbuSourceEntry  11 }


	pdcpBbuSourceTable		 OBJECT-TYPE
		SYNTAX					 SEQUENCE  OF	 PdcpBbuSourceEntry
		MAX-ACCESS			 not-accessible
		STATUS					 current
		DESCRIPTION			 " -- "
		::=  { localCell  13 }


	pdcpBbuSourceEntry		 OBJECT-TYPE
		SYNTAX					 PdcpBbuSourceEntry
		MAX-ACCESS			 not-accessible
		STATUS					 current
		DESCRIPTION			 " -- "
		INDEX						{ pdcpBbuSourceRackNo,pdcpBbuSourceShelfNo,pdcpBbuSourceSlotNo,pdcpBbuSourceIndex }
		::=  { pdcpBbuSourceTable  1 }


	PdcpBbuSourceEntry		 ::=  SEQUENCE {
		pdcpBbuSourceRackNo					Integer32,
		pdcpBbuSourceShelfNo					Integer32,
		pdcpBbuSourceSlotNo					Integer32,
		pdcpBbuSourceIndex					Integer32,
		pdcpBbuSourceRowStatus					RowStatus,
		pdcpBbuSourceCoreIndex					Integer32,
		pdcpBbuSourceLcId					Integer32,
		pdcpBbuSourceEngagedState					INTEGER,
		pdcpBbuSourceOperationalState					INTEGER,
		pdcpBbuSocIndex					Integer32
		}


	pdcpBbuSourceRackNo		 OBJECT-TYPE
		SYNTAX					 Integer32( 0 .. 0 )
		MAX-ACCESS			 not-accessible
		STATUS					 current
		DESCRIPTION			 " -- "
		::=  { pdcpBbuSourceEntry  1 }


	pdcpBbuSourceShelfNo		 OBJECT-TYPE
		SYNTAX					 Integer32( 0 .. 0 )
		MAX-ACCESS			 not-accessible
		STATUS					 current
		DESCRIPTION			 " -- "
		::=  { pdcpBbuSourceEntry  2 }


	pdcpBbuSourceSlotNo		 OBJECT-TYPE
		SYNTAX					 Integer32( 2 .. 7 )
		MAX-ACCESS			 not-accessible
		STATUS					 current
		DESCRIPTION			 " -- "
		::=  { pdcpBbuSourceEntry  3 }


	pdcpBbuSourceIndex		 OBJECT-TYPE
		SYNTAX					 Integer32( 0 .. 5 )
		MAX-ACCESS			 not-accessible
		STATUS					 current
		DESCRIPTION			 " -- "
		::=  { pdcpBbuSourceEntry  4 }


	pdcpBbuSourceRowStatus		 OBJECT-TYPE
		SYNTAX					 RowStatus
		MAX-ACCESS			 read-only
		STATUS					 current
		DESCRIPTION			 " -- "
		::=  { pdcpBbuSourceEntry  5 }


	pdcpBbuSourceCoreIndex		 OBJECT-TYPE
		SYNTAX					 Integer32( 0 .. 21 )
		MAX-ACCESS			 read-only
		STATUS					 current
		DESCRIPTION			 " -- "
		::=  { pdcpBbuSourceEntry  6 }


	pdcpBbuSourceLcId		 OBJECT-TYPE
		SYNTAX					 Integer32( 0 .. 11|-1 )
		MAX-ACCESS			 read-only
		STATUS					 current
		DESCRIPTION			 " -- "
		::=  { pdcpBbuSourceEntry  7 }


	pdcpBbuSourceEngagedState		 OBJECT-TYPE
		SYNTAX					 INTEGER{ free(0),engaging(2),engaged(3)  }
		MAX-ACCESS			 read-only
		STATUS					 current
		DESCRIPTION			 " -- "
		::=  { pdcpBbuSourceEntry  8 }


	pdcpBbuSourceOperationalState		 OBJECT-TYPE
		SYNTAX					 INTEGER{ enabled(0),disabled(1),invalid(2)  }
		MAX-ACCESS			 read-only
		STATUS					 current
		DESCRIPTION			 " -- "
		::=  { pdcpBbuSourceEntry  9 }


	pdcpBbuSocIndex		 OBJECT-TYPE
		SYNTAX					 Integer32( 0 .. 1|-1 )
		MAX-ACCESS			 read-only
		STATUS					 current
		DESCRIPTION			 " -- "
		::=  { pdcpBbuSourceEntry  10 }


	cellBoardLogTable		 OBJECT-TYPE
		SYNTAX					 SEQUENCE  OF	 CellBoardLogEntry
		MAX-ACCESS			 not-accessible
		STATUS					 current
		DESCRIPTION			 " -- "
		::=  { localCell  14 }


	cellBoardLogEntry		 OBJECT-TYPE
		SYNTAX					 CellBoardLogEntry
		MAX-ACCESS			 not-accessible
		STATUS					 current
		DESCRIPTION			 " -- "
		INDEX						{ cellBoardLoglcId }
		::=  { cellBoardLogTable  1 }


	CellBoardLogEntry		 ::=  SEQUENCE {
		cellBoardLoglcId					Integer32,
		cellBoardLogRowStatus					RowStatus,
		cellBoardLogRackNo					Integer32,
		cellBoardLogShelfNo					Integer32,
		cellBoardLogSlotNo					Integer32,
		cellBoardLogCoreIndex					Unsigned32Array
		}


	cellBoardLoglcId		 OBJECT-TYPE
		SYNTAX					 Integer32( 0 .. 23 )
		MAX-ACCESS			 not-accessible
		STATUS					 current
		DESCRIPTION			 " -- "
		::=  { cellBoardLogEntry  1 }


	cellBoardLogRowStatus		 OBJECT-TYPE
		SYNTAX					 RowStatus
		MAX-ACCESS			 read-only
		STATUS					 current
		DESCRIPTION			 " -- "
		::=  { cellBoardLogEntry  2 }


	cellBoardLogRackNo		 OBJECT-TYPE
		SYNTAX					 Integer32( 0 .. 0 )
		MAX-ACCESS			 read-only
		STATUS					 current
		DESCRIPTION			 " -- "
		::=  { cellBoardLogEntry  3 }


	cellBoardLogShelfNo		 OBJECT-TYPE
		SYNTAX					 Integer32( 0 .. 0 )
		MAX-ACCESS			 read-only
		STATUS					 current
		DESCRIPTION			 " -- "
		::=  { cellBoardLogEntry  4 }


	cellBoardLogSlotNo		 OBJECT-TYPE
		SYNTAX					 Integer32( 2 .. 7 )
		MAX-ACCESS			 read-only
		STATUS					 current
		DESCRIPTION			 " -- "
		::=  { cellBoardLogEntry  5 }


	cellBoardLogCoreIndex		 OBJECT-TYPE
		SYNTAX					 Unsigned32Array
		MAX-ACCESS			 read-only
		STATUS					 current
		DESCRIPTION			 " -- "
		::=  { cellBoardLogEntry  6 }


	cellRruCellTxPowerTable		 OBJECT-TYPE
		SYNTAX					 SEQUENCE  OF	 CellRruCellTxPowerEntry
		MAX-ACCESS			 not-accessible
		STATUS					 current
		DESCRIPTION			 " -- "
		::=  { localCell  15 }


	cellRruCellTxPowerEntry		 OBJECT-TYPE
		SYNTAX					 CellRruCellTxPowerEntry
		MAX-ACCESS			 not-accessible
		STATUS					 current
		DESCRIPTION			 " -- "
		INDEX						{ cellRruNo,cellRruLcNo }
		::=  { cellRruCellTxPowerTable  1 }


	CellRruCellTxPowerEntry		 ::=  SEQUENCE {
		cellRruNo					Integer32,
		cellRruLcNo					Integer32,
		cellRruRowStatus					RowStatus,
		cellRruCellLcId					Integer32,
		cellRruCellTxPower					Integer32
		}


	cellRruNo		 OBJECT-TYPE
		SYNTAX					 Integer32( 0 .. 47 )
		MAX-ACCESS			 not-accessible
		STATUS					 current
		DESCRIPTION			 " -- "
		::=  { cellRruCellTxPowerEntry  1 }


	cellRruLcNo		 OBJECT-TYPE
		SYNTAX					 Integer32( 0 .. 5 )
		MAX-ACCESS			 not-accessible
		STATUS					 current
		DESCRIPTION			 " -- "
		::=  { cellRruCellTxPowerEntry  2 }


	cellRruRowStatus		 OBJECT-TYPE
		SYNTAX					 RowStatus
		MAX-ACCESS			 read-only
		STATUS					 current
		DESCRIPTION			 " -- "
		::=  { cellRruCellTxPowerEntry  3 }


	cellRruCellLcId		 OBJECT-TYPE
		SYNTAX					 Integer32( 0 .. 35 )
		MAX-ACCESS			 read-only
		STATUS					 current
		DESCRIPTION			 " -- "
		::=  { cellRruCellTxPowerEntry  4 }


	cellRruCellTxPower		 OBJECT-TYPE
		SYNTAX					 Integer32( 0 .. 600 )
		MAX-ACCESS			 read-only
		STATUS					 current
		DESCRIPTION			 " -- "
		::=  { cellRruCellTxPowerEntry  5 }


	cellAntennaWeightTable		 OBJECT-TYPE
		SYNTAX					 SEQUENCE  OF	 CellAntennaWeightEntry
		MAX-ACCESS			 not-accessible
		STATUS					 current
		DESCRIPTION			 " -- "
		::=  { localCell  16 }


	cellAntennaWeightEntry		 OBJECT-TYPE
		SYNTAX					 CellAntennaWeightEntry
		MAX-ACCESS			 not-accessible
		STATUS					 current
		DESCRIPTION			 " -- "
		INDEX						{ cellAntWeightLcId }
		::=  { cellAntennaWeightTable  1 }


	CellAntennaWeightEntry		 ::=  SEQUENCE {
		cellAntWeightLcId					Integer32,
		cellAntWeightRowStatus					RowStatus,
		cellAntWeightAmplitude0					Integer32,
		cellAntWeightPhase0					Integer32,
		cellAntWeightAmplitude1					Integer32,
		cellAntWeightPhase1					Integer32,
		cellAntWeightAmplitude2					Integer32,
		cellAntWeightPhase2					Integer32,
		cellAntWeightAmplitude3					Integer32,
		cellAntWeightPhase3					Integer32,
		cellAntWeightAmplitude4					Integer32,
		cellAntWeightPhase4					Integer32,
		cellAntWeightAmplitude5					Integer32,
		cellAntWeightPhase5					Integer32,
		cellAntWeightAmplitude6					Integer32,
		cellAntWeightPhase6					Integer32,
		cellAntWeightAmplitude7					Integer32,
		cellAntWeightPhase7					Integer32,
		cellAntWeightAmplitude8					Integer32,
		cellAntWeightPhase8					Integer32,
		cellAntWeightAmplitude9					Integer32,
		cellAntWeightPhase9					Integer32,
		cellAntWeightAmplitude10					Integer32,
		cellAntWeightPhase10					Integer32,
		cellAntWeightAmplitude11					Integer32,
		cellAntWeightPhase11					Integer32,
		cellAntWeightAmplitude12					Integer32,
		cellAntWeightPhase12					Integer32,
		cellAntWeightAmplitude13					Integer32,
		cellAntWeightPhase13					Integer32,
		cellAntWeightAmplitude14					Integer32,
		cellAntWeightPhase14					Integer32,
		cellAntWeightAmplitude15					Integer32,
		cellAntWeightPhase15					Integer32,
		cellAntWeightAmplitude16					Integer32,
		cellAntWeightPhase16					Integer32,
		cellAntWeightAmplitude17					Integer32,
		cellAntWeightPhase17					Integer32,
		cellAntWeightAmplitude18					Integer32,
		cellAntWeightPhase18					Integer32,
		cellAntWeightAmplitude19					Integer32,
		cellAntWeightPhase19					Integer32,
		cellAntWeightAmplitude20					Integer32,
		cellAntWeightPhase20					Integer32,
		cellAntWeightAmplitude21					Integer32,
		cellAntWeightPhase21					Integer32,
		cellAntWeightAmplitude22					Integer32,
		cellAntWeightPhase22					Integer32,
		cellAntWeightAmplitude23					Integer32,
		cellAntWeightPhase23					Integer32
		}


	cellAntWeightLcId		 OBJECT-TYPE
		SYNTAX					 Integer32( 0 .. 23 )
		MAX-ACCESS			 not-accessible
		STATUS					 current
		DESCRIPTION			 " -- "
		::=  { cellAntennaWeightEntry  1 }


	cellAntWeightRowStatus		 OBJECT-TYPE
		SYNTAX					 RowStatus
		MAX-ACCESS			 read-only
		STATUS					 current
		DESCRIPTION			 " -- "
		::=  { cellAntennaWeightEntry  2 }


	cellAntWeightAmplitude0		 OBJECT-TYPE
		SYNTAX					 Integer32( -2147483648 .. 2147483647 )
		MAX-ACCESS			 read-only
		STATUS					 current
		DESCRIPTION			 " -- "
		::=  { cellAntennaWeightEntry  3 }


	cellAntWeightPhase0		 OBJECT-TYPE
		SYNTAX					 Integer32( -2147483648 .. 2147483647 )
		MAX-ACCESS			 read-only
		STATUS					 current
		DESCRIPTION			 " -- "
		::=  { cellAntennaWeightEntry  4 }


	cellAntWeightAmplitude1		 OBJECT-TYPE
		SYNTAX					 Integer32( -2147483648 .. 2147483647 )
		MAX-ACCESS			 read-only
		STATUS					 current
		DESCRIPTION			 " -- "
		::=  { cellAntennaWeightEntry  5 }


	cellAntWeightPhase1		 OBJECT-TYPE
		SYNTAX					 Integer32( -2147483648 .. 2147483647 )
		MAX-ACCESS			 read-only
		STATUS					 current
		DESCRIPTION			 " -- "
		::=  { cellAntennaWeightEntry  6 }


	cellAntWeightAmplitude2		 OBJECT-TYPE
		SYNTAX					 Integer32( -2147483648 .. 2147483647 )
		MAX-ACCESS			 read-only
		STATUS					 current
		DESCRIPTION			 " -- "
		::=  { cellAntennaWeightEntry  7 }


	cellAntWeightPhase2		 OBJECT-TYPE
		SYNTAX					 Integer32( -2147483648 .. 2147483647 )
		MAX-ACCESS			 read-only
		STATUS					 current
		DESCRIPTION			 " -- "
		::=  { cellAntennaWeightEntry  8 }


	cellAntWeightAmplitude3		 OBJECT-TYPE
		SYNTAX					 Integer32( -2147483648 .. 2147483647 )
		MAX-ACCESS			 read-only
		STATUS					 current
		DESCRIPTION			 " -- "
		::=  { cellAntennaWeightEntry  9 }


	cellAntWeightPhase3		 OBJECT-TYPE
		SYNTAX					 Integer32( -2147483648 .. 2147483647 )
		MAX-ACCESS			 read-only
		STATUS					 current
		DESCRIPTION			 " -- "
		::=  { cellAntennaWeightEntry  10 }


	cellAntWeightAmplitude4		 OBJECT-TYPE
		SYNTAX					 Integer32( -2147483648 .. 2147483647 )
		MAX-ACCESS			 read-only
		STATUS					 current
		DESCRIPTION			 " -- "
		::=  { cellAntennaWeightEntry  11 }


	cellAntWeightPhase4		 OBJECT-TYPE
		SYNTAX					 Integer32( -2147483648 .. 2147483647 )
		MAX-ACCESS			 read-only
		STATUS					 current
		DESCRIPTION			 " -- "
		::=  { cellAntennaWeightEntry  12 }


	cellAntWeightAmplitude5		 OBJECT-TYPE
		SYNTAX					 Integer32( -2147483648 .. 2147483647 )
		MAX-ACCESS			 read-only
		STATUS					 current
		DESCRIPTION			 " -- "
		::=  { cellAntennaWeightEntry  13 }


	cellAntWeightPhase5		 OBJECT-TYPE
		SYNTAX					 Integer32( -2147483648 .. 2147483647 )
		MAX-ACCESS			 read-only
		STATUS					 current
		DESCRIPTION			 " -- "
		::=  { cellAntennaWeightEntry  14 }


	cellAntWeightAmplitude6		 OBJECT-TYPE
		SYNTAX					 Integer32( -2147483648 .. 2147483647 )
		MAX-ACCESS			 read-only
		STATUS					 current
		DESCRIPTION			 " -- "
		::=  { cellAntennaWeightEntry  15 }


	cellAntWeightPhase6		 OBJECT-TYPE
		SYNTAX					 Integer32( -2147483648 .. 2147483647 )
		MAX-ACCESS			 read-only
		STATUS					 current
		DESCRIPTION			 " -- "
		::=  { cellAntennaWeightEntry  16 }


	cellAntWeightAmplitude7		 OBJECT-TYPE
		SYNTAX					 Integer32( -2147483648 .. 2147483647 )
		MAX-ACCESS			 read-only
		STATUS					 current
		DESCRIPTION			 " -- "
		::=  { cellAntennaWeightEntry  17 }


	cellAntWeightPhase7		 OBJECT-TYPE
		SYNTAX					 Integer32( -2147483648 .. 2147483647 )
		MAX-ACCESS			 read-only
		STATUS					 current
		DESCRIPTION			 " -- "
		::=  { cellAntennaWeightEntry  18 }


	cellAntWeightAmplitude8		 OBJECT-TYPE
		SYNTAX					 Integer32( -2147483648 .. 2147483647 )
		MAX-ACCESS			 read-only
		STATUS					 current
		DESCRIPTION			 " -- "
		::=  { cellAntennaWeightEntry  19 }


	cellAntWeightPhase8		 OBJECT-TYPE
		SYNTAX					 Integer32( -2147483648 .. 2147483647 )
		MAX-ACCESS			 read-only
		STATUS					 current
		DESCRIPTION			 " -- "
		::=  { cellAntennaWeightEntry  20 }


	cellAntWeightAmplitude9		 OBJECT-TYPE
		SYNTAX					 Integer32( -2147483648 .. 2147483647 )
		MAX-ACCESS			 read-only
		STATUS					 current
		DESCRIPTION			 " -- "
		::=  { cellAntennaWeightEntry  21 }


	cellAntWeightPhase9		 OBJECT-TYPE
		SYNTAX					 Integer32( -2147483648 .. 2147483647 )
		MAX-ACCESS			 read-only
		STATUS					 current
		DESCRIPTION			 " -- "
		::=  { cellAntennaWeightEntry  22 }


	cellAntWeightAmplitude10		 OBJECT-TYPE
		SYNTAX					 Integer32( -2147483648 .. 2147483647 )
		MAX-ACCESS			 read-only
		STATUS					 current
		DESCRIPTION			 " -- "
		::=  { cellAntennaWeightEntry  23 }


	cellAntWeightPhase10		 OBJECT-TYPE
		SYNTAX					 Integer32( -2147483648 .. 2147483647 )
		MAX-ACCESS			 read-only
		STATUS					 current
		DESCRIPTION			 " -- "
		::=  { cellAntennaWeightEntry  24 }


	cellAntWeightAmplitude11		 OBJECT-TYPE
		SYNTAX					 Integer32( -2147483648 .. 2147483647 )
		MAX-ACCESS			 read-only
		STATUS					 current
		DESCRIPTION			 " -- "
		::=  { cellAntennaWeightEntry  25 }


	cellAntWeightPhase11		 OBJECT-TYPE
		SYNTAX					 Integer32( -2147483648 .. 2147483647 )
		MAX-ACCESS			 read-only
		STATUS					 current
		DESCRIPTION			 " -- "
		::=  { cellAntennaWeightEntry  26 }


	cellAntWeightAmplitude12		 OBJECT-TYPE
		SYNTAX					 Integer32( -2147483648 .. 2147483647 )
		MAX-ACCESS			 read-only
		STATUS					 current
		DESCRIPTION			 " -- "
		::=  { cellAntennaWeightEntry  27 }


	cellAntWeightPhase12		 OBJECT-TYPE
		SYNTAX					 Integer32( -2147483648 .. 2147483647 )
		MAX-ACCESS			 read-only
		STATUS					 current
		DESCRIPTION			 " -- "
		::=  { cellAntennaWeightEntry  28 }


	cellAntWeightAmplitude13		 OBJECT-TYPE
		SYNTAX					 Integer32( -2147483648 .. 2147483647 )
		MAX-ACCESS			 read-only
		STATUS					 current
		DESCRIPTION			 " -- "
		::=  { cellAntennaWeightEntry  29 }


	cellAntWeightPhase13		 OBJECT-TYPE
		SYNTAX					 Integer32( -2147483648 .. 2147483647 )
		MAX-ACCESS			 read-only
		STATUS					 current
		DESCRIPTION			 " -- "
		::=  { cellAntennaWeightEntry  30 }


	cellAntWeightAmplitude14		 OBJECT-TYPE
		SYNTAX					 Integer32( -2147483648 .. 2147483647 )
		MAX-ACCESS			 read-only
		STATUS					 current
		DESCRIPTION			 " -- "
		::=  { cellAntennaWeightEntry  31 }


	cellAntWeightPhase14		 OBJECT-TYPE
		SYNTAX					 Integer32( -2147483648 .. 2147483647 )
		MAX-ACCESS			 read-only
		STATUS					 current
		DESCRIPTION			 " -- "
		::=  { cellAntennaWeightEntry  32 }


	cellAntWeightAmplitude15		 OBJECT-TYPE
		SYNTAX					 Integer32( -2147483648 .. 2147483647 )
		MAX-ACCESS			 read-only
		STATUS					 current
		DESCRIPTION			 " -- "
		::=  { cellAntennaWeightEntry  33 }


	cellAntWeightPhase15		 OBJECT-TYPE
		SYNTAX					 Integer32( -2147483648 .. 2147483647 )
		MAX-ACCESS			 read-only
		STATUS					 current
		DESCRIPTION			 " -- "
		::=  { cellAntennaWeightEntry  34 }


	cellAntWeightAmplitude16		 OBJECT-TYPE
		SYNTAX					 Integer32( -2147483648 .. 2147483647 )
		MAX-ACCESS			 read-only
		STATUS					 current
		DESCRIPTION			 " -- "
		::=  { cellAntennaWeightEntry  35 }


	cellAntWeightPhase16		 OBJECT-TYPE
		SYNTAX					 Integer32( -2147483648 .. 2147483647 )
		MAX-ACCESS			 read-only
		STATUS					 current
		DESCRIPTION			 " -- "
		::=  { cellAntennaWeightEntry  36 }


	cellAntWeightAmplitude17		 OBJECT-TYPE
		SYNTAX					 Integer32( -2147483648 .. 2147483647 )
		MAX-ACCESS			 read-only
		STATUS					 current
		DESCRIPTION			 " -- "
		::=  { cellAntennaWeightEntry  37 }


	cellAntWeightPhase17		 OBJECT-TYPE
		SYNTAX					 Integer32( -2147483648 .. 2147483647 )
		MAX-ACCESS			 read-only
		STATUS					 current
		DESCRIPTION			 " -- "
		::=  { cellAntennaWeightEntry  38 }


	cellAntWeightAmplitude18		 OBJECT-TYPE
		SYNTAX					 Integer32( -2147483648 .. 2147483647 )
		MAX-ACCESS			 read-only
		STATUS					 current
		DESCRIPTION			 " -- "
		::=  { cellAntennaWeightEntry  39 }


	cellAntWeightPhase18		 OBJECT-TYPE
		SYNTAX					 Integer32( -2147483648 .. 2147483647 )
		MAX-ACCESS			 read-only
		STATUS					 current
		DESCRIPTION			 " -- "
		::=  { cellAntennaWeightEntry  40 }


	cellAntWeightAmplitude19		 OBJECT-TYPE
		SYNTAX					 Integer32( -2147483648 .. 2147483647 )
		MAX-ACCESS			 read-only
		STATUS					 current
		DESCRIPTION			 " -- "
		::=  { cellAntennaWeightEntry  41 }


	cellAntWeightPhase19		 OBJECT-TYPE
		SYNTAX					 Integer32( -2147483648 .. 2147483647 )
		MAX-ACCESS			 read-only
		STATUS					 current
		DESCRIPTION			 " -- "
		::=  { cellAntennaWeightEntry  42 }


	cellAntWeightAmplitude20		 OBJECT-TYPE
		SYNTAX					 Integer32( -2147483648 .. 2147483647 )
		MAX-ACCESS			 read-only
		STATUS					 current
		DESCRIPTION			 " -- "
		::=  { cellAntennaWeightEntry  43 }


	cellAntWeightPhase20		 OBJECT-TYPE
		SYNTAX					 Integer32( -2147483648 .. 2147483647 )
		MAX-ACCESS			 read-only
		STATUS					 current
		DESCRIPTION			 " -- "
		::=  { cellAntennaWeightEntry  44 }


	cellAntWeightAmplitude21		 OBJECT-TYPE
		SYNTAX					 Integer32( -2147483648 .. 2147483647 )
		MAX-ACCESS			 read-only
		STATUS					 current
		DESCRIPTION			 " -- "
		::=  { cellAntennaWeightEntry  45 }


	cellAntWeightPhase21		 OBJECT-TYPE
		SYNTAX					 Integer32( -2147483648 .. 2147483647 )
		MAX-ACCESS			 read-only
		STATUS					 current
		DESCRIPTION			 " -- "
		::=  { cellAntennaWeightEntry  46 }


	cellAntWeightAmplitude22		 OBJECT-TYPE
		SYNTAX					 Integer32( -2147483648 .. 2147483647 )
		MAX-ACCESS			 read-only
		STATUS					 current
		DESCRIPTION			 " -- "
		::=  { cellAntennaWeightEntry  47 }


	cellAntWeightPhase22		 OBJECT-TYPE
		SYNTAX					 Integer32( -2147483648 .. 2147483647 )
		MAX-ACCESS			 read-only
		STATUS					 current
		DESCRIPTION			 " -- "
		::=  { cellAntennaWeightEntry  48 }


	cellAntWeightAmplitude23		 OBJECT-TYPE
		SYNTAX					 Integer32( -2147483648 .. 2147483647 )
		MAX-ACCESS			 read-only
		STATUS					 current
		DESCRIPTION			 " -- "
		::=  { cellAntennaWeightEntry  49 }


	cellAntWeightPhase23		 OBJECT-TYPE
		SYNTAX					 Integer32( -2147483648 .. 2147483647 )
		MAX-ACCESS			 read-only
		STATUS					 current
		DESCRIPTION			 " -- "
		::=  { cellAntennaWeightEntry  50 }


	calibrationNode		 OBJECT IDENTIFIER
		::=  { calibration  1 }


	calAcEnable		 OBJECT-TYPE
		SYNTAX					 INTEGER{ enable(0),disable(1)  }
		MAX-ACCESS			 read-write
		STATUS					 current
		DESCRIPTION			 " -- "
		::=  { calibrationNode  1 }


	calAcPeriod		 OBJECT-TYPE
		SYNTAX					 Unsigned32( 60 .. 2100000 )
		MAX-ACCESS			 read-write
		STATUS					 current
		DESCRIPTION			 " -- "
		::=  { calibrationNode  2 }


	calcellCalRepeatLength		 OBJECT-TYPE
		SYNTAX					 INTEGER{ n2(0),n4(1),n8(2),n16(3)  }
		MAX-ACCESS			 read-create
		STATUS					 current
		DESCRIPTION			 " -- "
		::=  { calibrationNode  3 }


	calcellCalRepeatPeriod		 OBJECT-TYPE
		SYNTAX					 INTEGER{ n128(0),n256(1),n512(2),n1024(3)  }
		MAX-ACCESS			 read-create
		STATUS					 current
		DESCRIPTION			 " -- "
		::=  { calibrationNode  4 }


	calcellCalModeSwitch		 OBJECT-TYPE
		SYNTAX					 INTEGER{ off(0),on(1)  }
		MAX-ACCESS			 read-write
		STATUS					 current
		DESCRIPTION			 " -- "
		::=  { calibrationNode  5 }


	periodCalibrationTable		 OBJECT-TYPE
		SYNTAX					 SEQUENCE  OF	 PeriodCalibrationEntry
		MAX-ACCESS			 not-accessible
		STATUS					 current
		DESCRIPTION			 " -- "
		::=  { calibration  4 }


	periodCalibrationEntry		 OBJECT-TYPE
		SYNTAX					 PeriodCalibrationEntry
		MAX-ACCESS			 not-accessible
		STATUS					 current
		DESCRIPTION			 " -- "
		INDEX						{ periodCalibrationRRUNo,periodCalibrationPathNo }
		::=  { periodCalibrationTable  1 }


	PeriodCalibrationEntry		 ::=  SEQUENCE {
		periodCalibrationRRUNo					Integer32,
		periodCalibrationPathNo					Integer32,
		periodCalibrationRowStatus					RowStatus,
		periodCalibrationTxPeakPosShift					Integer32,
		periodCalibrationTxCalGain					Integer32,
		periodCalibrationRxPeakPosShift					Integer32,
		periodCalibrationRxCalGain					Integer32,
		periodCalibrationTxCalGainTds					Integer32,
		periodCalibrationRxCalGainTds					Integer32
		}


	periodCalibrationRRUNo		 OBJECT-TYPE
		SYNTAX					 Integer32( 0 .. 191 )
		MAX-ACCESS			 not-accessible
		STATUS					 current
		DESCRIPTION			 " -- "
		::=  { periodCalibrationEntry  1 }


	periodCalibrationPathNo		 OBJECT-TYPE
		SYNTAX					 Integer32( 1 .. 8 )
		MAX-ACCESS			 not-accessible
		STATUS					 current
		DESCRIPTION			 " -- "
		::=  { periodCalibrationEntry  2 }


	periodCalibrationRowStatus		 OBJECT-TYPE
		SYNTAX					 RowStatus
		MAX-ACCESS			 read-only
		STATUS					 current
		DESCRIPTION			 " -- "
		::=  { periodCalibrationEntry  3 }


	periodCalibrationTxPeakPosShift		 OBJECT-TYPE
		SYNTAX					 Integer32( -2147483648 .. 2147483647 )
		MAX-ACCESS			 read-only
		STATUS					 current
		DESCRIPTION			 " -- "
		::=  { periodCalibrationEntry  4 }


	periodCalibrationTxCalGain		 OBJECT-TYPE
		SYNTAX					 Integer32( -2147483648 .. 2147483647 )
		MAX-ACCESS			 read-only
		STATUS					 current
		DESCRIPTION			 " -- "
		::=  { periodCalibrationEntry  5 }


	periodCalibrationRxPeakPosShift		 OBJECT-TYPE
		SYNTAX					 Integer32( -2147483648 .. 2147483647 )
		MAX-ACCESS			 read-only
		STATUS					 current
		DESCRIPTION			 " -- "
		::=  { periodCalibrationEntry  6 }


	periodCalibrationRxCalGain		 OBJECT-TYPE
		SYNTAX					 Integer32( -2147483648 .. 2147483647 )
		MAX-ACCESS			 read-only
		STATUS					 current
		DESCRIPTION			 " -- "
		::=  { periodCalibrationEntry  7 }


	periodCalibrationTxCalGainTds		 OBJECT-TYPE
		SYNTAX					 Integer32( -2147483648 .. 2147483647 )
		MAX-ACCESS			 read-only
		STATUS					 current
		DESCRIPTION			 " -- "
		::=  { periodCalibrationEntry  8 }


	periodCalibrationRxCalGainTds		 OBJECT-TYPE
		SYNTAX					 Integer32( -2147483648 .. 2147483647 )
		MAX-ACCESS			 read-only
		STATUS					 current
		DESCRIPTION			 " -- "
		::=  { periodCalibrationEntry  9 }


	ssc		 OBJECT IDENTIFIER
		::=  { eNBConfig  7 }


	sscLicense		 OBJECT IDENTIFIER
		::=  { ssc  1 }


	sscSwitch		 OBJECT-TYPE
		SYNTAX					 INTEGER{ off(0),on(1)  }
		MAX-ACCESS			 read-write
		STATUS					 current
		DESCRIPTION			 " -- "
		::=  { sscLicense  1 }


	sscTaskTable		 OBJECT-TYPE
		SYNTAX					 SEQUENCE  OF	 SscTaskEntry
		MAX-ACCESS			 not-accessible
		STATUS					 current
		DESCRIPTION			 " -- "
		::=  { ssc  2 }


	sscTaskEntry		 OBJECT-TYPE
		SYNTAX					 SscTaskEntry
		MAX-ACCESS			 not-accessible
		STATUS					 current
		DESCRIPTION			 " -- "
		INDEX						{ sscTaskIndex }
		::=  { sscTaskTable  1 }


	SscTaskEntry		 ::=  SEQUENCE {
		sscTaskIndex					Integer32,
		sscTaskRowStatus					RowStatus,
		sscServerInetAddrType					InetAddressType,
		sscServerInetAddr					InetAddress,
		sscTaskCollectEntityPort					Integer32,
		sscTmValidNum					Unsigned32,
		sscStartTime1					Unsigned32,
		sscEndTime1					Unsigned32,
		sscStartTime2					Unsigned32,
		sscEndTime2					Unsigned32,
		sscStartTime3					Unsigned32,
		sscEndTime3					Unsigned32,
		sscStartTime4					Unsigned32,
		sscEndTime4					Unsigned32,
		sscStartTime5					Unsigned32,
		sscEndTime5					Unsigned32,
		sscOptSwitch					INTEGER,
		sscOptRptInterval					INTEGER,
		sscX2Switch					INTEGER,
		sscMaxUserNum					Unsigned32,
		sscUuSwitch					INTEGER,
		sscUuExternBitmap					Unsigned32Array,
		sscPagSwitch					INTEGER,
		sscUuBitmap					Unsigned32Array,
		sscX2Bitmap					Unsigned32Array,
		sscStartMinute1					Unsigned32,
		sscEndMinute1					Unsigned32,
		sscStartMinute2					Unsigned32,
		sscEndMinute2					Unsigned32,
		sscStartMinute3					Unsigned32,
		sscEndMinute3					Unsigned32,
		sscStartMinute4					Unsigned32,
		sscEndMinute4					Unsigned32,
		sscStartMinute5					Unsigned32,
		sscEndMinute5					Unsigned32
		}


	sscTaskIndex		 OBJECT-TYPE
		SYNTAX					 Integer32( 0 .. 0 )
		MAX-ACCESS			 not-accessible
		STATUS					 current
		DESCRIPTION			 " -- "
		::=  { sscTaskEntry  1 }


	sscTaskRowStatus		 OBJECT-TYPE
		SYNTAX					 RowStatus
		MAX-ACCESS			 read-create
		STATUS					 current
		DESCRIPTION			 " -- "
		::=  { sscTaskEntry  2 }


	sscServerInetAddrType		 OBJECT-TYPE
		SYNTAX					 InetAddressType
		MAX-ACCESS			 read-write
		STATUS					 current
		DESCRIPTION			 " -- "
		::=  { sscTaskEntry  3 }


	sscServerInetAddr		 OBJECT-TYPE
		SYNTAX					 InetAddress
		MAX-ACCESS			 read-write
		STATUS					 current
		DESCRIPTION			 " -- "
		::=  { sscTaskEntry  4 }


	sscTaskCollectEntityPort		 OBJECT-TYPE
		SYNTAX					 Integer32( 0 .. 65535 )
		MAX-ACCESS			 read-write
		STATUS					 current
		DESCRIPTION			 " -- "
		::=  { sscTaskEntry  5 }


	sscTmValidNum		 OBJECT-TYPE
		SYNTAX					 Unsigned32( 0 .. 5 )
		MAX-ACCESS			 read-write
		STATUS					 current
		DESCRIPTION			 " -- "
		::=  { sscTaskEntry  6 }


	sscStartTime1		 OBJECT-TYPE
		SYNTAX					 Unsigned32( 0 .. 23|24 )
		MAX-ACCESS			 read-write
		STATUS					 current
		DESCRIPTION			 " -- "
		::=  { sscTaskEntry  7 }


	sscEndTime1		 OBJECT-TYPE
		SYNTAX					 Unsigned32( 0 .. 23|24 )
		MAX-ACCESS			 read-write
		STATUS					 current
		DESCRIPTION			 " -- "
		::=  { sscTaskEntry  8 }


	sscStartTime2		 OBJECT-TYPE
		SYNTAX					 Unsigned32( 0 .. 23|24 )
		MAX-ACCESS			 read-write
		STATUS					 current
		DESCRIPTION			 " -- "
		::=  { sscTaskEntry  9 }


	sscEndTime2		 OBJECT-TYPE
		SYNTAX					 Unsigned32( 0 .. 23|24 )
		MAX-ACCESS			 read-write
		STATUS					 current
		DESCRIPTION			 " -- "
		::=  { sscTaskEntry  10 }


	sscStartTime3		 OBJECT-TYPE
		SYNTAX					 Unsigned32( 0 .. 23|24 )
		MAX-ACCESS			 read-write
		STATUS					 current
		DESCRIPTION			 " -- "
		::=  { sscTaskEntry  11 }


	sscEndTime3		 OBJECT-TYPE
		SYNTAX					 Unsigned32( 0 .. 23|24 )
		MAX-ACCESS			 read-write
		STATUS					 current
		DESCRIPTION			 " -- "
		::=  { sscTaskEntry  12 }


	sscStartTime4		 OBJECT-TYPE
		SYNTAX					 Unsigned32( 0 .. 23|24 )
		MAX-ACCESS			 read-write
		STATUS					 current
		DESCRIPTION			 " -- "
		::=  { sscTaskEntry  13 }


	sscEndTime4		 OBJECT-TYPE
		SYNTAX					 Unsigned32( 0 .. 23|24 )
		MAX-ACCESS			 read-write
		STATUS					 current
		DESCRIPTION			 " -- "
		::=  { sscTaskEntry  14 }


	sscStartTime5		 OBJECT-TYPE
		SYNTAX					 Unsigned32( 0 .. 23|24 )
		MAX-ACCESS			 read-write
		STATUS					 current
		DESCRIPTION			 " -- "
		::=  { sscTaskEntry  15 }


	sscEndTime5		 OBJECT-TYPE
		SYNTAX					 Unsigned32( 0 .. 23|24 )
		MAX-ACCESS			 read-write
		STATUS					 current
		DESCRIPTION			 " -- "
		::=  { sscTaskEntry  16 }


	sscOptSwitch		 OBJECT-TYPE
		SYNTAX					 INTEGER{ off(0),on(1)  }
		MAX-ACCESS			 read-write
		STATUS					 current
		DESCRIPTION			 " -- "
		::=  { sscTaskEntry  17 }


	sscOptRptInterval		 OBJECT-TYPE
		SYNTAX					 INTEGER{ ms1024(4),ms2048(5),ms5120(6),ms10240(7),min1(8),min6(9),min12(10),min30(11),min60(12)  }
		MAX-ACCESS			 read-write
		STATUS					 current
		DESCRIPTION			 " -- "
		::=  { sscTaskEntry  18 }


	sscX2Switch		 OBJECT-TYPE
		SYNTAX					 INTEGER{ off(0),tx(1),rx(2),txRx(3)  }
		MAX-ACCESS			 read-write
		STATUS					 current
		DESCRIPTION			 " -- "
		::=  { sscTaskEntry  19 }


	sscMaxUserNum		 OBJECT-TYPE
		SYNTAX					 Unsigned32( 1 .. 600 )
		MAX-ACCESS			 read-write
		STATUS					 current
		DESCRIPTION			 " -- "
		::=  { sscTaskEntry  20 }


	sscUuSwitch		 OBJECT-TYPE
		SYNTAX					 INTEGER{ off(0),on(1)  }
		MAX-ACCESS			 read-write
		STATUS					 current
		DESCRIPTION			 " -- "
		::=  { sscTaskEntry  21 }


	sscUuExternBitmap		 OBJECT-TYPE
		SYNTAX					 Unsigned32Array
		MAX-ACCESS			 read-write
		STATUS					 current
		DESCRIPTION			 " -- "
		::=  { sscTaskEntry  22 }


	sscPagSwitch		 OBJECT-TYPE
		SYNTAX					 INTEGER{ off(0),on(1)  }
		MAX-ACCESS			 read-write
		STATUS					 current
		DESCRIPTION			 " -- "
		::=  { sscTaskEntry  23 }


	sscUuBitmap		 OBJECT-TYPE
		SYNTAX					 Unsigned32Array
		MAX-ACCESS			 read-write
		STATUS					 current
		DESCRIPTION			 " -- "
		::=  { sscTaskEntry  25 }


	sscX2Bitmap		 OBJECT-TYPE
		SYNTAX					 Unsigned32Array
		MAX-ACCESS			 read-write
		STATUS					 current
		DESCRIPTION			 " -- "
		::=  { sscTaskEntry  26 }


	sscStartMinute1		 OBJECT-TYPE
		SYNTAX					 Unsigned32( 0 .. 59 )
		MAX-ACCESS			 read-write
		STATUS					 current
		DESCRIPTION			 " -- "
		::=  { sscTaskEntry  27 }


	sscEndMinute1		 OBJECT-TYPE
		SYNTAX					 Unsigned32( 0 .. 59 )
		MAX-ACCESS			 read-write
		STATUS					 current
		DESCRIPTION			 " -- "
		::=  { sscTaskEntry  28 }


	sscStartMinute2		 OBJECT-TYPE
		SYNTAX					 Unsigned32( 0 .. 59 )
		MAX-ACCESS			 read-write
		STATUS					 current
		DESCRIPTION			 " -- "
		::=  { sscTaskEntry  29 }


	sscEndMinute2		 OBJECT-TYPE
		SYNTAX					 Unsigned32( 0 .. 59 )
		MAX-ACCESS			 read-write
		STATUS					 current
		DESCRIPTION			 " -- "
		::=  { sscTaskEntry  30 }


	sscStartMinute3		 OBJECT-TYPE
		SYNTAX					 Unsigned32( 0 .. 59 )
		MAX-ACCESS			 read-write
		STATUS					 current
		DESCRIPTION			 " -- "
		::=  { sscTaskEntry  31 }


	sscEndMinute3		 OBJECT-TYPE
		SYNTAX					 Unsigned32( 0 .. 59 )
		MAX-ACCESS			 read-write
		STATUS					 current
		DESCRIPTION			 " -- "
		::=  { sscTaskEntry  32 }


	sscStartMinute4		 OBJECT-TYPE
		SYNTAX					 Unsigned32( 0 .. 59 )
		MAX-ACCESS			 read-write
		STATUS					 current
		DESCRIPTION			 " -- "
		::=  { sscTaskEntry  33 }


	sscEndMinute4		 OBJECT-TYPE
		SYNTAX					 Unsigned32( 0 .. 59 )
		MAX-ACCESS			 read-write
		STATUS					 current
		DESCRIPTION			 " -- "
		::=  { sscTaskEntry  34 }


	sscStartMinute5		 OBJECT-TYPE
		SYNTAX					 Unsigned32( 0 .. 59 )
		MAX-ACCESS			 read-write
		STATUS					 current
		DESCRIPTION			 " -- "
		::=  { sscTaskEntry  35 }


	sscEndMinute5		 OBJECT-TYPE
		SYNTAX					 Unsigned32( 0 .. 59 )
		MAX-ACCESS			 read-write
		STATUS					 current
		DESCRIPTION			 " -- "
		::=  { sscTaskEntry  36 }


	tdsLocalcell		 OBJECT IDENTIFIER
		::=  { eNBConfig  8 }


	tdsLocalCellTable		 OBJECT-TYPE
		SYNTAX					 SEQUENCE  OF	 TdsLocalCellEntry
		MAX-ACCESS			 not-accessible
		STATUS					 current
		DESCRIPTION			 " -- "
		::=  { tdsLocalcell  1 }


	tdsLocalCellEntry		 OBJECT-TYPE
		SYNTAX					 TdsLocalCellEntry
		MAX-ACCESS			 not-accessible
		STATUS					 current
		DESCRIPTION			 " -- "
		INDEX						{ tdsLcId }
		::=  { tdsLocalCellTable  1 }


	TdsLocalCellEntry		 ::=  SEQUENCE {
		tdsLcId					Integer32,
		tdsLcRowStatus					RowStatus,
		tdsLcCellId					Integer32,
		tdsLcCellParaId					Unsigned32,
		tdsLcCellExpectedCarrierNum					Unsigned32,
		tdsLcCellBlockSwitch					INTEGER,
		tdsLcCellBlockStatus					INTEGER,
		tdsLcCellOperationalState					INTEGER,
		tdsLcCellAvailbilityStatus					INTEGER,
		tdsLcCalibrationMode					INTEGER,
		tdsLcAntArrayMode					INTEGER,
		tdsLcMaxCarrierNum					Integer32,
		tdsLcMinCarrierNum					Integer32,
		tdsLcPriority					Integer32,
		tdsLcIsAntCombination					INTEGER,
		tdsLcMaxCombinationAntNum					Integer32,
		tdsLcLocalCellGrpId					Integer32,
		tdsLcAppScene					INTEGER,
		tdsLcPrimaryLocalCarrierIndex					Integer32,
		tdsLcAntennaCalibrationEnable					INTEGER,
		tdsLcAntennaCalibrationPeriod					Unsigned32,
		tdsLcCellExpectedCarrierNumA					Unsigned32,
		tdsLcPrimaryCarrierBand					INTEGER,
		tdsLcDownTimeSlotClosedNum					Unsigned32,
		tdsLcDownTimeSlotTotalNum					Unsigned32
		}


	tdsLcId		 OBJECT-TYPE
		SYNTAX					 Integer32( 0 .. 11 )
		MAX-ACCESS			 not-accessible
		STATUS					 current
		DESCRIPTION			 " -- "
		::=  { tdsLocalCellEntry  1 }


	tdsLcRowStatus		 OBJECT-TYPE
		SYNTAX					 RowStatus
		MAX-ACCESS			 read-only
		STATUS					 current
		DESCRIPTION			 " -- "
		::=  { tdsLocalCellEntry  2 }


	tdsLcCellId		 OBJECT-TYPE
		SYNTAX					 Integer32( 0 .. 65535 )
		MAX-ACCESS			 read-only
		STATUS					 current
		DESCRIPTION			 " -- "
		::=  { tdsLocalCellEntry  3 }


	tdsLcCellParaId		 OBJECT-TYPE
		SYNTAX					 Unsigned32( 0 .. 4294967295 )
		MAX-ACCESS			 read-only
		STATUS					 current
		DESCRIPTION			 " -- "
		::=  { tdsLocalCellEntry  4 }


	tdsLcCellExpectedCarrierNum		 OBJECT-TYPE
		SYNTAX					 Unsigned32( 0|1 .. 65535 )
		MAX-ACCESS			 read-only
		STATUS					 current
		DESCRIPTION			 " -- "
		::=  { tdsLocalCellEntry  5 }


	tdsLcCellBlockSwitch		 OBJECT-TYPE
		SYNTAX					 INTEGER{ off(0),unblock(1),blockHigh(2),blockNormal(3),blockLow(4)  }
		MAX-ACCESS			 read-write
		STATUS					 current
		DESCRIPTION			 " -- "
		::=  { tdsLocalCellEntry  6 }


	tdsLcCellBlockStatus		 OBJECT-TYPE
		SYNTAX					 INTEGER{ unblocked(0),blocking(1),blocked(2)  }
		MAX-ACCESS			 read-only
		STATUS					 current
		DESCRIPTION			 " -- "
		::=  { tdsLocalCellEntry  7 }


	tdsLcCellOperationalState		 OBJECT-TYPE
		SYNTAX					 INTEGER{ enabled(0),disabled(1),invalid(2)  }
		MAX-ACCESS			 read-only
		STATUS					 current
		DESCRIPTION			 " -- "
		::=  { tdsLocalCellEntry  8 }


	tdsLcCellAvailbilityStatus		 OBJECT-TYPE
		SYNTAX					 INTEGER{ empty(0),intest(1),failed(2),powerOff(3),offline(4),offDuty(5),dependency(6),degraded(7),notInstalled(8),logFull(9)  }
		MAX-ACCESS			 read-only
		STATUS					 current
		DESCRIPTION			 " -- "
		::=  { tdsLocalCellEntry  9 }


	tdsLcCalibrationMode		 OBJECT-TYPE
		SYNTAX					 INTEGER{ unknown(-1),temperatureCompensation(0),outputPowerDetection(1)  }
		MAX-ACCESS			 read-write
		STATUS					 current
		DESCRIPTION			 " -- "
		::=  { tdsLocalCellEntry  10 }


	tdsLcAntArrayMode		 OBJECT-TYPE
		SYNTAX					 INTEGER{ unknown(0),singleAnt(1),disAnt(2),smartAnt(3),ambipolarAnt(4),disSmartAnt(5),disAmbipolarAnt(6),smartPolarAnt(7),disSmartPolarAnt(8),mixAnt(9)  }
		MAX-ACCESS			 read-only
		STATUS					 current
		DESCRIPTION			 " -- "
		::=  { tdsLocalCellEntry  11 }


	tdsLcMaxCarrierNum		 OBJECT-TYPE
		SYNTAX					 Integer32( 1 .. 21|0 )
		MAX-ACCESS			 read-only
		STATUS					 current
		DESCRIPTION			 " -- "
		::=  { tdsLocalCellEntry  12 }


	tdsLcMinCarrierNum		 OBJECT-TYPE
		SYNTAX					 Integer32( 1 .. 21|0 )
		MAX-ACCESS			 read-only
		STATUS					 current
		DESCRIPTION			 " -- "
		::=  { tdsLocalCellEntry  13 }


	tdsLcPriority		 OBJECT-TYPE
		SYNTAX					 Integer32( 0 .. 11 )
		MAX-ACCESS			 read-only
		STATUS					 current
		DESCRIPTION			 " -- "
		::=  { tdsLocalCellEntry  14 }


	tdsLcIsAntCombination		 OBJECT-TYPE
		SYNTAX					 INTEGER{ false(0),antCombinationBetweenRRS(1),antCombinationInRRS(2),antCompleteCombination(3),antOptionalCombination(4)  }
		MAX-ACCESS			 read-only
		STATUS					 current
		DESCRIPTION			 " -- "
		::=  { tdsLocalCellEntry  15 }


	tdsLcMaxCombinationAntNum		 OBJECT-TYPE
		SYNTAX					 Integer32( 0 .. 8 )
		MAX-ACCESS			 read-only
		STATUS					 current
		DESCRIPTION			 " -- "
		::=  { tdsLocalCellEntry  16 }


	tdsLcLocalCellGrpId		 OBJECT-TYPE
		SYNTAX					 Integer32( 0|1 .. 11 )
		MAX-ACCESS			 read-only
		STATUS					 current
		DESCRIPTION			 " -- "
		::=  { tdsLocalCellEntry  17 }


	tdsLcAppScene		 OBJECT-TYPE
		SYNTAX					 INTEGER{ normal(0),largeScope(1),underground(2)  }
		MAX-ACCESS			 read-only
		STATUS					 current
		DESCRIPTION			 " -- "
		::=  { tdsLocalCellEntry  18 }


	tdsLcPrimaryLocalCarrierIndex		 OBJECT-TYPE
		SYNTAX					 Integer32( -1|0 .. 20 )
		MAX-ACCESS			 read-only
		STATUS					 current
		DESCRIPTION			 " -- "
		::=  { tdsLocalCellEntry  19 }


	tdsLcAntennaCalibrationEnable		 OBJECT-TYPE
		SYNTAX					 INTEGER{ enable(0),disable(1)  }
		MAX-ACCESS			 read-write
		STATUS					 current
		DESCRIPTION			 " -- "
		::=  { tdsLocalCellEntry  20 }


	tdsLcAntennaCalibrationPeriod		 OBJECT-TYPE
		SYNTAX					 Unsigned32( 15 .. 65535 )
		MAX-ACCESS			 read-write
		STATUS					 current
		DESCRIPTION			 " -- "
		::=  { tdsLocalCellEntry  21 }


	tdsLcCellExpectedCarrierNumA		 OBJECT-TYPE
		SYNTAX					 Unsigned32( 0|1 .. 65535 )
		MAX-ACCESS			 read-only
		STATUS					 current
		DESCRIPTION			 " -- "
		::=  { tdsLocalCellEntry  22 }


	tdsLcPrimaryCarrierBand		 OBJECT-TYPE
		SYNTAX					 INTEGER{ unknown(-1),v1880to1920(0),v2010to2025(1),v2300to2400(2)  }
		MAX-ACCESS			 read-only
		STATUS					 current
		DESCRIPTION			 " -- "
		::=  { tdsLocalCellEntry  23 }


	tdsLcDownTimeSlotClosedNum		 OBJECT-TYPE
		SYNTAX					 Unsigned32( 0 .. 4294967295 )
		MAX-ACCESS			 read-only
		STATUS					 current
		DESCRIPTION			 " -- "
		::=  { tdsLocalCellEntry  24 }


	tdsLcDownTimeSlotTotalNum		 OBJECT-TYPE
		SYNTAX					 Unsigned32( 0 .. 4294967295 )
		MAX-ACCESS			 read-only
		STATUS					 current
		DESCRIPTION			 " -- "
		::=  { tdsLocalCellEntry  25 }


	localCellConfigTable		 OBJECT-TYPE
		SYNTAX					 SEQUENCE  OF	 LocalCellConfigEntry
		MAX-ACCESS			 not-accessible
		STATUS					 current
		DESCRIPTION			 " -- "
		::=  { tdsLocalcell  2 }


	localCellConfigEntry		 OBJECT-TYPE
		SYNTAX					 LocalCellConfigEntry
		MAX-ACCESS			 not-accessible
		STATUS					 current
		DESCRIPTION			 " -- "
		INDEX						{ lcConfigLcId }
		::=  { localCellConfigTable  1 }


	LocalCellConfigEntry		 ::=  SEQUENCE {
		lcConfigLcId					Integer32,
		lcConfigRowStatus					RowStatus,
		tdsLcConfigTrigger					INTEGER,
		lcConfigCellBlockTime					Integer32,
		lcConfigRefClockAvail					INTEGER,
		lcConfigMaxDlPower					Integer32,
		lcConfigMinDlPower					Integer32,
		lcConfigCellPerfReportSwitch					INTEGER,
		lcConfigEts0Switch					INTEGER
		}


	lcConfigLcId		 OBJECT-TYPE
		SYNTAX					 Integer32( 0 .. 11 )
		MAX-ACCESS			 not-accessible
		STATUS					 current
		DESCRIPTION			 " -- "
		::=  { localCellConfigEntry  1 }


	lcConfigRowStatus		 OBJECT-TYPE
		SYNTAX					 RowStatus
		MAX-ACCESS			 read-only
		STATUS					 current
		DESCRIPTION			 " -- "
		::=  { localCellConfigEntry  2 }


	tdsLcConfigTrigger		 OBJECT-TYPE
		SYNTAX					 INTEGER{ add(0),delete(1),reconfig(2)  }
		MAX-ACCESS			 read-write
		STATUS					 current
		DESCRIPTION			 " -- "
		::=  { localCellConfigEntry  3 }


	lcConfigCellBlockTime		 OBJECT-TYPE
		SYNTAX					 Integer32( 1 .. 3600 )
		MAX-ACCESS			 read-write
		STATUS					 current
		DESCRIPTION			 " -- "
		::=  { localCellConfigEntry  4 }


	lcConfigRefClockAvail		 OBJECT-TYPE
		SYNTAX					 INTEGER{ available(0),unavailable(1)  }
		MAX-ACCESS			 read-write
		STATUS					 current
		DESCRIPTION			 " -- "
		::=  { localCellConfigEntry  5 }


	lcConfigMaxDlPower		 OBJECT-TYPE
		SYNTAX					 Integer32( 0 .. 500 )
		MAX-ACCESS			 read-only
		STATUS					 current
		DESCRIPTION			 " -- "
		::=  { localCellConfigEntry  6 }


	lcConfigMinDlPower		 OBJECT-TYPE
		SYNTAX					 Integer32( 0 .. 800 )
		MAX-ACCESS			 read-only
		STATUS					 current
		DESCRIPTION			 " -- "
		::=  { localCellConfigEntry  7 }


	lcConfigCellPerfReportSwitch		 OBJECT-TYPE
		SYNTAX					 INTEGER{ off(0),on(1)  }
		MAX-ACCESS			 read-write
		STATUS					 current
		DESCRIPTION			 " -- "
		::=  { localCellConfigEntry  8 }


	lcConfigEts0Switch		 OBJECT-TYPE
		SYNTAX					 INTEGER{ off(0),on(1)  }
		MAX-ACCESS			 read-write
		STATUS					 current
		DESCRIPTION			 " -- "
		::=  { localCellConfigEntry  9 }


	localCellGrpTable		 OBJECT-TYPE
		SYNTAX					 SEQUENCE  OF	 LocalCellGrpEntry
		MAX-ACCESS			 not-accessible
		STATUS					 current
		DESCRIPTION			 " -- "
		::=  { tdsLocalcell  3 }


	localCellGrpEntry		 OBJECT-TYPE
		SYNTAX					 LocalCellGrpEntry
		MAX-ACCESS			 not-accessible
		STATUS					 current
		DESCRIPTION			 " -- "
		INDEX						{ lcGrpId }
		::=  { localCellGrpTable  1 }


	LocalCellGrpEntry		 ::=  SEQUENCE {
		lcGrpId					Integer32,
		lcGrpRowStatus					RowStatus,
		lcGrpCarrierNum					Integer32,
		lcGrpPlanCarrierNum					Integer32
		}


	lcGrpId		 OBJECT-TYPE
		SYNTAX					 Integer32( 1 .. 11 )
		MAX-ACCESS			 not-accessible
		STATUS					 current
		DESCRIPTION			 " -- "
		::=  { localCellGrpEntry  1 }


	lcGrpRowStatus		 OBJECT-TYPE
		SYNTAX					 RowStatus
		MAX-ACCESS			 read-only
		STATUS					 current
		DESCRIPTION			 " -- "
		::=  { localCellGrpEntry  2 }


	lcGrpCarrierNum		 OBJECT-TYPE
		SYNTAX					 Integer32( 0 .. 72 )
		MAX-ACCESS			 read-only
		STATUS					 current
		DESCRIPTION			 " -- "
		::=  { localCellGrpEntry  3 }


	lcGrpPlanCarrierNum		 OBJECT-TYPE
		SYNTAX					 Integer32( 0 .. 72 )
		MAX-ACCESS			 read-only
		STATUS					 current
		DESCRIPTION			 " -- "
		::=  { localCellGrpEntry  4 }


	localCarrierTable		 OBJECT-TYPE
		SYNTAX					 SEQUENCE  OF	 LocalCarrierEntry
		MAX-ACCESS			 not-accessible
		STATUS					 current
		DESCRIPTION			 " -- "
		::=  { tdsLocalcell  4 }


	localCarrierEntry		 OBJECT-TYPE
		SYNTAX					 LocalCarrierEntry
		MAX-ACCESS			 not-accessible
		STATUS					 current
		DESCRIPTION			 " -- "
		INDEX						{ localCarrierLocalCellId,localCarrierIndex }
		::=  { localCarrierTable  1 }


	LocalCarrierEntry		 ::=  SEQUENCE {
		localCarrierLocalCellId					Integer32,
		localCarrierIndex					Integer32,
		localCarrierRowStatus					RowStatus,
		localCarrierPrimarySecondery					INTEGER,
		localCarrierFreqValue					Unsigned32,
		localCarrierCarrierOperationalState					INTEGER,
		localCarrierCarrierAvailbilityStatus					INTEGER,
		localCarrierStatusCheckTrigger					INTEGER,
		localCarrierAckedUsrDataVolume					Unsigned32,
		localCarrierTTINum					Unsigned32,
		localCarrierUsrBufferNum					Unsigned32,
		localCarrierRxACKNum					Unsigned32,
		localCarrierRxNACKNum					Unsigned32,
		localCarrierDiscardHsFrameNum					Unsigned32,
		localCarrierPdschPowerMinRate					Integer32,
		localCarrierScchPowerMinRate					Integer32,
		localCarrierInterfaceBaseBandCarrierNo					Integer32,
		localCarrierFirstRxACKNum					Unsigned32,
		localCarrierFirstRxNACKNum					Unsigned32,
		localCarrierSyncUlConflicts					Unsigned32,
		localCarrierSyncUlDiscards					Unsigned32,
		localCarrierFpachResps					Unsigned32,
		localCarrierHsdpaUsedBRUNum					Unsigned32,
		localCarrierHsupaUsedBRUNum					Unsigned32,
		localCarrierhsdpaTfrcMode					INTEGER,
		localCarrierhsupaTfrcMode					INTEGER,
		localCarrierOKRachs					Unsigned32,
		localCarrierFachs					Unsigned32,
		localCarrierPchs					Unsigned32,
		localCarrierERRRachs					Unsigned32,
		localCarrierCurrentUpptsPosition					Unsigned32,
		localCarrierNbrMacePdu					Unsigned32,
		localCarrierNbrAckMacePdu					Unsigned32,
		localCarrierNbrAckMaceOcts					Unsigned32,
		localCarrierhsdpaCtrlSDMACapability					INTEGER,
		localCarrierhsupaCtrlSDMACapability					INTEGER,
		localCarrierFpToDdRachs					Unsigned32,
		localCarrierFpFromDdRachs					Unsigned32,
		localCarrierFpToDdFachs					Unsigned32,
		localCarrierFpFromDdFachs					Unsigned32,
		localCarrierFpToDdPchs					Unsigned32,
		localCarrierFpFromDdPchs					Unsigned32,
		localCarrierApeSwitch					INTEGER
		}


	localCarrierLocalCellId		 OBJECT-TYPE
		SYNTAX					 Integer32( 0 .. 11 )
		MAX-ACCESS			 not-accessible
		STATUS					 current
		DESCRIPTION			 " -- "
		::=  { localCarrierEntry  1 }


	localCarrierIndex		 OBJECT-TYPE
		SYNTAX					 Integer32( 0 .. 20 )
		MAX-ACCESS			 not-accessible
		STATUS					 current
		DESCRIPTION			 " -- "
		::=  { localCarrierEntry  2 }


	localCarrierRowStatus		 OBJECT-TYPE
		SYNTAX					 RowStatus
		MAX-ACCESS			 read-only
		STATUS					 current
		DESCRIPTION			 " -- "
		::=  { localCarrierEntry  3 }


	localCarrierPrimarySecondery		 OBJECT-TYPE
		SYNTAX					 INTEGER{ undetermined(-1),primary(0),secondery(1)  }
		MAX-ACCESS			 read-only
		STATUS					 current
		DESCRIPTION			 " -- "
		::=  { localCarrierEntry  4 }


	localCarrierFreqValue		 OBJECT-TYPE
		SYNTAX					 Unsigned32( 0|1 .. 65535 )
		MAX-ACCESS			 read-only
		STATUS					 current
		DESCRIPTION			 " -- "
		::=  { localCarrierEntry  5 }


	localCarrierCarrierOperationalState		 OBJECT-TYPE
		SYNTAX					 INTEGER{ enabled(0),disabled(1),invalid(2)  }
		MAX-ACCESS			 read-only
		STATUS					 current
		DESCRIPTION			 " -- "
		::=  { localCarrierEntry  6 }


	localCarrierCarrierAvailbilityStatus		 OBJECT-TYPE
		SYNTAX					 INTEGER{ empty(0),intest(1),failed(2),powerOff(3),offline(4),offDuty(5),dependency(6),degraded(7),notInstalled(8),logFull(9)  }
		MAX-ACCESS			 read-only
		STATUS					 current
		DESCRIPTION			 " -- "
		::=  { localCarrierEntry  7 }


	localCarrierStatusCheckTrigger		 OBJECT-TYPE
		SYNTAX					 INTEGER{ off(0),on(1)  }
		MAX-ACCESS			 read-write
		STATUS					 current
		DESCRIPTION			 " -- "
		::=  { localCarrierEntry  8 }


	localCarrierAckedUsrDataVolume		 OBJECT-TYPE
		SYNTAX					 Unsigned32( 0 .. 4294967295 )
		MAX-ACCESS			 read-only
		STATUS					 current
		DESCRIPTION			 " -- "
		::=  { localCarrierEntry  9 }


	localCarrierTTINum		 OBJECT-TYPE
		SYNTAX					 Unsigned32( 0 .. 4294967295 )
		MAX-ACCESS			 read-only
		STATUS					 current
		DESCRIPTION			 " -- "
		::=  { localCarrierEntry  10 }


	localCarrierUsrBufferNum		 OBJECT-TYPE
		SYNTAX					 Unsigned32( 0 .. 4294967295 )
		MAX-ACCESS			 read-only
		STATUS					 current
		DESCRIPTION			 " -- "
		::=  { localCarrierEntry  11 }


	localCarrierRxACKNum		 OBJECT-TYPE
		SYNTAX					 Unsigned32( 0 .. 4294967295 )
		MAX-ACCESS			 read-only
		STATUS					 current
		DESCRIPTION			 " -- "
		::=  { localCarrierEntry  12 }


	localCarrierRxNACKNum		 OBJECT-TYPE
		SYNTAX					 Unsigned32( 0 .. 4294967295 )
		MAX-ACCESS			 read-only
		STATUS					 current
		DESCRIPTION			 " -- "
		::=  { localCarrierEntry  13 }


	localCarrierDiscardHsFrameNum		 OBJECT-TYPE
		SYNTAX					 Unsigned32( 0 .. 4294967295 )
		MAX-ACCESS			 read-only
		STATUS					 current
		DESCRIPTION			 " -- "
		::=  { localCarrierEntry  14 }


	localCarrierPdschPowerMinRate		 OBJECT-TYPE
		SYNTAX					 Integer32( 0 .. 1000 )
		MAX-ACCESS			 read-write
		STATUS					 current
		DESCRIPTION			 " -- "
		::=  { localCarrierEntry  15 }


	localCarrierScchPowerMinRate		 OBJECT-TYPE
		SYNTAX					 Integer32( 0 .. 1000 )
		MAX-ACCESS			 read-write
		STATUS					 current
		DESCRIPTION			 " -- "
		::=  { localCarrierEntry  16 }


	localCarrierInterfaceBaseBandCarrierNo		 OBJECT-TYPE
		SYNTAX					 Integer32( -1|18 .. 143 )
		MAX-ACCESS			 read-only
		STATUS					 current
		DESCRIPTION			 " -- "
		::=  { localCarrierEntry  17 }


	localCarrierFirstRxACKNum		 OBJECT-TYPE
		SYNTAX					 Unsigned32( 0 .. 4294967295 )
		MAX-ACCESS			 read-only
		STATUS					 current
		DESCRIPTION			 " -- "
		::=  { localCarrierEntry  18 }


	localCarrierFirstRxNACKNum		 OBJECT-TYPE
		SYNTAX					 Unsigned32( 0 .. 4294967295 )
		MAX-ACCESS			 read-only
		STATUS					 current
		DESCRIPTION			 " -- "
		::=  { localCarrierEntry  19 }


	localCarrierSyncUlConflicts		 OBJECT-TYPE
		SYNTAX					 Unsigned32( 0 .. 4294967295 )
		MAX-ACCESS			 read-only
		STATUS					 current
		DESCRIPTION			 " -- "
		::=  { localCarrierEntry  20 }


	localCarrierSyncUlDiscards		 OBJECT-TYPE
		SYNTAX					 Unsigned32( 0 .. 4294967295 )
		MAX-ACCESS			 read-only
		STATUS					 current
		DESCRIPTION			 " -- "
		::=  { localCarrierEntry  21 }


	localCarrierFpachResps		 OBJECT-TYPE
		SYNTAX					 Unsigned32( 0 .. 4294967295 )
		MAX-ACCESS			 read-only
		STATUS					 current
		DESCRIPTION			 " -- "
		::=  { localCarrierEntry  22 }


	localCarrierHsdpaUsedBRUNum		 OBJECT-TYPE
		SYNTAX					 Unsigned32( 0 .. 4294967295 )
		MAX-ACCESS			 read-only
		STATUS					 current
		DESCRIPTION			 " -- "
		::=  { localCarrierEntry  23 }


	localCarrierHsupaUsedBRUNum		 OBJECT-TYPE
		SYNTAX					 Unsigned32( 0 .. 4294967295 )
		MAX-ACCESS			 read-only
		STATUS					 current
		DESCRIPTION			 " -- "
		::=  { localCarrierEntry  24 }


	localCarrierhsdpaTfrcMode		 OBJECT-TYPE
		SYNTAX					 INTEGER{ invalid(-1),tdcdPartialTd(0),tdcdPartialCd(1),pureTd(2),allTd(3),sd(4)  }
		MAX-ACCESS			 read-only
		STATUS					 current
		DESCRIPTION			 " -- "
		::=  { localCarrierEntry  25 }


	localCarrierhsupaTfrcMode		 OBJECT-TYPE
		SYNTAX					 INTEGER{ invalid(-1),pureTd(0),pureCd(1),tdcd(2),sd(3)  }
		MAX-ACCESS			 read-only
		STATUS					 current
		DESCRIPTION			 " -- "
		::=  { localCarrierEntry  26 }


	localCarrierOKRachs		 OBJECT-TYPE
		SYNTAX					 Unsigned32( 0 .. 4294967295 )
		MAX-ACCESS			 read-only
		STATUS					 current
		DESCRIPTION			 " -- "
		::=  { localCarrierEntry  27 }


	localCarrierFachs		 OBJECT-TYPE
		SYNTAX					 Unsigned32( 0 .. 4294967295 )
		MAX-ACCESS			 read-only
		STATUS					 current
		DESCRIPTION			 " -- "
		::=  { localCarrierEntry  28 }


	localCarrierPchs		 OBJECT-TYPE
		SYNTAX					 Unsigned32( 0 .. 4294967295 )
		MAX-ACCESS			 read-only
		STATUS					 current
		DESCRIPTION			 " -- "
		::=  { localCarrierEntry  29 }


	localCarrierERRRachs		 OBJECT-TYPE
		SYNTAX					 Unsigned32( 0 .. 4294967295 )
		MAX-ACCESS			 read-only
		STATUS					 current
		DESCRIPTION			 " -- "
		::=  { localCarrierEntry  30 }


	localCarrierCurrentUpptsPosition		 OBJECT-TYPE
		SYNTAX					 Unsigned32( 0 .. 4294967295 )
		MAX-ACCESS			 read-only
		STATUS					 current
		DESCRIPTION			 " -- "
		::=  { localCarrierEntry  31 }


	localCarrierNbrMacePdu		 OBJECT-TYPE
		SYNTAX					 Unsigned32( 0 .. 4294967295 )
		MAX-ACCESS			 read-only
		STATUS					 current
		DESCRIPTION			 " -- "
		::=  { localCarrierEntry  32 }


	localCarrierNbrAckMacePdu		 OBJECT-TYPE
		SYNTAX					 Unsigned32( 0 .. 4294967295 )
		MAX-ACCESS			 read-only
		STATUS					 current
		DESCRIPTION			 " -- "
		::=  { localCarrierEntry  33 }


	localCarrierNbrAckMaceOcts		 OBJECT-TYPE
		SYNTAX					 Unsigned32( 0 .. 4294967295 )
		MAX-ACCESS			 read-only
		STATUS					 current
		DESCRIPTION			 " -- "
		::=  { localCarrierEntry  34 }


	localCarrierhsdpaCtrlSDMACapability		 OBJECT-TYPE
		SYNTAX					 INTEGER{ notsdma(0),sdma(64)  }
		MAX-ACCESS			 read-only
		STATUS					 current
		DESCRIPTION			 " -- "
		::=  { localCarrierEntry  35 }


	localCarrierhsupaCtrlSDMACapability		 OBJECT-TYPE
		SYNTAX					 INTEGER{ notsdma(0),sdma(64)  }
		MAX-ACCESS			 read-only
		STATUS					 current
		DESCRIPTION			 " -- "
		::=  { localCarrierEntry  36 }


	localCarrierFpToDdRachs		 OBJECT-TYPE
		SYNTAX					 Unsigned32( 0 .. 4294967295 )
		MAX-ACCESS			 read-only
		STATUS					 current
		DESCRIPTION			 " -- "
		::=  { localCarrierEntry  37 }


	localCarrierFpFromDdRachs		 OBJECT-TYPE
		SYNTAX					 Unsigned32( 0 .. 4294967295 )
		MAX-ACCESS			 read-only
		STATUS					 current
		DESCRIPTION			 " -- "
		::=  { localCarrierEntry  38 }


	localCarrierFpToDdFachs		 OBJECT-TYPE
		SYNTAX					 Unsigned32( 0 .. 4294967295 )
		MAX-ACCESS			 read-only
		STATUS					 current
		DESCRIPTION			 " -- "
		::=  { localCarrierEntry  39 }


	localCarrierFpFromDdFachs		 OBJECT-TYPE
		SYNTAX					 Unsigned32( 0 .. 4294967295 )
		MAX-ACCESS			 read-only
		STATUS					 current
		DESCRIPTION			 " -- "
		::=  { localCarrierEntry  40 }


	localCarrierFpToDdPchs		 OBJECT-TYPE
		SYNTAX					 Unsigned32( 0 .. 4294967295 )
		MAX-ACCESS			 read-only
		STATUS					 current
		DESCRIPTION			 " -- "
		::=  { localCarrierEntry  41 }


	localCarrierFpFromDdPchs		 OBJECT-TYPE
		SYNTAX					 Unsigned32( 0 .. 4294967295 )
		MAX-ACCESS			 read-only
		STATUS					 current
		DESCRIPTION			 " -- "
		::=  { localCarrierEntry  42 }


	localCarrierApeSwitch		 OBJECT-TYPE
		SYNTAX					 INTEGER{ off(0),on(1)  }
		MAX-ACCESS			 read-only
		STATUS					 current
		DESCRIPTION			 " -- "
		::=  { localCarrierEntry  43 }


	baseBandCarrierTable		 OBJECT-TYPE
		SYNTAX					 SEQUENCE  OF	 BaseBandCarrierEntry
		MAX-ACCESS			 not-accessible
		STATUS					 current
		DESCRIPTION			 " -- "
		::=  { tdsLocalcell  5 }


	baseBandCarrierEntry		 OBJECT-TYPE
		SYNTAX					 BaseBandCarrierEntry
		MAX-ACCESS			 not-accessible
		STATUS					 current
		DESCRIPTION			 " -- "
		INDEX						{ baseBandCarrierNo }
		::=  { baseBandCarrierTable  1 }


	BaseBandCarrierEntry		 ::=  SEQUENCE {
		baseBandCarrierNo					Integer32,
		baseBandCarrierRowStatus					RowStatus,
		baseBandCarrierFrameNo					Integer32,
		baseBandCarrierSlotNo					Integer32,
		baseBandCarrierIndexOnBBU					Integer32,
		baseBandCarrierEngagedState					INTEGER,
		baseBandCarrierLocalCellId					Integer32,
		baseBandCarrierLocalCarrierIndex					Integer32,
		baseBandCarrierIsInterface					INTEGER,
		baseBandCarrierlcGrpId					Integer32,
		baseBandCarrierAntCalTrigger					INTEGER,
		baseBandCarrierAntCalType					INTEGER,
		baseBandCarrierTxPath1CalFactorI					Integer32,
		baseBandCarrierTxPath1CalFactorQ					Integer32,
		baseBandCarrierTxPath2CalFactorI					Integer32,
		baseBandCarrierTxPath2CalFactorQ					Integer32,
		baseBandCarrierTxPath3CalFactorI					Integer32,
		baseBandCarrierTxPath3CalFactorQ					Integer32,
		baseBandCarrierTxPath4CalFactorI					Integer32,
		baseBandCarrierTxPath4CalFactorQ					Integer32,
		baseBandCarrierTxPath5CalFactorI					Integer32,
		baseBandCarrierTxPath5CalFactorQ					Integer32,
		baseBandCarrierTxPath6CalFactorI					Integer32,
		baseBandCarrierTxPath6CalFactorQ					Integer32,
		baseBandCarrierTxPath7CalFactorI					Integer32,
		baseBandCarrierTxPath7CalFactorQ					Integer32,
		baseBandCarrierTxPath8CalFactorI					Integer32,
		baseBandCarrierTxPath8CalFactorQ					Integer32,
		baseBandCarrierRadioPathTxStatus					Integer32,
		baseBandCarrierRadioPathRxStatus					Integer32,
		baseBandCarrierMaxDlPower					Integer32,
		baseBandCarrierGpIscp					DisplayString,
		baseBandCarrierDwPccpchInfo					DisplayString
		}


	baseBandCarrierNo		 OBJECT-TYPE
		SYNTAX					 Integer32( 18 .. 143 )
		MAX-ACCESS			 not-accessible
		STATUS					 current
		DESCRIPTION			 " -- "
		::=  { baseBandCarrierEntry  1 }


	baseBandCarrierRowStatus		 OBJECT-TYPE
		SYNTAX					 RowStatus
		MAX-ACCESS			 read-only
		STATUS					 current
		DESCRIPTION			 " -- "
		::=  { baseBandCarrierEntry  2 }


	baseBandCarrierFrameNo		 OBJECT-TYPE
		SYNTAX					 Integer32( -1|0 .. 0 )
		MAX-ACCESS			 read-only
		STATUS					 current
		DESCRIPTION			 " -- "
		::=  { baseBandCarrierEntry  3 }


	baseBandCarrierSlotNo		 OBJECT-TYPE
		SYNTAX					 Integer32( -1|1 .. 7 )
		MAX-ACCESS			 read-only
		STATUS					 current
		DESCRIPTION			 " -- "
		::=  { baseBandCarrierEntry  4 }


	baseBandCarrierIndexOnBBU		 OBJECT-TYPE
		SYNTAX					 Integer32( -1|0 .. 17 )
		MAX-ACCESS			 read-only
		STATUS					 current
		DESCRIPTION			 " -- "
		::=  { baseBandCarrierEntry  5 }


	baseBandCarrierEngagedState		 OBJECT-TYPE
		SYNTAX					 INTEGER{ free(0),preengage(1),engaging(2),engaged(3)  }
		MAX-ACCESS			 read-write
		STATUS					 current
		DESCRIPTION			 " -- "
		::=  { baseBandCarrierEntry  6 }


	baseBandCarrierLocalCellId		 OBJECT-TYPE
		SYNTAX					 Integer32( -1|0 .. 11 )
		MAX-ACCESS			 read-write
		STATUS					 current
		DESCRIPTION			 " -- "
		::=  { baseBandCarrierEntry  7 }


	baseBandCarrierLocalCarrierIndex		 OBJECT-TYPE
		SYNTAX					 Integer32( -1|0 .. 20 )
		MAX-ACCESS			 read-only
		STATUS					 current
		DESCRIPTION			 " -- "
		::=  { baseBandCarrierEntry  8 }


	baseBandCarrierIsInterface		 OBJECT-TYPE
		SYNTAX					 INTEGER{ unknown(-1),false(0),true(1)  }
		MAX-ACCESS			 read-only
		STATUS					 current
		DESCRIPTION			 " -- "
		::=  { baseBandCarrierEntry  9 }


	baseBandCarrierlcGrpId		 OBJECT-TYPE
		SYNTAX					 Integer32( 0|1 .. 11 )
		MAX-ACCESS			 read-only
		STATUS					 current
		DESCRIPTION			 " -- "
		::=  { baseBandCarrierEntry  10 }


	baseBandCarrierAntCalTrigger		 OBJECT-TYPE
		SYNTAX					 INTEGER{ txPath(0),rxPath(1),rtxPath(2)  }
		MAX-ACCESS			 read-write
		STATUS					 current
		DESCRIPTION			 " -- "
		::=  { baseBandCarrierEntry  11 }


	baseBandCarrierAntCalType		 OBJECT-TYPE
		SYNTAX					 INTEGER{ txPath(0),rxPath(1),rtxPath(2)  }
		MAX-ACCESS			 read-write
		STATUS					 current
		DESCRIPTION			 " -- "
		::=  { baseBandCarrierEntry  12 }


	baseBandCarrierTxPath1CalFactorI		 OBJECT-TYPE
		SYNTAX					 Integer32( -1|0 .. 65535 )
		MAX-ACCESS			 read-only
		STATUS					 current
		DESCRIPTION			 " -- "
		::=  { baseBandCarrierEntry  13 }


	baseBandCarrierTxPath1CalFactorQ		 OBJECT-TYPE
		SYNTAX					 Integer32( -1|0 .. 65535 )
		MAX-ACCESS			 read-only
		STATUS					 current
		DESCRIPTION			 " -- "
		::=  { baseBandCarrierEntry  14 }


	baseBandCarrierTxPath2CalFactorI		 OBJECT-TYPE
		SYNTAX					 Integer32( -1|0 .. 65535 )
		MAX-ACCESS			 read-only
		STATUS					 current
		DESCRIPTION			 " -- "
		::=  { baseBandCarrierEntry  15 }


	baseBandCarrierTxPath2CalFactorQ		 OBJECT-TYPE
		SYNTAX					 Integer32( -1|0 .. 65535 )
		MAX-ACCESS			 read-only
		STATUS					 current
		DESCRIPTION			 " -- "
		::=  { baseBandCarrierEntry  16 }


	baseBandCarrierTxPath3CalFactorI		 OBJECT-TYPE
		SYNTAX					 Integer32( -1|0 .. 65535 )
		MAX-ACCESS			 read-only
		STATUS					 current
		DESCRIPTION			 " -- "
		::=  { baseBandCarrierEntry  17 }


	baseBandCarrierTxPath3CalFactorQ		 OBJECT-TYPE
		SYNTAX					 Integer32( -1|0 .. 65535 )
		MAX-ACCESS			 read-only
		STATUS					 current
		DESCRIPTION			 " -- "
		::=  { baseBandCarrierEntry  18 }


	baseBandCarrierTxPath4CalFactorI		 OBJECT-TYPE
		SYNTAX					 Integer32( -1|0 .. 65535 )
		MAX-ACCESS			 read-only
		STATUS					 current
		DESCRIPTION			 " -- "
		::=  { baseBandCarrierEntry  19 }


	baseBandCarrierTxPath4CalFactorQ		 OBJECT-TYPE
		SYNTAX					 Integer32( -1|0 .. 65535 )
		MAX-ACCESS			 read-only
		STATUS					 current
		DESCRIPTION			 " -- "
		::=  { baseBandCarrierEntry  20 }


	baseBandCarrierTxPath5CalFactorI		 OBJECT-TYPE
		SYNTAX					 Integer32( -1|0 .. 65535 )
		MAX-ACCESS			 read-only
		STATUS					 current
		DESCRIPTION			 " -- "
		::=  { baseBandCarrierEntry  21 }


	baseBandCarrierTxPath5CalFactorQ		 OBJECT-TYPE
		SYNTAX					 Integer32( -1|0 .. 65535 )
		MAX-ACCESS			 read-only
		STATUS					 current
		DESCRIPTION			 " -- "
		::=  { baseBandCarrierEntry  22 }


	baseBandCarrierTxPath6CalFactorI		 OBJECT-TYPE
		SYNTAX					 Integer32( -1|0 .. 65535 )
		MAX-ACCESS			 read-only
		STATUS					 current
		DESCRIPTION			 " -- "
		::=  { baseBandCarrierEntry  23 }


	baseBandCarrierTxPath6CalFactorQ		 OBJECT-TYPE
		SYNTAX					 Integer32( -1|0 .. 65535 )
		MAX-ACCESS			 read-only
		STATUS					 current
		DESCRIPTION			 " -- "
		::=  { baseBandCarrierEntry  24 }


	baseBandCarrierTxPath7CalFactorI		 OBJECT-TYPE
		SYNTAX					 Integer32( -1|0 .. 65535 )
		MAX-ACCESS			 read-only
		STATUS					 current
		DESCRIPTION			 " -- "
		::=  { baseBandCarrierEntry  25 }


	baseBandCarrierTxPath7CalFactorQ		 OBJECT-TYPE
		SYNTAX					 Integer32( -1|0 .. 65535 )
		MAX-ACCESS			 read-only
		STATUS					 current
		DESCRIPTION			 " -- "
		::=  { baseBandCarrierEntry  26 }


	baseBandCarrierTxPath8CalFactorI		 OBJECT-TYPE
		SYNTAX					 Integer32( -1|0 .. 65535 )
		MAX-ACCESS			 read-only
		STATUS					 current
		DESCRIPTION			 " -- "
		::=  { baseBandCarrierEntry  27 }


	baseBandCarrierTxPath8CalFactorQ		 OBJECT-TYPE
		SYNTAX					 Integer32( -1|0 .. 65535 )
		MAX-ACCESS			 read-only
		STATUS					 current
		DESCRIPTION			 " -- "
		::=  { baseBandCarrierEntry  28 }


	baseBandCarrierRadioPathTxStatus		 OBJECT-TYPE
		SYNTAX					 Integer32( -2147483648 .. 2147483647 )
		MAX-ACCESS			 read-only
		STATUS					 current
		DESCRIPTION			 " -- "
		::=  { baseBandCarrierEntry  29 }


	baseBandCarrierRadioPathRxStatus		 OBJECT-TYPE
		SYNTAX					 Integer32( -2147483648 .. 2147483647 )
		MAX-ACCESS			 read-only
		STATUS					 current
		DESCRIPTION			 " -- "
		::=  { baseBandCarrierEntry  30 }


	baseBandCarrierMaxDlPower		 OBJECT-TYPE
		SYNTAX					 Integer32( 0 .. 500 )
		MAX-ACCESS			 read-only
		STATUS					 current
		DESCRIPTION			 " -- "
		::=  { baseBandCarrierEntry  31 }


	baseBandCarrierGpIscp		 OBJECT-TYPE
		SYNTAX					 DisplayString( SIZE ( 1 .. 255 ) )
		MAX-ACCESS			 read-only
		STATUS					 current
		DESCRIPTION			 " -- "
		::=  { baseBandCarrierEntry  32 }


	baseBandCarrierDwPccpchInfo		 OBJECT-TYPE
		SYNTAX					 DisplayString( SIZE ( 1 .. 255 ) )
		MAX-ACCESS			 read-only
		STATUS					 current
		DESCRIPTION			 " -- "
		::=  { baseBandCarrierEntry  37 }


	radioCarrierTable		 OBJECT-TYPE
		SYNTAX					 SEQUENCE  OF	 RadioCarrierEntry
		MAX-ACCESS			 not-accessible
		STATUS					 current
		DESCRIPTION			 " -- "
		::=  { tdsLocalcell  6 }


	radioCarrierEntry		 OBJECT-TYPE
		SYNTAX					 RadioCarrierEntry
		MAX-ACCESS			 not-accessible
		STATUS					 current
		DESCRIPTION			 " -- "
		INDEX						{ radioCarrierNo }
		::=  { radioCarrierTable  1 }


	RadioCarrierEntry		 ::=  SEQUENCE {
		radioCarrierNo					Integer32,
		radioCarrierRowStatus					RowStatus,
		radioCarrierIFUNo					Integer32,
		radioCarrierIFUPathNo					Integer32,
		radioCarrierIndexOnIFUPath					Integer32,
		radioCarrierEngagedState					INTEGER,
		radioCarrierBaseBandCarrierNo					Integer32,
		radioCarrierBand					INTEGER,
		radioCarrierCellStatus					INTEGER
		}


	radioCarrierNo		 OBJECT-TYPE
		SYNTAX					 Integer32( 36 .. 27683 )
		MAX-ACCESS			 not-accessible
		STATUS					 current
		DESCRIPTION			 " -- "
		::=  { radioCarrierEntry  1 }


	radioCarrierRowStatus		 OBJECT-TYPE
		SYNTAX					 RowStatus
		MAX-ACCESS			 read-only
		STATUS					 current
		DESCRIPTION			 " -- "
		::=  { radioCarrierEntry  2 }


	radioCarrierIFUNo		 OBJECT-TYPE
		SYNTAX					 Integer32( -1|0 .. 47 )
		MAX-ACCESS			 read-only
		STATUS					 current
		DESCRIPTION			 " -- "
		::=  { radioCarrierEntry  3 }


	radioCarrierIFUPathNo		 OBJECT-TYPE
		SYNTAX					 Integer32( -1|1 .. 16 )
		MAX-ACCESS			 read-only
		STATUS					 current
		DESCRIPTION			 " -- "
		::=  { radioCarrierEntry  4 }


	radioCarrierIndexOnIFUPath		 OBJECT-TYPE
		SYNTAX					 Integer32( -1|0 .. 35 )
		MAX-ACCESS			 read-only
		STATUS					 current
		DESCRIPTION			 " -- "
		::=  { radioCarrierEntry  5 }


	radioCarrierEngagedState		 OBJECT-TYPE
		SYNTAX					 INTEGER{ free(0),preengage(1),engaging(2),engaged(3)  }
		MAX-ACCESS			 read-only
		STATUS					 current
		DESCRIPTION			 " -- "
		::=  { radioCarrierEntry  6 }


	radioCarrierBaseBandCarrierNo		 OBJECT-TYPE
		SYNTAX					 Integer32( -1|18 .. 143 )
		MAX-ACCESS			 read-only
		STATUS					 current
		DESCRIPTION			 " -- "
		::=  { radioCarrierEntry  7 }


	radioCarrierBand		 OBJECT-TYPE
		SYNTAX					 INTEGER{ unknown(-1),v1880to1920(0),v2010to2025(1),v2300to2400(2)  }
		MAX-ACCESS			 read-only
		STATUS					 current
		DESCRIPTION			 " -- "
		::=  { radioCarrierEntry  8 }


	radioCarrierCellStatus		 OBJECT-TYPE
		SYNTAX					 INTEGER{ unknown(0),cellActiving(1),cellActived(2)  }
		MAX-ACCESS			 read-only
		STATUS					 current
		DESCRIPTION			 " -- "
		::=  { radioCarrierEntry  9 }


	carrierTimeSlotTable		 OBJECT-TYPE
		SYNTAX					 SEQUENCE  OF	 CarrierTimeSlotEntry
		MAX-ACCESS			 not-accessible
		STATUS					 current
		DESCRIPTION			 " -- "
		::=  { tdsLocalcell  7 }


	carrierTimeSlotEntry		 OBJECT-TYPE
		SYNTAX					 CarrierTimeSlotEntry
		MAX-ACCESS			 not-accessible
		STATUS					 current
		DESCRIPTION			 " -- "
		INDEX						{ carrierTsLocalCellId,carrierTsLocalCarrierIndex }
		::=  { carrierTimeSlotTable  1 }


	CarrierTimeSlotEntry		 ::=  SEQUENCE {
		carrierTsLocalCellId					Integer32,
		carrierTsLocalCarrierIndex					Integer32,
		carrierTsRowStatus					RowStatus,
		carrierTs1ISCP					Integer32,
		carrierTs2ISCP					Integer32,
		carrierTs3ISCP					Integer32,
		carrierTs4ISCP					Integer32,
		carrierTs1RxPower					Integer32,
		carrierTs2RxPower					Integer32,
		carrierTs3RxPower					Integer32,
		carrierTs4RxPower					Integer32,
		carrierTs1ISCPInfo					DisplayString,
		carrierTs2ISCPInfo					DisplayString,
		carrierTs3ISCPInfo					DisplayString,
		carrierTs4ISCPInfo					DisplayString,
		carrierUpTs1CofStatus					INTEGER,
		carrierUpTs2CofStatus					INTEGER,
		carrierUpTs3CofStatus					INTEGER,
		carrierUpTs4CofStatus					INTEGER
		}


	carrierTsLocalCellId		 OBJECT-TYPE
		SYNTAX					 Integer32( 0 .. 11 )
		MAX-ACCESS			 not-accessible
		STATUS					 current
		DESCRIPTION			 " -- "
		::=  { carrierTimeSlotEntry  1 }


	carrierTsLocalCarrierIndex		 OBJECT-TYPE
		SYNTAX					 Integer32( 0 .. 20 )
		MAX-ACCESS			 not-accessible
		STATUS					 current
		DESCRIPTION			 " -- "
		::=  { carrierTimeSlotEntry  2 }


	carrierTsRowStatus		 OBJECT-TYPE
		SYNTAX					 RowStatus
		MAX-ACCESS			 read-only
		STATUS					 current
		DESCRIPTION			 " -- "
		::=  { carrierTimeSlotEntry  3 }


	carrierTs1ISCP		 OBJECT-TYPE
		SYNTAX					 Integer32( -2147483648 .. 2147483647 )
		MAX-ACCESS			 read-only
		STATUS					 current
		DESCRIPTION			 " -- "
		::=  { carrierTimeSlotEntry  4 }


	carrierTs2ISCP		 OBJECT-TYPE
		SYNTAX					 Integer32( -2147483648 .. 2147483647 )
		MAX-ACCESS			 read-only
		STATUS					 current
		DESCRIPTION			 " -- "
		::=  { carrierTimeSlotEntry  5 }


	carrierTs3ISCP		 OBJECT-TYPE
		SYNTAX					 Integer32( -2147483648 .. 2147483647 )
		MAX-ACCESS			 read-only
		STATUS					 current
		DESCRIPTION			 " -- "
		::=  { carrierTimeSlotEntry  6 }


	carrierTs4ISCP		 OBJECT-TYPE
		SYNTAX					 Integer32( -2147483648 .. 2147483647 )
		MAX-ACCESS			 read-only
		STATUS					 current
		DESCRIPTION			 " -- "
		::=  { carrierTimeSlotEntry  7 }


	carrierTs1RxPower		 OBJECT-TYPE
		SYNTAX					 Integer32( -2147483648 .. 2147483647 )
		MAX-ACCESS			 read-only
		STATUS					 current
		DESCRIPTION			 " -- "
		::=  { carrierTimeSlotEntry  8 }


	carrierTs2RxPower		 OBJECT-TYPE
		SYNTAX					 Integer32( -2147483648 .. 2147483647 )
		MAX-ACCESS			 read-only
		STATUS					 current
		DESCRIPTION			 " -- "
		::=  { carrierTimeSlotEntry  9 }


	carrierTs3RxPower		 OBJECT-TYPE
		SYNTAX					 Integer32( -2147483648 .. 2147483647 )
		MAX-ACCESS			 read-only
		STATUS					 current
		DESCRIPTION			 " -- "
		::=  { carrierTimeSlotEntry  10 }


	carrierTs4RxPower		 OBJECT-TYPE
		SYNTAX					 Integer32( -2147483648 .. 2147483647 )
		MAX-ACCESS			 read-only
		STATUS					 current
		DESCRIPTION			 " -- "
		::=  { carrierTimeSlotEntry  11 }


	carrierTs1ISCPInfo		 OBJECT-TYPE
		SYNTAX					 DisplayString( SIZE ( 1 .. 255 ) )
		MAX-ACCESS			 read-only
		STATUS					 current
		DESCRIPTION			 " -- "
		::=  { carrierTimeSlotEntry  12 }


	carrierTs2ISCPInfo		 OBJECT-TYPE
		SYNTAX					 DisplayString( SIZE ( 1 .. 255 ) )
		MAX-ACCESS			 read-only
		STATUS					 current
		DESCRIPTION			 " -- "
		::=  { carrierTimeSlotEntry  13 }


	carrierTs3ISCPInfo		 OBJECT-TYPE
		SYNTAX					 DisplayString( SIZE ( 1 .. 255 ) )
		MAX-ACCESS			 read-only
		STATUS					 current
		DESCRIPTION			 " -- "
		::=  { carrierTimeSlotEntry  14 }


	carrierTs4ISCPInfo		 OBJECT-TYPE
		SYNTAX					 DisplayString( SIZE ( 1 .. 255 ) )
		MAX-ACCESS			 read-only
		STATUS					 current
		DESCRIPTION			 " -- "
		::=  { carrierTimeSlotEntry  15 }


	carrierUpTs1CofStatus		 OBJECT-TYPE
		SYNTAX					 INTEGER{ coFreqOffRnOff(0),coFreqOffRnOn(1),coFreqOnRnOff(2),coFreqOnRnOn(3),invalid(255)  }
		MAX-ACCESS			 read-only
		STATUS					 current
		DESCRIPTION			 " -- "
		::=  { carrierTimeSlotEntry  16 }


	carrierUpTs2CofStatus		 OBJECT-TYPE
		SYNTAX					 INTEGER{ coFreqOffRnOff(0),coFreqOffRnOn(1),coFreqOnRnOff(2),coFreqOnRnOn(3),invalid(255)  }
		MAX-ACCESS			 read-only
		STATUS					 current
		DESCRIPTION			 " -- "
		::=  { carrierTimeSlotEntry  17 }


	carrierUpTs3CofStatus		 OBJECT-TYPE
		SYNTAX					 INTEGER{ coFreqOffRnOff(0),coFreqOffRnOn(1),coFreqOnRnOff(2),coFreqOnRnOn(3),invalid(255)  }
		MAX-ACCESS			 read-only
		STATUS					 current
		DESCRIPTION			 " -- "
		::=  { carrierTimeSlotEntry  18 }


	carrierUpTs4CofStatus		 OBJECT-TYPE
		SYNTAX					 INTEGER{ coFreqOffRnOff(0),coFreqOffRnOn(1),coFreqOnRnOff(2),coFreqOnRnOn(3),invalid(255)  }
		MAX-ACCESS			 read-only
		STATUS					 current
		DESCRIPTION			 " -- "
		::=  { carrierTimeSlotEntry  19 }


	rruCarrierTable		 OBJECT-TYPE
		SYNTAX					 SEQUENCE  OF	 RruCarrierEntry
		MAX-ACCESS			 not-accessible
		STATUS					 current
		DESCRIPTION			 " -- "
		::=  { tdsLocalcell  8 }


	rruCarrierEntry		 OBJECT-TYPE
		SYNTAX					 RruCarrierEntry
		MAX-ACCESS			 not-accessible
		STATUS					 current
		DESCRIPTION			 " -- "
		INDEX						{ rruCarrierRRSNo,rruCarrierAntGrpID }
		::=  { rruCarrierTable  1 }


	RruCarrierEntry		 ::=  SEQUENCE {
		rruCarrierRRSNo					Integer32,
		rruCarrierAntGrpID					Integer32,
		rruCarrierRowStatus					RowStatus,
		rruCarrierState					DisplayString
		}


	rruCarrierRRSNo		 OBJECT-TYPE
		SYNTAX					 Integer32( 0 .. 47 )
		MAX-ACCESS			 not-accessible
		STATUS					 current
		DESCRIPTION			 " -- "
		::=  { rruCarrierEntry  1 }


	rruCarrierAntGrpID		 OBJECT-TYPE
		SYNTAX					 Integer32( 1 .. 8 )
		MAX-ACCESS			 not-accessible
		STATUS					 current
		DESCRIPTION			 " -- "
		::=  { rruCarrierEntry  2 }


	rruCarrierRowStatus		 OBJECT-TYPE
		SYNTAX					 RowStatus
		MAX-ACCESS			 read-only
		STATUS					 current
		DESCRIPTION			 " -- "
		::=  { rruCarrierEntry  3 }


	rruCarrierState		 OBJECT-TYPE
		SYNTAX					 DisplayString( SIZE ( 1 .. 255 ) )
		MAX-ACCESS			 read-only
		STATUS					 current
		DESCRIPTION			 " -- "
		::=  { rruCarrierEntry  4 }


	carrierRuTable		 OBJECT-TYPE
		SYNTAX					 SEQUENCE  OF	 CarrierRuEntry
		MAX-ACCESS			 not-accessible
		STATUS					 current
		DESCRIPTION			 " -- "
		::=  { tdsLocalcell  9 }


	carrierRuEntry		 OBJECT-TYPE
		SYNTAX					 CarrierRuEntry
		MAX-ACCESS			 not-accessible
		STATUS					 current
		DESCRIPTION			 " -- "
		INDEX						{ carrierRuLocalCellId,carrierRuLocalCarrierIndex }
		::=  { carrierRuTable  1 }


	CarrierRuEntry		 ::=  SEQUENCE {
		carrierRuLocalCellId					Integer32,
		carrierRuLocalCarrierIndex					Integer32,
		carrierRuRowStatus					RowStatus,
		carrierRuCellId					Integer32,
		carrierRuCellFreq					Unsigned32,
		carrierRuTs0Info					OCTET STRING,
		carrierRuTs1Info					OCTET STRING,
		carrierRuTs2Info					OCTET STRING,
		carrierRuTs3Info					OCTET STRING,
		carrierRuTs4Info					OCTET STRING,
		carrierRuTs5Info					OCTET STRING,
		carrierRuTs6Info					OCTET STRING
		}


	carrierRuLocalCellId		 OBJECT-TYPE
		SYNTAX					 Integer32( 0 .. 11 )
		MAX-ACCESS			 not-accessible
		STATUS					 current
		DESCRIPTION			 " -- "
		::=  { carrierRuEntry  1 }


	carrierRuLocalCarrierIndex		 OBJECT-TYPE
		SYNTAX					 Integer32( 0 .. 20 )
		MAX-ACCESS			 not-accessible
		STATUS					 current
		DESCRIPTION			 " -- "
		::=  { carrierRuEntry  2 }


	carrierRuRowStatus		 OBJECT-TYPE
		SYNTAX					 RowStatus
		MAX-ACCESS			 read-only
		STATUS					 current
		DESCRIPTION			 " -- "
		::=  { carrierRuEntry  3 }


	carrierRuCellId		 OBJECT-TYPE
		SYNTAX					 Integer32( -2147483648 .. 2147483647 )
		MAX-ACCESS			 read-only
		STATUS					 current
		DESCRIPTION			 " -- "
		::=  { carrierRuEntry  4 }


	carrierRuCellFreq		 OBJECT-TYPE
		SYNTAX					 Unsigned32( 0 .. 65535 )
		MAX-ACCESS			 read-only
		STATUS					 current
		DESCRIPTION			 " -- "
		::=  { carrierRuEntry  5 }


	carrierRuTs0Info		 OBJECT-TYPE
		SYNTAX					 OCTET STRING
		MAX-ACCESS			 read-only
		STATUS					 current
		DESCRIPTION			 " -- "
		::=  { carrierRuEntry  6 }


	carrierRuTs1Info		 OBJECT-TYPE
		SYNTAX					 OCTET STRING
		MAX-ACCESS			 read-only
		STATUS					 current
		DESCRIPTION			 " -- "
		::=  { carrierRuEntry  7 }


	carrierRuTs2Info		 OBJECT-TYPE
		SYNTAX					 OCTET STRING
		MAX-ACCESS			 read-only
		STATUS					 current
		DESCRIPTION			 " -- "
		::=  { carrierRuEntry  8 }


	carrierRuTs3Info		 OBJECT-TYPE
		SYNTAX					 OCTET STRING
		MAX-ACCESS			 read-only
		STATUS					 current
		DESCRIPTION			 " -- "
		::=  { carrierRuEntry  9 }


	carrierRuTs4Info		 OBJECT-TYPE
		SYNTAX					 OCTET STRING
		MAX-ACCESS			 read-only
		STATUS					 current
		DESCRIPTION			 " -- "
		::=  { carrierRuEntry  10 }


	carrierRuTs5Info		 OBJECT-TYPE
		SYNTAX					 OCTET STRING
		MAX-ACCESS			 read-only
		STATUS					 current
		DESCRIPTION			 " -- "
		::=  { carrierRuEntry  11 }


	carrierRuTs6Info		 OBJECT-TYPE
		SYNTAX					 OCTET STRING
		MAX-ACCESS			 read-only
		STATUS					 current
		DESCRIPTION			 " -- "
		::=  { carrierRuEntry  12 }


	minimizationOfDriveTests		 OBJECT IDENTIFIER
		::=  { eNBConfig  9 }


	mdtSwitchInfo		 OBJECT IDENTIFIER
		::=  { minimizationOfDriveTests  1 }


	mdtManageEnableSwitch		 OBJECT-TYPE
		SYNTAX					 INTEGER{ false(0),true(1)  }
		MAX-ACCESS			 read-write
		STATUS					 current
		DESCRIPTION			 " -- "
		::=  { mdtSwitchInfo  1 }


	mdtSignalEnableSwitch		 OBJECT-TYPE
		SYNTAX					 INTEGER{ false(0),true(1)  }
		MAX-ACCESS			 read-write
		STATUS					 current
		DESCRIPTION			 " -- "
		::=  { mdtSwitchInfo  2 }


	mdtConfigManagement		 OBJECT IDENTIFIER
		::=  { minimizationOfDriveTests  2 }


	mdtServerInetAddrType		 OBJECT-TYPE
		SYNTAX					 InetAddressType
		MAX-ACCESS			 read-write
		STATUS					 current
		DESCRIPTION			 " -- "
		::=  { mdtConfigManagement  1 }


	mdtServerInetAddr		 OBJECT-TYPE
		SYNTAX					 InetAddress
		MAX-ACCESS			 read-write
		STATUS					 current
		DESCRIPTION			 " -- "
		::=  { mdtConfigManagement  2 }


	mdtFileDirectory		 OBJECT-TYPE
		SYNTAX					 DisplayString( SIZE ( 1 .. 199 ) )
		MAX-ACCESS			 read-write
		STATUS					 current
		DESCRIPTION			 " -- "
		::=  { mdtConfigManagement  3 }


	mdtFtpServerLoginName		 OBJECT-TYPE
		SYNTAX					 DisplayString( SIZE ( 1 .. 255 ) )
		MAX-ACCESS			 read-write
		STATUS					 current
		DESCRIPTION			 " -- "
		::=  { mdtConfigManagement  4 }


	mdtFtpServerPassword		 OBJECT-TYPE
		SYNTAX					 DisplayString( SIZE ( 1 .. 255 ) )
		MAX-ACCESS			 read-write
		STATUS					 current
		DESCRIPTION			 " -- "
		::=  { mdtConfigManagement  5 }


	mdtMmeSwitch		 OBJECT-TYPE
		SYNTAX					 INTEGER{ false(0),true(1)  }
		MAX-ACCESS			 read-write
		STATUS					 current
		DESCRIPTION			 " -- "
		::=  { mdtConfigManagement  6 }


	mdtRptPeriod		 OBJECT-TYPE
		SYNTAX					 INTEGER{ min15(2),min30(5),min45(8),min60(11)  }
		MAX-ACCESS			 read-write
		STATUS					 current
		DESCRIPTION			 " -- "
		::=  { mdtConfigManagement  7 }


	mdtTCEIpaddrType		 OBJECT-TYPE
		SYNTAX					 InetAddressType
		MAX-ACCESS			 read-write
		STATUS					 current
		DESCRIPTION			 " -- "
		::=  { mdtConfigManagement  8 }


	mdtTCEIpaddr		 OBJECT-TYPE
		SYNTAX					 InetAddress
		MAX-ACCESS			 read-write
		STATUS					 current
		DESCRIPTION			 " -- "
		::=  { mdtConfigManagement  9 }


	mdtTCEId		 OBJECT-TYPE
		SYNTAX					 Integer32( 0 .. 255 )
		MAX-ACCESS			 read-write
		STATUS					 current
		DESCRIPTION			 " -- "
		::=  { mdtConfigManagement  10 }


	mdtMaxUserNumber		 OBJECT-TYPE
		SYNTAX					 Integer32( 0 .. 600 )
		MAX-ACCESS			 read-write
		STATUS					 current
		DESCRIPTION			 " -- "
		::=  { mdtConfigManagement  11 }


	mdtSelectUserPercent		 OBJECT-TYPE
		SYNTAX					 Integer32( 0 .. 100 )
		MAX-ACCESS			 read-write
		STATUS					 current
		DESCRIPTION			 " -- "
		::=  { mdtConfigManagement  12 }


	mdtDataAnonymization		 OBJECT-TYPE
		SYNTAX					 INTEGER{ noIdentity(0),tacPartofIMEI(1)  }
		MAX-ACCESS			 read-write
		STATUS					 current
		DESCRIPTION			 " -- "
		::=  { mdtConfigManagement  13 }


	mdtImmediateMDTUeLocation		 OBJECT-TYPE
		SYNTAX					 INTEGER{ false(0),true(1)  }
		MAX-ACCESS			 read-write
		STATUS					 current
		DESCRIPTION			 " -- "
		::=  { mdtConfigManagement  14 }


	mdtImmediateMDTReportQuantity		 OBJECT-TYPE
		SYNTAX					 BITS{ rsrp(0),rsrq(1),phr(2)  }
		MAX-ACCESS			 read-write
		STATUS					 current
		DESCRIPTION			 " -- "
		::=  { mdtConfigManagement  15 }


	mdtImmediateMDTReportType		 OBJECT-TYPE
		SYNTAX					 INTEGER{ a2(0),periodical(1),a2periodical(2)  }
		MAX-ACCESS			 read-write
		STATUS					 current
		DESCRIPTION			 " -- "
		::=  { mdtConfigManagement  16 }


	mdtLoggedMDTExecuteTime		 OBJECT-TYPE
		SYNTAX					 INTEGER{ ms10(0),ms20(1),ms40(2),ms60(3),ms90(4),ms120(5)  }
		MAX-ACCESS			 read-write
		STATUS					 current
		DESCRIPTION			 " -- "
		::=  { mdtConfigManagement  22 }


	mdtLoggedMDTMeasureInterval		 OBJECT-TYPE
		SYNTAX					 INTEGER{ oneDot28(0),twoDot56(1),fiveDot12(2),tenDot24(3),twentyDot48(4),thirtyDot72(5),fortyDot96(6),sixtyOneDot44(7)  }
		MAX-ACCESS			 read-write
		STATUS					 current
		DESCRIPTION			 " -- "
		::=  { mdtConfigManagement  23 }


	mdtLoggedMDTAbsoluteTime		 OBJECT-TYPE
		SYNTAX					 DateAndTime
		MAX-ACCESS			 read-write
		STATUS					 current
		DESCRIPTION			 " -- "
		::=  { mdtConfigManagement  24 }


	mdtLoggedMDTTraceAreaCfgType		 OBJECT-TYPE
		SYNTAX					 INTEGER{ plmn(0),tacList(1),cellList(2)  }
		MAX-ACCESS			 read-write
		STATUS					 current
		DESCRIPTION			 " -- "
		::=  { mdtConfigManagement  26 }


	mdtLoggedMDTUeLocation		 OBJECT-TYPE
		SYNTAX					 INTEGER{ false(0),true(1)  }
		MAX-ACCESS			 read-write
		STATUS					 current
		DESCRIPTION			 " -- "
		::=  { mdtConfigManagement  27 }


	mdtImmediateMdtPositionMethod		 OBJECT-TYPE
		SYNTAX					 INTEGER{ trybest(0),gnss(1),ecid(2),gnssAndECID(3)  }
		MAX-ACCESS			 read-write
		STATUS					 current
		DESCRIPTION			 " -- "
		::=  { mdtConfigManagement  28 }


	mdtLoggedMdtPositionMethod		 OBJECT-TYPE
		SYNTAX					 INTEGER{ trybest(0),gnss(1),ecid(2),gnssAndECID(3)  }
		MAX-ACCESS			 read-write
		STATUS					 current
		DESCRIPTION			 " -- "
		::=  { mdtConfigManagement  29 }


	mdtDataFormat		 OBJECT-TYPE
		SYNTAX					 INTEGER{ xml(1),csv(2)  }
		MAX-ACCESS			 read-write
		STATUS					 current
		DESCRIPTION			 " -- "
		::=  { mdtConfigManagement  30 }


	loggedMdtCellTable		 OBJECT-TYPE
		SYNTAX					 SEQUENCE  OF	 LoggedMdtCellEntry
		MAX-ACCESS			 not-accessible
		STATUS					 current
		DESCRIPTION			 " -- "
		::=  { minimizationOfDriveTests  3 }


	loggedMdtCellEntry		 OBJECT-TYPE
		SYNTAX					 LoggedMdtCellEntry
		MAX-ACCESS			 not-accessible
		STATUS					 current
		DESCRIPTION			 " -- "
		INDEX						{ loggedMdtCellIndex }
		::=  { loggedMdtCellTable  1 }


	LoggedMdtCellEntry		 ::=  SEQUENCE {
		loggedMdtCellIndex					Integer32,
		loggedMdtCellRowStatus					RowStatus,
		loggedMdtPlmnMcc					MncMccType,
		loggedMdtPlmnMnc					MncMccType,
		loggedMdtCellEnbGlobalId					Unsigned32,
		loggedMdtCellId					Integer32
		}


	loggedMdtCellIndex		 OBJECT-TYPE
		SYNTAX					 Integer32( 1 .. 32 )
		MAX-ACCESS			 not-accessible
		STATUS					 current
		DESCRIPTION			 " -- "
		::=  { loggedMdtCellEntry  1 }


	loggedMdtCellRowStatus		 OBJECT-TYPE
		SYNTAX					 RowStatus
		MAX-ACCESS			 read-create
		STATUS					 current
		DESCRIPTION			 " -- "
		::=  { loggedMdtCellEntry  2 }


	loggedMdtPlmnMcc		 OBJECT-TYPE
		SYNTAX					 MncMccType
		MAX-ACCESS			 read-create
		STATUS					 current
		DESCRIPTION			 " -- "
		::=  { loggedMdtCellEntry  3 }


	loggedMdtPlmnMnc		 OBJECT-TYPE
		SYNTAX					 MncMccType
		MAX-ACCESS			 read-create
		STATUS					 current
		DESCRIPTION			 " -- "
		::=  { loggedMdtCellEntry  4 }


	loggedMdtCellEnbGlobalId		 OBJECT-TYPE
		SYNTAX					 Unsigned32( 0 .. 1048575 )
		MAX-ACCESS			 read-create
		STATUS					 current
		DESCRIPTION			 " -- "
		::=  { loggedMdtCellEntry  5 }


	loggedMdtCellId		 OBJECT-TYPE
		SYNTAX					 Integer32( 0 .. 255 )
		MAX-ACCESS			 read-create
		STATUS					 current
		DESCRIPTION			 " -- "
		::=  { loggedMdtCellEntry  6 }


	loggedMdtTaTable		 OBJECT-TYPE
		SYNTAX					 SEQUENCE  OF	 LoggedMdtTaEntry
		MAX-ACCESS			 not-accessible
		STATUS					 current
		DESCRIPTION			 " -- "
		::=  { minimizationOfDriveTests  4 }


	loggedMdtTaEntry		 OBJECT-TYPE
		SYNTAX					 LoggedMdtTaEntry
		MAX-ACCESS			 not-accessible
		STATUS					 current
		DESCRIPTION			 " -- "
		INDEX						{ loggedMdtTaIndex }
		::=  { loggedMdtTaTable  1 }


	LoggedMdtTaEntry		 ::=  SEQUENCE {
		loggedMdtTaIndex					Integer32,
		loggedMdtTaRowStatus					RowStatus,
		loggedMdtTac					Integer32
		}


	loggedMdtTaIndex		 OBJECT-TYPE
		SYNTAX					 Integer32( 1 .. 8 )
		MAX-ACCESS			 not-accessible
		STATUS					 current
		DESCRIPTION			 " -- "
		::=  { loggedMdtTaEntry  1 }


	loggedMdtTaRowStatus		 OBJECT-TYPE
		SYNTAX					 RowStatus
		MAX-ACCESS			 read-create
		STATUS					 current
		DESCRIPTION			 " -- "
		::=  { loggedMdtTaEntry  2 }


	loggedMdtTac		 OBJECT-TYPE
		SYNTAX					 Integer32( 0 .. 65535 )
		MAX-ACCESS			 read-create
		STATUS					 current
		DESCRIPTION			 " -- "
		::=  { loggedMdtTaEntry  3 }


	mdtTaskTable		 OBJECT-TYPE
		SYNTAX					 SEQUENCE  OF	 MdtTaskEntry
		MAX-ACCESS			 not-accessible
		STATUS					 current
		DESCRIPTION			 " -- "
		::=  { minimizationOfDriveTests  5 }


	mdtTaskEntry		 OBJECT-TYPE
		SYNTAX					 MdtTaskEntry
		MAX-ACCESS			 not-accessible
		STATUS					 current
		DESCRIPTION			 " -- "
		INDEX						{ mdtTaskIndex }
		::=  { mdtTaskTable  1 }


	MdtTaskEntry		 ::=  SEQUENCE {
		mdtTaskIndex					Integer32,
		mdtTaskRowStatus					RowStatus,
		mdtTaskPlmnMcc					MncMccType,
		mdtTaskPlmnMnc					MncMccType,
		mdtTaskTraceID					Unsigned32,
		mdtTaskTRSR					Integer32,
		mdtCellListBitMap					BITS,
		mdtTaskType					INTEGER
		}


	mdtTaskIndex		 OBJECT-TYPE
		SYNTAX					 Integer32( 0 .. 3 )
		MAX-ACCESS			 not-accessible
		STATUS					 current
		DESCRIPTION			 " -- "
		::=  { mdtTaskEntry  1 }


	mdtTaskRowStatus		 OBJECT-TYPE
		SYNTAX					 RowStatus
		MAX-ACCESS			 read-create
		STATUS					 current
		DESCRIPTION			 " -- "
		::=  { mdtTaskEntry  2 }


	mdtTaskPlmnMcc		 OBJECT-TYPE
		SYNTAX					 MncMccType
		MAX-ACCESS			 read-create
		STATUS					 current
		DESCRIPTION			 " -- "
		::=  { mdtTaskEntry  3 }


	mdtTaskPlmnMnc		 OBJECT-TYPE
		SYNTAX					 MncMccType
		MAX-ACCESS			 read-create
		STATUS					 current
		DESCRIPTION			 " -- "
		::=  { mdtTaskEntry  4 }


	mdtTaskTraceID		 OBJECT-TYPE
		SYNTAX					 Unsigned32( 0 .. 16777215 )
		MAX-ACCESS			 read-create
		STATUS					 current
		DESCRIPTION			 " -- "
		::=  { mdtTaskEntry  5 }


	mdtTaskTRSR		 OBJECT-TYPE
		SYNTAX					 Integer32( 0 .. 65535 )
		MAX-ACCESS			 read-create
		STATUS					 current
		DESCRIPTION			 " -- "
		::=  { mdtTaskEntry  6 }


	mdtCellListBitMap		 OBJECT-TYPE
		SYNTAX					 BITS{ localCell0(0),localCell1(1),localCell2(2),localCell3(3),localCell4(4),localCell5(5),localCell6(6),localCell7(7),localCell8(8),localCell9(9),localCell10(10),localCell11(11),localCell12(12),localCell13(13),localCell14(14),localCell15(15),localCell16(16),localCell17(17),localCell18(18),localCell19(19),localCell20(20),localCell21(21),localCell22(22),localCell23(23)  }
		MAX-ACCESS			 read-create
		STATUS					 current
		DESCRIPTION			 " -- "
		::=  { mdtTaskEntry  7 }


	mdtTaskType		 OBJECT-TYPE
		SYNTAX					 INTEGER{ immediateMDTOnly(0),loggedMDTOnly(1),traceOnly(2),rlf(200)  }
		MAX-ACCESS			 read-create
		STATUS					 current
		DESCRIPTION			 " -- "
		::=  { mdtTaskEntry  8 }


	netLocalCellInfo		 OBJECT IDENTIFIER
		::=  { networkElementLayoutPlan  3 }


	netLocalCellCtrl		 OBJECT IDENTIFIER
		::=  { netLocalCellInfo  1 }


	netLocalCellCtrlTable		 OBJECT-TYPE
		SYNTAX					 SEQUENCE  OF	 NetLocalCellCtrlEntry
		MAX-ACCESS			 not-accessible
		STATUS					 current
		DESCRIPTION			 " -- "
		::=  { netLocalCellCtrl  1 }


	netLocalCellCtrlEntry		 OBJECT-TYPE
		SYNTAX					 NetLocalCellCtrlEntry
		MAX-ACCESS			 not-accessible
		STATUS					 current
		DESCRIPTION			 " -- "
		INDEX						{ netPlanControlLcId }
		::=  { netLocalCellCtrlTable  1 }


	NetLocalCellCtrlEntry		 ::=  SEQUENCE {
		netPlanControlLcId					Integer32,
		netPlanControlLcConfigSwitch					INTEGER
		}


	netPlanControlLcId		 OBJECT-TYPE
		SYNTAX					 Integer32( 0 .. 23 )
		MAX-ACCESS			 not-accessible
		STATUS					 current
		DESCRIPTION			 " -- "
		::=  { netLocalCellCtrlEntry  1 }


	netPlanControlLcConfigSwitch		 OBJECT-TYPE
		SYNTAX					 INTEGER{ off(0),on(1)  }
		MAX-ACCESS			 read-write
		STATUS					 current
		DESCRIPTION			 " -- "
		::=  { netLocalCellCtrlEntry  2 }


	tdsNetLocalCellCtrlTable		 OBJECT-TYPE
		SYNTAX					 SEQUENCE  OF	 TdsNetLocalCellCtrlEntry
		MAX-ACCESS			 not-accessible
		STATUS					 current
		DESCRIPTION			 " -- "
		::=  { netLocalCellCtrl  2 }


	tdsNetLocalCellCtrlEntry		 OBJECT-TYPE
		SYNTAX					 TdsNetLocalCellCtrlEntry
		MAX-ACCESS			 not-accessible
		STATUS					 current
		DESCRIPTION			 " -- "
		INDEX						{ tdsNetPlanControlLcId }
		::=  { tdsNetLocalCellCtrlTable  1 }


	TdsNetLocalCellCtrlEntry		 ::=  SEQUENCE {
		tdsNetPlanControlLcId					Integer32,
		tdsNetPlanControlLcConfigSwitch					INTEGER
		}


	tdsNetPlanControlLcId		 OBJECT-TYPE
		SYNTAX					 Integer32( 0 .. 23 )
		MAX-ACCESS			 not-accessible
		STATUS					 current
		DESCRIPTION			 " -- "
		::=  { tdsNetLocalCellCtrlEntry  1 }


	tdsNetPlanControlLcConfigSwitch		 OBJECT-TYPE
		SYNTAX					 INTEGER{ off(0),on(1)  }
		MAX-ACCESS			 read-write
		STATUS					 current
		DESCRIPTION			 " -- "
		::=  { tdsNetLocalCellCtrlEntry  2 }


	netLocalCellPowerCtrlTable		 OBJECT-TYPE
		SYNTAX					 SEQUENCE  OF	 NetLocalCellPowerCtrlEntry
		MAX-ACCESS			 not-accessible
		STATUS					 current
		DESCRIPTION			 " -- "
		::=  { netLocalCellCtrl  3 }


	netLocalCellPowerCtrlEntry		 OBJECT-TYPE
		SYNTAX					 NetLocalCellPowerCtrlEntry
		MAX-ACCESS			 not-accessible
		STATUS					 current
		DESCRIPTION			 " -- "
		INDEX						{ netPlanPowerControlLcId }
		::=  { netLocalCellPowerCtrlTable  1 }


	NetLocalCellPowerCtrlEntry		 ::=  SEQUENCE {
		netPlanPowerControlLcId					Integer32,
		netPlanPowerControlCfgSwitch					INTEGER
		}


	netPlanPowerControlLcId		 OBJECT-TYPE
		SYNTAX					 Integer32( 0 .. 23 )
		MAX-ACCESS			 not-accessible
		STATUS					 current
		DESCRIPTION			 " -- "
		::=  { netLocalCellPowerCtrlEntry  1 }


	netPlanPowerControlCfgSwitch		 OBJECT-TYPE
		SYNTAX					 INTEGER{ off(0),on(1)  }
		MAX-ACCESS			 read-write
		STATUS					 current
		DESCRIPTION			 " -- "
		::=  { netLocalCellPowerCtrlEntry  2 }


	netLocalCell		 OBJECT IDENTIFIER
		::=  { netLocalCellInfo  2 }


	netLocalCellTable		 OBJECT-TYPE
		SYNTAX					 SEQUENCE  OF	 NetLocalCellEntry
		MAX-ACCESS			 not-accessible
		STATUS					 current
		DESCRIPTION			 " -- "
		::=  { netLocalCell  1 }


	netLocalCellEntry		 OBJECT-TYPE
		SYNTAX					 NetLocalCellEntry
		MAX-ACCESS			 not-accessible
		STATUS					 current
		DESCRIPTION			 " -- "
		INDEX						{ netLcLocalCellId }
		::=  { netLocalCellTable  1 }


	NetLocalCellEntry		 ::=  SEQUENCE {
		netLcLocalCellId					Integer32,
		netLcRowStatus					RowStatus,
		netLcFreqBand					INTEGER,
		netLcFreqBandWidth					INTEGER,
		netLcAntCombinationFlag					INTEGER,
		netLcAppScene					INTEGER,
		netLcAntArrayMode					INTEGER,
		netLcIrCompressMode					INTEGER,
		netLcAntPortNum					INTEGER,
		netLcFrameType					INTEGER,
		netLcCellCombineEnhancedSwitch					INTEGER,
		netLcSdcFuncSwitch					INTEGER,
		netLcCellCombine4PortSwitch					INTEGER,
		netLcRadioChannelCombinSwitch					INTEGER
		}


	netLcLocalCellId		 OBJECT-TYPE
		SYNTAX					 Integer32( 0 .. 23 )
		MAX-ACCESS			 not-accessible
		STATUS					 current
		DESCRIPTION			 " -- "
		::=  { netLocalCellEntry  1 }


	netLcRowStatus		 OBJECT-TYPE
		SYNTAX					 RowStatus
		MAX-ACCESS			 read-create
		STATUS					 current
		DESCRIPTION			 " -- "
		::=  { netLocalCellEntry  2 }


	netLcFreqBand		 OBJECT-TYPE
		SYNTAX					 INTEGER{ a(1),d(2),e(4),f(8),v(32),b41(64),t(128),b03(256),b01(512),b44(1024)  }
		MAX-ACCESS			 read-create
		STATUS					 current
		DESCRIPTION			 " -- "
		::=  { netLocalCellEntry  3 }


	netLcFreqBandWidth		 OBJECT-TYPE
		SYNTAX					 INTEGER{ val5M(0),val10M(1),val15M(2),val20M(3)  }
		MAX-ACCESS			 read-create
		STATUS					 current
		DESCRIPTION			 " -- "
		::=  { netLocalCellEntry  4 }


	netLcAntCombinationFlag		 OBJECT-TYPE
		SYNTAX					 INTEGER{ false(0),true(1)  }
		MAX-ACCESS			 read-create
		STATUS					 current
		DESCRIPTION			 " -- "
		::=  { netLocalCellEntry  5 }


	netLcAppScene		 OBJECT-TYPE
		SYNTAX					 INTEGER{ indoorNormal(0),outdoorNormal(1),outdoorHighSpeed(2)  }
		MAX-ACCESS			 read-create
		STATUS					 current
		DESCRIPTION			 " -- "
		::=  { netLocalCellEntry  6 }


	netLcAntArrayMode		 OBJECT-TYPE
		SYNTAX					 INTEGER{ unknown(0),smartAnt(1),nonSmartAnt(2),mixedAnt(3)  }
		MAX-ACCESS			 read-create
		STATUS					 current
		DESCRIPTION			 " -- "
		::=  { netLocalCellEntry  7 }


	netLcIrCompressMode		 OBJECT-TYPE
		SYNTAX					 INTEGER{ notCompress(0),compress(1)  }
		MAX-ACCESS			 read-create
		STATUS					 current
		DESCRIPTION			 " -- "
		::=  { netLocalCellEntry  8 }


	netLcAntPortNum		 OBJECT-TYPE
		SYNTAX					 INTEGER{ port1(0),port2(1),port4(2),unknown(255)  }
		MAX-ACCESS			 read-create
		STATUS					 current
		DESCRIPTION			 " -- "
		::=  { netLocalCellEntry  9 }


	netLcFrameType		 OBJECT-TYPE
		SYNTAX					 INTEGER{ fdd(0),tdd(1)  }
		MAX-ACCESS			 read-create
		STATUS					 current
		DESCRIPTION			 " -- "
		::=  { netLocalCellEntry  10 }


	netLcCellCombineEnhancedSwitch		 OBJECT-TYPE
		SYNTAX					 INTEGER{ off(0),on(1)  }
		MAX-ACCESS			 read-create
		STATUS					 current
		DESCRIPTION			 " -- "
		::=  { netLocalCellEntry  11 }


	netLcSdcFuncSwitch		 OBJECT-TYPE
		SYNTAX					 INTEGER{ off(0),on(1)  }
		MAX-ACCESS			 read-create
		STATUS					 current
		DESCRIPTION			 " -- "
		::=  { netLocalCellEntry  12 }


	netLcCellCombine4PortSwitch		 OBJECT-TYPE
		SYNTAX					 INTEGER{ off(0),on(1)  }
		MAX-ACCESS			 read-create
		STATUS					 current
		DESCRIPTION			 " -- "
		::=  { netLocalCellEntry  13 }


	netLcRadioChannelCombinSwitch		 OBJECT-TYPE
		SYNTAX					 INTEGER{ off(0),bbuCom(1),rhubCom(2)  }
		MAX-ACCESS			 read-create
		STATUS					 current
		DESCRIPTION			 " -- "
		::=  { netLocalCellEntry  14 }


	netLocalCellRruPowerTable		 OBJECT-TYPE
		SYNTAX					 SEQUENCE  OF	 NetLocalCellRruPowerEntry
		MAX-ACCESS			 not-accessible
		STATUS					 current
		DESCRIPTION			 " -- "
		::=  { netLocalCell  2 }


	netLocalCellRruPowerEntry		 OBJECT-TYPE
		SYNTAX					 NetLocalCellRruPowerEntry
		MAX-ACCESS			 not-accessible
		STATUS					 current
		DESCRIPTION			 " -- "
		INDEX						{ netLcRruPowerLcId,netLcRruPowerRruNo,netLcRruPowerRruPathNo }
		::=  { netLocalCellRruPowerTable  1 }


	NetLocalCellRruPowerEntry		 ::=  SEQUENCE {
		netLcRruPowerLcId					Integer32,
		netLcRruPowerRruNo					Integer32,
		netLcRruPowerRruPathNo					Integer32,
		netLcRruPowerRowStatus					RowStatus,
		netLcRruPowerPathAdjustValue					Integer32
		}


	netLcRruPowerLcId		 OBJECT-TYPE
		SYNTAX					 Integer32( 0 .. 23 )
		MAX-ACCESS			 not-accessible
		STATUS					 current
		DESCRIPTION			 " -- "
		::=  { netLocalCellRruPowerEntry  1 }


	netLcRruPowerRruNo		 OBJECT-TYPE
		SYNTAX					 Integer32( 0 .. 191 )
		MAX-ACCESS			 not-accessible
		STATUS					 current
		DESCRIPTION			 " -- "
		::=  { netLocalCellRruPowerEntry  2 }


	netLcRruPowerRruPathNo		 OBJECT-TYPE
		SYNTAX					 Integer32( 1 .. 16 )
		MAX-ACCESS			 not-accessible
		STATUS					 current
		DESCRIPTION			 " -- "
		::=  { netLocalCellRruPowerEntry  3 }


	netLcRruPowerRowStatus		 OBJECT-TYPE
		SYNTAX					 RowStatus
		MAX-ACCESS			 read-create
		STATUS					 current
		DESCRIPTION			 " -- "
		::=  { netLocalCellRruPowerEntry  4 }


	netLcRruPowerPathAdjustValue		 OBJECT-TYPE
		SYNTAX					 Integer32( 0 .. 400 )
		MAX-ACCESS			 read-create
		STATUS					 current
		DESCRIPTION			 " -- "
		::=  { netLocalCellRruPowerEntry  5 }


	netLocalCellComponentTable		 OBJECT-TYPE
		SYNTAX					 SEQUENCE  OF	 NetLocalCellComponentEntry
		MAX-ACCESS			 not-accessible
		STATUS					 current
		DESCRIPTION			 " -- "
		::=  { netLocalCell  3 }


	netLocalCellComponentEntry		 OBJECT-TYPE
		SYNTAX					 NetLocalCellComponentEntry
		MAX-ACCESS			 not-accessible
		STATUS					 current
		DESCRIPTION			 " -- "
		INDEX						{ netLcComponentLcId,netLcComponentIndex }
		::=  { netLocalCellComponentTable  1 }


	NetLocalCellComponentEntry		 ::=  SEQUENCE {
		netLcComponentLcId					Integer32,
		netLcComponentIndex					Integer32,
		netLcComponentRowStatus					RowStatus,
		netLcComponentRRUId					Unsigned32Array
		}


	netLcComponentLcId		 OBJECT-TYPE
		SYNTAX					 Integer32( 0 .. 23 )
		MAX-ACCESS			 not-accessible
		STATUS					 current
		DESCRIPTION			 " -- "
		::=  { netLocalCellComponentEntry  1 }


	netLcComponentIndex		 OBJECT-TYPE
		SYNTAX					 Integer32( 0 .. 11 )
		MAX-ACCESS			 not-accessible
		STATUS					 current
		DESCRIPTION			 " -- "
		::=  { netLocalCellComponentEntry  2 }


	netLcComponentRowStatus		 OBJECT-TYPE
		SYNTAX					 RowStatus
		MAX-ACCESS			 read-only
		STATUS					 current
		DESCRIPTION			 " -- "
		::=  { netLocalCellComponentEntry  3 }


	netLcComponentRRUId		 OBJECT-TYPE
		SYNTAX					 Unsigned32Array
		MAX-ACCESS			 read-only
		STATUS					 current
		DESCRIPTION			 " -- "
		::=  { netLocalCellComponentEntry  4 }


	tdsNetLocalCell		 OBJECT IDENTIFIER
		::=  { netLocalCellInfo  3 }


	tdsNetLocalCellTable		 OBJECT-TYPE
		SYNTAX					 SEQUENCE  OF	 TdsNetLocalCellEntry
		MAX-ACCESS			 not-accessible
		STATUS					 current
		DESCRIPTION			 " -- "
		::=  { tdsNetLocalCell  1 }


	tdsNetLocalCellEntry		 OBJECT-TYPE
		SYNTAX					 TdsNetLocalCellEntry
		MAX-ACCESS			 not-accessible
		STATUS					 current
		DESCRIPTION			 " -- "
		INDEX						{ tdsNetLcLocalCellId }
		::=  { tdsNetLocalCellTable  1 }


	TdsNetLocalCellEntry		 ::=  SEQUENCE {
		tdsNetLcLocalCellId					Integer32,
		tdsNetLcRowStatus					RowStatus,
		tdsNetLcAntArrayMode					INTEGER,
		tdsNetLcMaxCarrierNum					Integer32,
		tdsNetLcMinCarrierNum					Integer32,
		tdsNetLcLocalCellGrpId					Integer32,
		tdsNetLocalCellPriority					Integer32,
		tdsNetLocalCellIsAntCombination					INTEGER,
		tdsNetLocalCellMaxCombinationAntNum					Integer32,
		tdsNetLcAppScene					INTEGER,
		tdsNetLcPrimaryCarrierBand					INTEGER,
		tdsNetLcCellPortionNum					Integer32
		}


	tdsNetLcLocalCellId		 OBJECT-TYPE
		SYNTAX					 Integer32( 0 .. 11 )
		MAX-ACCESS			 not-accessible
		STATUS					 current
		DESCRIPTION			 " -- "
		::=  { tdsNetLocalCellEntry  1 }


	tdsNetLcRowStatus		 OBJECT-TYPE
		SYNTAX					 RowStatus
		MAX-ACCESS			 read-create
		STATUS					 current
		DESCRIPTION			 " -- "
		::=  { tdsNetLocalCellEntry  2 }


	tdsNetLcAntArrayMode		 OBJECT-TYPE
		SYNTAX					 INTEGER{ unknown(0),singleAnt(1),disAnt(2),smartAnt(3),ambipolarAnt(4),disSmartAnt(5),disAmbipolarAnt(6),smartPolarAnt(7),disSmartPolarAnt(8),mixAnt(9)  }
		MAX-ACCESS			 read-create
		STATUS					 current
		DESCRIPTION			 " -- "
		::=  { tdsNetLocalCellEntry  3 }


	tdsNetLcMaxCarrierNum		 OBJECT-TYPE
		SYNTAX					 Integer32( 1 .. 21|0 )
		MAX-ACCESS			 read-create
		STATUS					 current
		DESCRIPTION			 " -- "
		::=  { tdsNetLocalCellEntry  4 }


	tdsNetLcMinCarrierNum		 OBJECT-TYPE
		SYNTAX					 Integer32( 1 .. 21|0 )
		MAX-ACCESS			 read-create
		STATUS					 current
		DESCRIPTION			 " -- "
		::=  { tdsNetLocalCellEntry  5 }


	tdsNetLcLocalCellGrpId		 OBJECT-TYPE
		SYNTAX					 Integer32( 0 .. 11|0 )
		MAX-ACCESS			 read-create
		STATUS					 current
		DESCRIPTION			 " -- "
		::=  { tdsNetLocalCellEntry  6 }


	tdsNetLocalCellPriority		 OBJECT-TYPE
		SYNTAX					 Integer32( 0 .. 11 )
		MAX-ACCESS			 read-create
		STATUS					 current
		DESCRIPTION			 " -- "
		::=  { tdsNetLocalCellEntry  7 }


	tdsNetLocalCellIsAntCombination		 OBJECT-TYPE
		SYNTAX					 INTEGER{ false(0),antCombinationBetweenRRS(1),antCombinationInRRS(2),antCompleteCombination(3),antOptionalCombination(4)  }
		MAX-ACCESS			 read-create
		STATUS					 current
		DESCRIPTION			 " -- "
		::=  { tdsNetLocalCellEntry  8 }


	tdsNetLocalCellMaxCombinationAntNum		 OBJECT-TYPE
		SYNTAX					 Integer32( 2 .. 5|0 )
		MAX-ACCESS			 read-create
		STATUS					 current
		DESCRIPTION			 " -- "
		::=  { tdsNetLocalCellEntry  9 }


	tdsNetLcAppScene		 OBJECT-TYPE
		SYNTAX					 INTEGER{ normal(0),largeScope(1),underground(2)  }
		MAX-ACCESS			 read-write
		STATUS					 current
		DESCRIPTION			 " -- "
		::=  { tdsNetLocalCellEntry  10 }


	tdsNetLcPrimaryCarrierBand		 OBJECT-TYPE
		SYNTAX					 INTEGER{ v1880to1920(0),v2010to2025(1),v2300to2400(2)  }
		MAX-ACCESS			 read-create
		STATUS					 current
		DESCRIPTION			 " -- "
		::=  { tdsNetLocalCellEntry  11 }


	tdsNetLcCellPortionNum		 OBJECT-TYPE
		SYNTAX					 Integer32( 2 .. 8|0 )
		MAX-ACCESS			 read-create
		STATUS					 current
		DESCRIPTION			 " -- "
		::=  { tdsNetLocalCellEntry  12 }


	netLocalCellGroup		 OBJECT IDENTIFIER
		::=  { netLocalCellInfo  4 }


	netLocalCellGrpTable		 OBJECT-TYPE
		SYNTAX					 SEQUENCE  OF	 NetLocalCellGrpEntry
		MAX-ACCESS			 not-accessible
		STATUS					 current
		DESCRIPTION			 " -- "
		::=  { netLocalCellGroup  1 }


	netLocalCellGrpEntry		 OBJECT-TYPE
		SYNTAX					 NetLocalCellGrpEntry
		MAX-ACCESS			 not-accessible
		STATUS					 current
		DESCRIPTION			 " -- "
		INDEX						{ netLocalCellGrpId }
		::=  { netLocalCellGrpTable  1 }


	NetLocalCellGrpEntry		 ::=  SEQUENCE {
		netLocalCellGrpId					Integer32,
		netLocalCellGrpRowStatus					RowStatus,
		netLocalCellGrpCarrierTotalNum					Integer32,
		netLocalCellGrpMode					INTEGER
		}


	netLocalCellGrpId		 OBJECT-TYPE
		SYNTAX					 Integer32( 1 .. 11 )
		MAX-ACCESS			 not-accessible
		STATUS					 current
		DESCRIPTION			 " -- "
		::=  { netLocalCellGrpEntry  1 }


	netLocalCellGrpRowStatus		 OBJECT-TYPE
		SYNTAX					 RowStatus
		MAX-ACCESS			 read-create
		STATUS					 current
		DESCRIPTION			 " -- "
		::=  { netLocalCellGrpEntry  2 }


	netLocalCellGrpCarrierTotalNum		 OBJECT-TYPE
		SYNTAX					 Integer32( 0 .. 72 )
		MAX-ACCESS			 read-create
		STATUS					 current
		DESCRIPTION			 " -- "
		::=  { netLocalCellGrpEntry  3 }


	netLocalCellGrpMode		 OBJECT-TYPE
		SYNTAX					 INTEGER{ unknown(0),singleAntSupportable(1),multiAntSupportable(2),miscellaneous(3)  }
		MAX-ACCESS			 read-create
		STATUS					 current
		DESCRIPTION			 " -- "
		::=  { netLocalCellGrpEntry  4 }


	networkElementMME		 OBJECT IDENTIFIER
		::=  { networkElementLayoutPlan  4 }


	mmeCfgTable		 OBJECT-TYPE
		SYNTAX					 SEQUENCE  OF	 MmeCfgEntry
		MAX-ACCESS			 not-accessible
		STATUS					 current
		DESCRIPTION			 " -- "
		::=  { networkElementMME  1 }


	mmeCfgEntry		 OBJECT-TYPE
		SYNTAX					 MmeCfgEntry
		MAX-ACCESS			 not-accessible
		STATUS					 current
		DESCRIPTION			 " -- "
		INDEX						{ mmeIndex,mmeCfgIndex }
		::=  { mmeCfgTable  1 }


	MmeCfgEntry		 ::=  SEQUENCE {
		mmeIndex					Integer32,
		mmeCfgIndex					Integer32,
		mmeCfgRowStatus					RowStatus,
		mmeCfgPlmnMcc					MncMccType,
		mmeCfgPlmnMnc					MncMccType,
		mmeCfgGroupId					Integer32,
		mmeCfgMmeCode					Integer32,
		mmeCfgSctpIndex					Integer32,
		mmeCfgCapacity					Integer32,
		mmeCfgConnectUENum					Integer32
		}


	mmeIndex		 OBJECT-TYPE
		SYNTAX					 Integer32( 0 .. 15 )
		MAX-ACCESS			 not-accessible
		STATUS					 current
		DESCRIPTION			 " -- "
		::=  { mmeCfgEntry  1 }


	mmeCfgIndex		 OBJECT-TYPE
		SYNTAX					 Integer32( 0 .. 15 )
		MAX-ACCESS			 not-accessible
		STATUS					 current
		DESCRIPTION			 " -- "
		::=  { mmeCfgEntry  2 }


	mmeCfgRowStatus		 OBJECT-TYPE
		SYNTAX					 RowStatus
		MAX-ACCESS			 read-only
		STATUS					 current
		DESCRIPTION			 " -- "
		::=  { mmeCfgEntry  3 }


	mmeCfgPlmnMcc		 OBJECT-TYPE
		SYNTAX					 MncMccType
		MAX-ACCESS			 read-only
		STATUS					 current
		DESCRIPTION			 " -- "
		::=  { mmeCfgEntry  4 }


	mmeCfgPlmnMnc		 OBJECT-TYPE
		SYNTAX					 MncMccType
		MAX-ACCESS			 read-only
		STATUS					 current
		DESCRIPTION			 " -- "
		::=  { mmeCfgEntry  5 }


	mmeCfgGroupId		 OBJECT-TYPE
		SYNTAX					 Integer32( 0 .. 65535|-1 )
		MAX-ACCESS			 read-only
		STATUS					 current
		DESCRIPTION			 " -- "
		::=  { mmeCfgEntry  6 }


	mmeCfgMmeCode		 OBJECT-TYPE
		SYNTAX					 Integer32( 0 .. 255|-1 )
		MAX-ACCESS			 read-only
		STATUS					 current
		DESCRIPTION			 " -- "
		::=  { mmeCfgEntry  7 }


	mmeCfgSctpIndex		 OBJECT-TYPE
		SYNTAX					 Integer32( 0 .. 81|255 )
		MAX-ACCESS			 read-only
		STATUS					 current
		DESCRIPTION			 " -- "
		::=  { mmeCfgEntry  8 }


	mmeCfgCapacity		 OBJECT-TYPE
		SYNTAX					 Integer32( 0 .. 255 )
		MAX-ACCESS			 read-only
		STATUS					 current
		DESCRIPTION			 " -- "
		::=  { mmeCfgEntry  9 }


	mmeCfgConnectUENum		 OBJECT-TYPE
		SYNTAX					 Integer32( -2147483648 .. 2147483647 )
		MAX-ACCESS			 read-only
		STATUS					 current
		DESCRIPTION			 " -- "
		::=  { mmeCfgEntry  10 }


	networkElementPlanCell		 OBJECT IDENTIFIER
		::=  { networkElementLayoutPlan  5 }


	cellCfg		 OBJECT IDENTIFIER
		::=  { networkElementPlanCell  1 }


	cellCfgTable		 OBJECT-TYPE
		SYNTAX					 SEQUENCE  OF	 CellCfgEntry
		MAX-ACCESS			 not-accessible
		STATUS					 current
		DESCRIPTION			 " -- "
		::=  { cellCfg  1 }


	cellCfgEntry		 OBJECT-TYPE
		SYNTAX					 CellCfgEntry
		MAX-ACCESS			 not-accessible
		STATUS					 current
		DESCRIPTION			 " -- "
		INDEX						{ cellLcId }
		::=  { cellCfgTable  1 }


	CellCfgEntry		 ::=  SEQUENCE {
		cellLcId					Integer32,
		cellCfgRowStatus					RowStatus,
		cellFriendName					DisplayString,
		cellPhyId					Integer32,
		cellOmcPhyId					Integer32,
		cellPhyIdList					Unsigned32Array,
		cellFreqBand					INTEGER,
		cellCenterFreq					Integer32,
		cellDlSysBandWidth					INTEGER,
		cellCpType					INTEGER,
		cellSubSfnAssign					INTEGER,
		cellSpecialSubSfnPatterns					INTEGER,
		cellMaxTransPwr					Integer32,
		cellRsPower					Integer32,
		cellPbchPower					Integer32,
		cellPschPower					Integer32,
		cellSschPower					Integer32,
		cellPchPower					Integer32,
		cellPdschSibPower					Integer32,
		cellPcfichPower					Integer32,
		cellPhichPower					Integer32,
		cellPdcchPower					Integer32,
		cellBarred					INTEGER,
		cellSiPageMcs					Integer32,
		cellCountMSBcheckValue					Unsigned32,
		cellCounterOverturnValue					Unsigned32,
		cellCounterCheckErrorThresh					Unsigned32,
		cellDwptsForUserDataFlag					INTEGER,
		cellType					INTEGER,
		cellAntPortNum					INTEGER,
		cellQoffset					INTEGER,
		cellAddtionlSpecEmis					Integer32,
		cellCalAcOffset					Unsigned32,
		cellCdlDetailSwitch					INTEGER,
		cellPdcchCo4CceFormat1cPower					Integer32,
		cellPdcchCo4CceOtherFormatPower					Integer32,
		cellPdcchCo8CceFormat1cPower					Integer32,
		cellPdcchCo8CceOtherFormatPower					Integer32,
		cellMsg3PhichPower					Integer32,
		cellPriority					INTEGER,
		cellCdlServiceSwitch					INTEGER,
		cellCdlTcpSwitch					INTEGER,
		cellCellID					Integer32,
		cellPowerOffset					Integer32,
		cellCRSBoostingSwitch					INTEGER,
		cellBlackCellsStartPhyId					Integer32,
		cellBlackCellsRange					INTEGER,
		cellRsPowerDelta					Integer32,
		cellPortID					Integer32,
		cellTypeFlag					INTEGER,
		cellCfgFrameType					INTEGER,
		cellOffsetFreq					INTEGER,
		cellEARFCN					Integer32,
		cellAntTilt					Integer32,
		cellCdlPagingSwitch					INTEGER,
		cellCdlVoLTESwitch					INTEGER,
		cellCdlSpeedSwitch					INTEGER,
		cellAntWeightSwitch					INTEGER,
		cellDisguiseMaintenceState					INTEGER
		}


	cellLcId		 OBJECT-TYPE
		SYNTAX					 Integer32( 0 .. 23 )
		MAX-ACCESS			 not-accessible
		STATUS					 current
		DESCRIPTION			 " -- "
		::=  { cellCfgEntry  1 }


	cellCfgRowStatus		 OBJECT-TYPE
		SYNTAX					 RowStatus
		MAX-ACCESS			 read-create
		STATUS					 current
		DESCRIPTION			 " -- "
		::=  { cellCfgEntry  2 }


	cellFriendName		 OBJECT-TYPE
		SYNTAX					 DisplayString( SIZE ( 1 .. 255 ) )
		MAX-ACCESS			 read-create
		STATUS					 current
		DESCRIPTION			 " -- "
		::=  { cellCfgEntry  3 }


	cellPhyId		 OBJECT-TYPE
		SYNTAX					 Integer32( 0 .. 504|65535 )
		MAX-ACCESS			 read-only
		STATUS					 current
		DESCRIPTION			 " -- "
		::=  { cellCfgEntry  4 }


	cellOmcPhyId		 OBJECT-TYPE
		SYNTAX					 Integer32( 0 .. 504|65535 )
		MAX-ACCESS			 read-create
		STATUS					 current
		DESCRIPTION			 " -- "
		::=  { cellCfgEntry  5 }


	cellPhyIdList		 OBJECT-TYPE
		SYNTAX					 Unsigned32Array
		MAX-ACCESS			 read-create
		STATUS					 current
		DESCRIPTION			 " -- "
		::=  { cellCfgEntry  6 }


	cellFreqBand		 OBJECT-TYPE
		SYNTAX					 INTEGER{ band1(1),band2(2),band3(3),band4(4),band5(5),band7(7),band8(8),band9(9),band10(10),band11(11),band12(12),band13(13),band14(14),band17(17),band18(18),band19(19),band20(20),band21(21),band22(22),band23(23),band24(24),band25(25),band33(33),band34(34),band35(35),band36(36),band37(37),band38(38),band39(39),band40(40),band41(41),band44(44),band61(61),band62(62)  }
		MAX-ACCESS			 read-create
		STATUS					 current
		DESCRIPTION			 " -- "
		::=  { cellCfgEntry  7 }


	cellCenterFreq		 OBJECT-TYPE
		SYNTAX					 Integer32( 0 .. 65535 )
		MAX-ACCESS			 read-create
		STATUS					 current
		DESCRIPTION			 " -- "
		::=  { cellCfgEntry  8 }


	cellDlSysBandWidth		 OBJECT-TYPE
		SYNTAX					 INTEGER{ val1dot4(0),val3(1),val5(2),val10(3),val15(4),val20(5)  }
		MAX-ACCESS			 read-create
		STATUS					 current
		DESCRIPTION			 " -- "
		::=  { cellCfgEntry  9 }


	cellCpType		 OBJECT-TYPE
		SYNTAX					 INTEGER{ normal(0),extended(1)  }
		MAX-ACCESS			 read-create
		STATUS					 current
		DESCRIPTION			 " -- "
		::=  { cellCfgEntry  10 }


	cellSubSfnAssign		 OBJECT-TYPE
		SYNTAX					 INTEGER{ sa0(0),sa1(1),sa2(2),sa3(3),sa4(4),sa5(5),sa6(6)  }
		MAX-ACCESS			 read-create
		STATUS					 current
		DESCRIPTION			 " -- "
		::=  { cellCfgEntry  11 }


	cellSpecialSubSfnPatterns		 OBJECT-TYPE
		SYNTAX					 INTEGER{ ssp0(0),ssp1(1),ssp2(2),ssp3(3),ssp4(4),ssp5(5),ssp6(6),ssp7(7),ssp8(8),ssp9(9)  }
		MAX-ACCESS			 read-create
		STATUS					 current
		DESCRIPTION			 " -- "
		::=  { cellCfgEntry  12 }


	cellMaxTransPwr		 OBJECT-TYPE
		SYNTAX					 Integer32( 0 .. 600 )
		MAX-ACCESS			 read-create
		STATUS					 current
		DESCRIPTION			 " -- "
		::=  { cellCfgEntry  13 }


	cellRsPower		 OBJECT-TYPE
		SYNTAX					 Integer32( -18 .. 24 )
		MAX-ACCESS			 read-create
		STATUS					 current
		DESCRIPTION			 " -- "
		::=  { cellCfgEntry  15 }


	cellPbchPower		 OBJECT-TYPE
		SYNTAX					 Integer32( -6 .. 3 )
		MAX-ACCESS			 read-create
		STATUS					 current
		DESCRIPTION			 " -- "
		::=  { cellCfgEntry  16 }


	cellPschPower		 OBJECT-TYPE
		SYNTAX					 Integer32( -6 .. 3 )
		MAX-ACCESS			 read-create
		STATUS					 current
		DESCRIPTION			 " -- "
		::=  { cellCfgEntry  17 }


	cellSschPower		 OBJECT-TYPE
		SYNTAX					 Integer32( -6 .. 3 )
		MAX-ACCESS			 read-create
		STATUS					 current
		DESCRIPTION			 " -- "
		::=  { cellCfgEntry  18 }


	cellPchPower		 OBJECT-TYPE
		SYNTAX					 Integer32( -6 .. 3 )
		MAX-ACCESS			 read-create
		STATUS					 current
		DESCRIPTION			 " -- "
		::=  { cellCfgEntry  19 }


	cellPdschSibPower		 OBJECT-TYPE
		SYNTAX					 Integer32( -6 .. 9 )
		MAX-ACCESS			 read-create
		STATUS					 current
		DESCRIPTION			 " -- "
		::=  { cellCfgEntry  20 }


	cellPcfichPower		 OBJECT-TYPE
		SYNTAX					 Integer32( -6 .. 7 )
		MAX-ACCESS			 read-create
		STATUS					 current
		DESCRIPTION			 " -- "
		::=  { cellCfgEntry  21 }


	cellPhichPower		 OBJECT-TYPE
		SYNTAX					 Integer32( -6 .. 7 )
		MAX-ACCESS			 read-create
		STATUS					 current
		DESCRIPTION			 " -- "
		::=  { cellCfgEntry  22 }


	cellPdcchPower		 OBJECT-TYPE
		SYNTAX					 Integer32( -6 .. 7 )
		MAX-ACCESS			 read-create
		STATUS					 current
		DESCRIPTION			 " -- "
		::=  { cellCfgEntry  23 }


	cellBarred		 OBJECT-TYPE
		SYNTAX					 INTEGER{ barred(0),notBarred(1)  }
		MAX-ACCESS			 read-create
		STATUS					 current
		DESCRIPTION			 " -- "
		::=  { cellCfgEntry  25 }


	cellSiPageMcs		 OBJECT-TYPE
		SYNTAX					 Integer32( 0 .. 28 )
		MAX-ACCESS			 read-create
		STATUS					 current
		DESCRIPTION			 " -- "
		::=  { cellCfgEntry  27 }


	cellCountMSBcheckValue		 OBJECT-TYPE
		SYNTAX					 Unsigned32( 0 .. 4294967295 )
		MAX-ACCESS			 read-create
		STATUS					 current
		DESCRIPTION			 " -- "
		::=  { cellCfgEntry  28 }


	cellCounterOverturnValue		 OBJECT-TYPE
		SYNTAX					 Unsigned32( 0 .. 4294967295 )
		MAX-ACCESS			 read-create
		STATUS					 current
		DESCRIPTION			 " -- "
		::=  { cellCfgEntry  29 }


	cellCounterCheckErrorThresh		 OBJECT-TYPE
		SYNTAX					 Unsigned32( 0 .. 4294967295 )
		MAX-ACCESS			 read-create
		STATUS					 current
		DESCRIPTION			 " -- "
		::=  { cellCfgEntry  30 }


	cellDwptsForUserDataFlag		 OBJECT-TYPE
		SYNTAX					 INTEGER{ false(0),true(1)  }
		MAX-ACCESS			 read-create
		STATUS					 current
		DESCRIPTION			 " -- "
		::=  { cellCfgEntry  31 }


	cellType		 OBJECT-TYPE
		SYNTAX					 INTEGER{ verysmall(0),small(1),medium(2),large(3)  }
		MAX-ACCESS			 read-create
		STATUS					 current
		DESCRIPTION			 " -- "
		::=  { cellCfgEntry  32 }


	cellAntPortNum		 OBJECT-TYPE
		SYNTAX					 INTEGER{ port1(0),port2(1),port4(2)  }
		MAX-ACCESS			 read-create
		STATUS					 current
		DESCRIPTION			 " -- "
		::=  { cellCfgEntry  33 }


	cellQoffset		 OBJECT-TYPE
		SYNTAX					 INTEGER{ n24dB(0),n22dB(1),n20dB(2),n18dB(3),n16dB(4),n14dB(5),n12dB(6),n10dB(7),n8dB(8),n6dB(9),n5dB(10),n4dB(11),n3dB(12),n2dB(13),n1dB(14),p0dB(15),p1dB(16),p2dB(17),p3dB(18),p4dB(19),p5dB(20),p6dB(21),p8dB(22),p10dB(23),p12dB(24),p14dB(25),p16dB(26),p18dB(27),p20dB(28),p22dB(29),p24dB(30)  }
		MAX-ACCESS			 read-create
		STATUS					 current
		DESCRIPTION			 " -- "
		::=  { cellCfgEntry  34 }


	cellAddtionlSpecEmis		 OBJECT-TYPE
		SYNTAX					 Integer32( 1 .. 32 )
		MAX-ACCESS			 read-create
		STATUS					 current
		DESCRIPTION			 " -- "
		::=  { cellCfgEntry  35 }


	cellCalAcOffset		 OBJECT-TYPE
		SYNTAX					 Unsigned32( 0 .. 65535 )
		MAX-ACCESS			 read-write
		STATUS					 current
		DESCRIPTION			 " -- "
		::=  { cellCfgEntry  37 }


	cellCdlDetailSwitch		 OBJECT-TYPE
		SYNTAX					 INTEGER{ off(0),on(1)  }
		MAX-ACCESS			 read-create
		STATUS					 current
		DESCRIPTION			 " -- "
		::=  { cellCfgEntry  38 }


	cellPdcchCo4CceFormat1cPower		 OBJECT-TYPE
		SYNTAX					 Integer32( -6 .. 7 )
		MAX-ACCESS			 read-create
		STATUS					 current
		DESCRIPTION			 " -- "
		::=  { cellCfgEntry  39 }


	cellPdcchCo4CceOtherFormatPower		 OBJECT-TYPE
		SYNTAX					 Integer32( -6 .. 7 )
		MAX-ACCESS			 read-create
		STATUS					 current
		DESCRIPTION			 " -- "
		::=  { cellCfgEntry  40 }


	cellPdcchCo8CceFormat1cPower		 OBJECT-TYPE
		SYNTAX					 Integer32( -6 .. 7 )
		MAX-ACCESS			 read-create
		STATUS					 current
		DESCRIPTION			 " -- "
		::=  { cellCfgEntry  41 }


	cellPdcchCo8CceOtherFormatPower		 OBJECT-TYPE
		SYNTAX					 Integer32( -6 .. 7 )
		MAX-ACCESS			 read-create
		STATUS					 current
		DESCRIPTION			 " -- "
		::=  { cellCfgEntry  42 }


	cellMsg3PhichPower		 OBJECT-TYPE
		SYNTAX					 Integer32( -6 .. 7 )
		MAX-ACCESS			 read-create
		STATUS					 current
		DESCRIPTION			 " -- "
		::=  { cellCfgEntry  43 }


	cellPriority		 OBJECT-TYPE
		SYNTAX					 INTEGER{ high(0),normal(1)  }
		MAX-ACCESS			 read-create
		STATUS					 current
		DESCRIPTION			 " -- "
		::=  { cellCfgEntry  44 }


	cellCdlServiceSwitch		 OBJECT-TYPE
		SYNTAX					 INTEGER{ off(0),on(1)  }
		MAX-ACCESS			 read-create
		STATUS					 current
		DESCRIPTION			 " -- "
		::=  { cellCfgEntry  45 }


	cellCdlTcpSwitch		 OBJECT-TYPE
		SYNTAX					 INTEGER{ off(0),on(1)  }
		MAX-ACCESS			 read-create
		STATUS					 current
		DESCRIPTION			 " -- "
		::=  { cellCfgEntry  46 }


	cellCellID		 OBJECT-TYPE
		SYNTAX					 Integer32( 0 .. 255 )
		MAX-ACCESS			 read-create
		STATUS					 current
		DESCRIPTION			 " -- "
		::=  { cellCfgEntry  47 }


	cellPowerOffset		 OBJECT-TYPE
		SYNTAX					 Integer32( 0 .. 6 )
		MAX-ACCESS			 read-create
		STATUS					 current
		DESCRIPTION			 " -- "
		::=  { cellCfgEntry  48 }


	cellCRSBoostingSwitch		 OBJECT-TYPE
		SYNTAX					 INTEGER{ off(0),on(1)  }
		MAX-ACCESS			 read-create
		STATUS					 current
		DESCRIPTION			 " -- "
		::=  { cellCfgEntry  49 }


	cellBlackCellsStartPhyId		 OBJECT-TYPE
		SYNTAX					 Integer32( 0 .. 503|65535 )
		MAX-ACCESS			 read-create
		STATUS					 current
		DESCRIPTION			 " -- "
		::=  { cellCfgEntry  50 }


	cellBlackCellsRange		 OBJECT-TYPE
		SYNTAX					 INTEGER{ n4(0),n8(1),n12(2),n16(3),n24(4),n32(5),n48(6),n64(7),n84(8),n96(9),n128(10),n168(11),n252(12),n504(13),spare2(14),spare1(15)  }
		MAX-ACCESS			 read-create
		STATUS					 current
		DESCRIPTION			 " -- "
		::=  { cellCfgEntry  51 }


	cellRsPowerDelta		 OBJECT-TYPE
		SYNTAX					 Integer32( 0 .. 9 )
		MAX-ACCESS			 read-create
		STATUS					 current
		DESCRIPTION			 " -- "
		::=  { cellCfgEntry  52 }


	cellPortID		 OBJECT-TYPE
		SYNTAX					 Integer32( 0 .. 1 )
		MAX-ACCESS			 read-create
		STATUS					 current
		DESCRIPTION			 " -- "
		::=  { cellCfgEntry  55 }


	cellTypeFlag		 OBJECT-TYPE
		SYNTAX					 INTEGER{ sameBBUCell(0),normalCell(1),differBBUCell(2)  }
		MAX-ACCESS			 read-create
		STATUS					 current
		DESCRIPTION			 " -- "
		::=  { cellCfgEntry  57 }


	cellCfgFrameType		 OBJECT-TYPE
		SYNTAX					 INTEGER{ structureFdd(0),structureTdd(1)  }
		MAX-ACCESS			 read-create
		STATUS					 current
		DESCRIPTION			 " -- "
		::=  { cellCfgEntry  58 }


	cellOffsetFreq		 OBJECT-TYPE
		SYNTAX					 INTEGER{ n24dB(0),n22dB(1),n20dB(2),n18dB(3),n16dB(4),n14dB(5),n12dB(6),n10dB(7),n8dB(8),n6dB(9),n5dB(10),n4dB(11),n3dB(12),n2dB(13),n1dB(14),p0dB(15),p1dB(16),p2dB(17),p3dB(18),p4dB(19),p5dB(20),p6dB(21),p8dB(22),p10dB(23),p12dB(24),p14dB(25),p16dB(26),p18dB(27),p20dB(28),p22dB(29),p24dB(30)  }
		MAX-ACCESS			 read-create
		STATUS					 current
		DESCRIPTION			 " -- "
		::=  { cellCfgEntry  61 }


	cellEARFCN		 OBJECT-TYPE
		SYNTAX					 Integer32( 0 .. 65535 )
		MAX-ACCESS			 read-only
		STATUS					 current
		DESCRIPTION			 " -- "
		::=  { cellCfgEntry  62 }


	cellAntTilt		 OBJECT-TYPE
		SYNTAX					 Integer32( 0 .. 3600 )
		MAX-ACCESS			 read-create
		STATUS					 current
		DESCRIPTION			 " -- "
		::=  { cellCfgEntry  63 }


	cellCdlPagingSwitch		 OBJECT-TYPE
		SYNTAX					 INTEGER{ off(0),on(1)  }
		MAX-ACCESS			 read-create
		STATUS					 current
		DESCRIPTION			 " -- "
		::=  { cellCfgEntry  64 }


	cellCdlVoLTESwitch		 OBJECT-TYPE
		SYNTAX					 INTEGER{ off(0),on(1)  }
		MAX-ACCESS			 read-create
		STATUS					 current
		DESCRIPTION			 " -- "
		::=  { cellCfgEntry  65 }


	cellCdlSpeedSwitch		 OBJECT-TYPE
		SYNTAX					 INTEGER{ off(0),on(1)  }
		MAX-ACCESS			 read-create
		STATUS					 current
		DESCRIPTION			 " -- "
		::=  { cellCfgEntry  66 }


	cellAntWeightSwitch		 OBJECT-TYPE
		SYNTAX					 INTEGER{ off(0),on(1)  }
		MAX-ACCESS			 read-write
		STATUS					 current
		DESCRIPTION			 " -- "
		::=  { cellCfgEntry  67 }


	cellDisguiseMaintenceState		 OBJECT-TYPE
		SYNTAX					 INTEGER{ inMaintenance(2),inService(3)  }
		MAX-ACCESS			 read-create
		STATUS					 current
		DESCRIPTION			 " -- "
		::=  { cellCfgEntry  68 }


	cellNetPara		 OBJECT IDENTIFIER
		::=  { networkElementPlanCell  2 }


	cellNetParaTable		 OBJECT-TYPE
		SYNTAX					 SEQUENCE  OF	 CellNetParaEntry
		MAX-ACCESS			 not-accessible
		STATUS					 current
		DESCRIPTION			 " -- "
		::=  { cellNetPara  1 }


	cellNetParaEntry		 OBJECT-TYPE
		SYNTAX					 CellNetParaEntry
		MAX-ACCESS			 not-accessible
		STATUS					 current
		DESCRIPTION			 " -- "
		INDEX						{ cellNetLcId }
		::=  { cellNetParaTable  1 }


	CellNetParaEntry		 ::=  SEQUENCE {
		cellNetLcId					Integer32,
		cellNetRowStatus					RowStatus,
		cellNetTac					Integer32,
		cellNetPlmnMcc					MncMccType,
		cellNetPlmnMnc					MncMccType,
		cellNetResrvForOpUse					INTEGER,
		cellNetImsEmergencyTag					INTEGER
		}


	cellNetLcId		 OBJECT-TYPE
		SYNTAX					 Integer32( 0 .. 23 )
		MAX-ACCESS			 not-accessible
		STATUS					 current
		DESCRIPTION			 " -- "
		::=  { cellNetParaEntry  1 }


	cellNetRowStatus		 OBJECT-TYPE
		SYNTAX					 RowStatus
		MAX-ACCESS			 read-create
		STATUS					 current
		DESCRIPTION			 " -- "
		::=  { cellNetParaEntry  2 }


	cellNetTac		 OBJECT-TYPE
		SYNTAX					 Integer32( 0 .. 65535 )
		MAX-ACCESS			 read-create
		STATUS					 current
		DESCRIPTION			 " -- "
		::=  { cellNetParaEntry  3 }


	cellNetPlmnMcc		 OBJECT-TYPE
		SYNTAX					 MncMccType
		MAX-ACCESS			 read-create
		STATUS					 current
		DESCRIPTION			 " -- "
		::=  { cellNetParaEntry  4 }


	cellNetPlmnMnc		 OBJECT-TYPE
		SYNTAX					 MncMccType
		MAX-ACCESS			 read-create
		STATUS					 current
		DESCRIPTION			 " -- "
		::=  { cellNetParaEntry  5 }


	cellNetResrvForOpUse		 OBJECT-TYPE
		SYNTAX					 INTEGER{ reserved(0),notReserved(1)  }
		MAX-ACCESS			 read-create
		STATUS					 current
		DESCRIPTION			 " -- "
		::=  { cellNetParaEntry  6 }


	cellNetImsEmergencyTag		 OBJECT-TYPE
		SYNTAX					 INTEGER{ false(0),true(1)  }
		MAX-ACCESS			 read-create
		STATUS					 current
		DESCRIPTION			 " -- "
		::=  { cellNetParaEntry  7 }


	netS1InterfaceTable		 OBJECT-TYPE
		SYNTAX					 SEQUENCE  OF	 NetS1InterfaceEntry
		MAX-ACCESS			 not-accessible
		STATUS					 current
		DESCRIPTION			 " -- "
		::=  { cellNetPara  2 }


	netS1InterfaceEntry		 OBJECT-TYPE
		SYNTAX					 NetS1InterfaceEntry
		MAX-ACCESS			 not-accessible
		STATUS					 current
		DESCRIPTION			 " -- "
		INDEX						{ netS1IfIndex }
		::=  { netS1InterfaceTable  1 }


	NetS1InterfaceEntry		 ::=  SEQUENCE {
		netS1IfIndex					Integer32,
		netS1IfRowStatus					RowStatus,
		netS1IfMcc					MncMccType,
		netS1IfMnc					MncMccType,
		netS1IfSctpIndex					Integer32
		}


	netS1IfIndex		 OBJECT-TYPE
		SYNTAX					 Integer32( 0 .. 15 )
		MAX-ACCESS			 not-accessible
		STATUS					 current
		DESCRIPTION			 " -- "
		::=  { netS1InterfaceEntry  1 }


	netS1IfRowStatus		 OBJECT-TYPE
		SYNTAX					 RowStatus
		MAX-ACCESS			 read-create
		STATUS					 current
		DESCRIPTION			 " -- "
		::=  { netS1InterfaceEntry  2 }


	netS1IfMcc		 OBJECT-TYPE
		SYNTAX					 MncMccType
		MAX-ACCESS			 read-create
		STATUS					 current
		DESCRIPTION			 " -- "
		::=  { netS1InterfaceEntry  3 }


	netS1IfMnc		 OBJECT-TYPE
		SYNTAX					 MncMccType
		MAX-ACCESS			 read-create
		STATUS					 current
		DESCRIPTION			 " -- "
		::=  { netS1InterfaceEntry  4 }


	netS1IfSctpIndex		 OBJECT-TYPE
		SYNTAX					 Integer32( 0 .. 81 )
		MAX-ACCESS			 read-create
		STATUS					 current
		DESCRIPTION			 " -- "
		::=  { netS1InterfaceEntry  5 }


	cellSharingNetParaTable		 OBJECT-TYPE
		SYNTAX					 SEQUENCE  OF	 CellSharingNetParaEntry
		MAX-ACCESS			 not-accessible
		STATUS					 current
		DESCRIPTION			 " -- "
		::=  { cellNetPara  3 }


	cellSharingNetParaEntry		 OBJECT-TYPE
		SYNTAX					 CellSharingNetParaEntry
		MAX-ACCESS			 not-accessible
		STATUS					 current
		DESCRIPTION			 " -- "
		INDEX						{ cellShareNetLcId,cellShareNetOperatorIndex }
		::=  { cellSharingNetParaTable  1 }


	CellSharingNetParaEntry		 ::=  SEQUENCE {
		cellShareNetLcId					Integer32,
		cellShareNetOperatorIndex					Integer32,
		cellShareNetRowStatus					RowStatus,
		cellShareNetTac					Integer32,
		cellShareNetMcc					MncMccType,
		cellShareNetMnc					MncMccType,
		cellShareNetReservFlag					INTEGER
		}


	cellShareNetLcId		 OBJECT-TYPE
		SYNTAX					 Integer32( 0 .. 23 )
		MAX-ACCESS			 not-accessible
		STATUS					 current
		DESCRIPTION			 " -- "
		::=  { cellSharingNetParaEntry  1 }


	cellShareNetOperatorIndex		 OBJECT-TYPE
		SYNTAX					 Integer32( 0 .. 4 )
		MAX-ACCESS			 not-accessible
		STATUS					 current
		DESCRIPTION			 " -- "
		::=  { cellSharingNetParaEntry  2 }


	cellShareNetRowStatus		 OBJECT-TYPE
		SYNTAX					 RowStatus
		MAX-ACCESS			 read-create
		STATUS					 current
		DESCRIPTION			 " -- "
		::=  { cellSharingNetParaEntry  3 }


	cellShareNetTac		 OBJECT-TYPE
		SYNTAX					 Integer32( 0 .. 65535 )
		MAX-ACCESS			 read-create
		STATUS					 current
		DESCRIPTION			 " -- "
		::=  { cellSharingNetParaEntry  4 }


	cellShareNetMcc		 OBJECT-TYPE
		SYNTAX					 MncMccType
		MAX-ACCESS			 read-create
		STATUS					 current
		DESCRIPTION			 " -- "
		::=  { cellSharingNetParaEntry  5 }


	cellShareNetMnc		 OBJECT-TYPE
		SYNTAX					 MncMccType
		MAX-ACCESS			 read-create
		STATUS					 current
		DESCRIPTION			 " -- "
		::=  { cellSharingNetParaEntry  6 }


	cellShareNetReservFlag		 OBJECT-TYPE
		SYNTAX					 INTEGER{ reserved(0),notReserved(1)  }
		MAX-ACCESS			 read-create
		STATUS					 current
		DESCRIPTION			 " -- "
		::=  { cellSharingNetParaEntry  7 }


	cellInterFreqInfo		 OBJECT IDENTIFIER
		::=  { networkElementPlanCell  3 }


	cellInterFreqTable		 OBJECT-TYPE
		SYNTAX					 SEQUENCE  OF	 CellInterFreqEntry
		MAX-ACCESS			 not-accessible
		STATUS					 current
		DESCRIPTION			 " -- "
		::=  { cellInterFreqInfo  1 }


	cellInterFreqEntry		 OBJECT-TYPE
		SYNTAX					 CellInterFreqEntry
		MAX-ACCESS			 not-accessible
		STATUS					 current
		DESCRIPTION			 " -- "
		INDEX						{ cellInterFreqLcId,cellInterFreqIndex }
		::=  { cellInterFreqTable  1 }


	CellInterFreqEntry		 ::=  SEQUENCE {
		cellInterFreqLcId					Integer32,
		cellInterFreqIndex					Integer32,
		cellInterFreqRowStatus					RowStatus,
		cellInterFreqBand					INTEGER,
		cellInterFreq					Integer32,
		cellInterFreqRxLevMin					INTEGER,
		cellInterFreqPmax					Integer32,
		cellInterFreqTselection					Integer32,
		cellInterFreqSpeedStateSfMedium					INTEGER,
		cellInterFreqSpeedStateSfHigh					INTEGER,
		cellInterFreqThreshXHigh					INTEGER,
		cellInterFreqThreshXLow					INTEGER,
		cellInterFreqMeasBandWidth					INTEGER,
		cellInterFreqPresenceAntePort1					INTEGER,
		cellInterFreqReselPriorityFlag					INTEGER,
		cellInterFreqReselPriority					Integer32,
		cellInterFreqNeighCellCfg					INTEGER,
		cellInterFreqQOffsetFreq					INTEGER,
		cellInterFreqPmaxFlag					INTEGER,
		cellInterFreqSpeedStateScaleFactorsFlag					INTEGER,
		cellInterFreqQualMinFlag					INTEGER,
		cellInterFreqQualMin					INTEGER,
		cellInterFreqThreshXQFlag					INTEGER,
		cellInterFreqThreshXHighQ					INTEGER,
		cellInterFreqThreshXLowQ					INTEGER,
		cellInterFreqOffsetFreq					INTEGER,
		cellInterEARFCN					Integer32,
		cellInterFreqEvenType					INTEGER,
		cellInterFreqCfgPriForIdle					Integer32,
		cellInterFreqCfgPriForConnect					Integer32,
		cellInterFreqMrLimitForConnect					INTEGER
		}


	cellInterFreqLcId		 OBJECT-TYPE
		SYNTAX					 Integer32( 0 .. 23 )
		MAX-ACCESS			 not-accessible
		STATUS					 current
		DESCRIPTION			 " -- "
		::=  { cellInterFreqEntry  1 }


	cellInterFreqIndex		 OBJECT-TYPE
		SYNTAX					 Integer32( 1 .. 50 )
		MAX-ACCESS			 not-accessible
		STATUS					 current
		DESCRIPTION			 " -- "
		::=  { cellInterFreqEntry  2 }


	cellInterFreqRowStatus		 OBJECT-TYPE
		SYNTAX					 RowStatus
		MAX-ACCESS			 read-create
		STATUS					 current
		DESCRIPTION			 " -- "
		::=  { cellInterFreqEntry  3 }


	cellInterFreqBand		 OBJECT-TYPE
		SYNTAX					 INTEGER{ band1(1),band2(2),band3(3),band4(4),band5(5),band7(7),band8(8),band9(9),band10(10),band11(11),band12(12),band13(13),band14(14),band17(17),band18(18),band19(19),band20(20),band21(21),band22(22),band23(23),band24(24),band25(25),band26(26),band33(33),band34(34),band35(35),band36(36),band37(37),band38(38),band39(39),band40(40),band41(41),band44(44),band61(61),band62(62)  }
		MAX-ACCESS			 read-create
		STATUS					 current
		DESCRIPTION			 " -- "
		::=  { cellInterFreqEntry  4 }


	cellInterFreq		 OBJECT-TYPE
		SYNTAX					 Integer32( 0 .. 65535 )
		MAX-ACCESS			 read-create
		STATUS					 current
		DESCRIPTION			 " -- "
		::=  { cellInterFreqEntry  5 }


	cellInterFreqRxLevMin		 OBJECT-TYPE
		SYNTAX					 INTEGER{ rxLevMinMinusDbm140(0),rxLevMinMinusDbm138(1),rxLevMinMinusDbm136(2),rxLevMinMinusDbm134(3),rxLevMinMinusDbm132(4),rxLevMinMinusDbm130(5),rxLevMinMinusDbm128(6),rxLevMinMinusDbm126(7),rxLevMinMinusDbm124(8),rxLevMinMinusDbm122(9),rxLevMinMinusDbm120(10),rxLevMinMinusDbm118(11),rxLevMinMinusDbm116(12),rxLevMinMinusDbm114(13),rxLevMinMinusDbm112(14),rxLevMinMinusDbm110(15),rxLevMinMinusDbm108(16),rxLevMinMinusDbm106(17),rxLevMinMinusDbm104(18),rxLevMinMinusDbm102(19),rxLevMinMinusDbm100(20),rxLevMinMinusDbm98(21),rxLevMinMinusDbm96(22),rxLevMinMinusDbm94(23),rxLevMinMinusDbm92(24),rxLevMinMinusDbm90(25),rxLevMinMinusDbm88(26),rxLevMinMinusDbm86(27),rxLevMinMinusDbm84(28),rxLevMinMinusDbm82(29),rxLevMinMinusDbm80(30),rxLevMinMinusDbm78(31),rxLevMinMinusDbm76(32),rxLevMinMinusDbm74(33),rxLevMinMinusDbm72(34),rxLevMinMinusDbm70(35),rxLevMinMinusDbm68(36),rxLevMinMinusDbm66(37),rxLevMinMinusDbm64(38),rxLevMinMinusDbm62(39),rxLevMinMinusDbm60(40),rxLevMinMinusDbm58(41),rxLevMinMinusDbm56(42),rxLevMinMinusDbm54(43),rxLevMinMinusDbm52(44),rxLevMinMinusDbm50(45),rxLevMinMinusDbm48(46),rxLevMinMinusDbm46(47),rxLevMinMinusDbm44(48)  }
		MAX-ACCESS			 read-create
		STATUS					 current
		DESCRIPTION			 " -- "
		::=  { cellInterFreqEntry  6 }


	cellInterFreqPmax		 OBJECT-TYPE
		SYNTAX					 Integer32( -30 .. 33 )
		MAX-ACCESS			 read-create
		STATUS					 current
		DESCRIPTION			 " -- "
		::=  { cellInterFreqEntry  7 }


	cellInterFreqTselection		 OBJECT-TYPE
		SYNTAX					 Integer32( 0 .. 7 )
		MAX-ACCESS			 read-create
		STATUS					 current
		DESCRIPTION			 " -- "
		::=  { cellInterFreqEntry  8 }


	cellInterFreqSpeedStateSfMedium		 OBJECT-TYPE
		SYNTAX					 INTEGER{ oDot25(0),oDot5(1),oDot75(2),one(3)  }
		MAX-ACCESS			 read-create
		STATUS					 current
		DESCRIPTION			 " -- "
		::=  { cellInterFreqEntry  9 }


	cellInterFreqSpeedStateSfHigh		 OBJECT-TYPE
		SYNTAX					 INTEGER{ oDot25(0),oDot5(1),oDot75(2),one(3)  }
		MAX-ACCESS			 read-create
		STATUS					 current
		DESCRIPTION			 " -- "
		::=  { cellInterFreqEntry  10 }


	cellInterFreqThreshXHigh		 OBJECT-TYPE
		SYNTAX					 INTEGER{ reselectThresholdDb0(0),reselectThresholdDb2(1),reselectThresholdDb4(2),reselectThresholdDb6(3),reselectThresholdDb8(4),reselectThresholdDb10(5),reselectThresholdDb12(6),reselectThresholdDb14(7),reselectThresholdDb16(8),reselectThresholdDb18(9),reselectThresholdDb20(10),reselectThresholdDb22(11),reselectThresholdDb24(12),reselectThresholdDb26(13),reselectThresholdDb28(14),reselectThresholdDb30(15),reselectThresholdDb32(16),reselectThresholdDb34(17),reselectThresholdDb36(18),reselectThresholdDb38(19),reselectThresholdDb40(20),reselectThresholdDb42(21),reselectThresholdDb44(22),reselectThresholdDb46(23),reselectThresholdDb48(24),reselectThresholdDb50(25),reselectThresholdDb52(26),reselectThresholdDb54(27),reselectThresholdDb56(28),reselectThresholdDb58(29),reselectThresholdDb60(30),reselectThresholdDb62(31)  }
		MAX-ACCESS			 read-create
		STATUS					 current
		DESCRIPTION			 " -- "
		::=  { cellInterFreqEntry  11 }


	cellInterFreqThreshXLow		 OBJECT-TYPE
		SYNTAX					 INTEGER{ reselectThresholdDb0(0),reselectThresholdDb2(1),reselectThresholdDb4(2),reselectThresholdDb6(3),reselectThresholdDb8(4),reselectThresholdDb10(5),reselectThresholdDb12(6),reselectThresholdDb14(7),reselectThresholdDb16(8),reselectThresholdDb18(9),reselectThresholdDb20(10),reselectThresholdDb22(11),reselectThresholdDb24(12),reselectThresholdDb26(13),reselectThresholdDb28(14),reselectThresholdDb30(15),reselectThresholdDb32(16),reselectThresholdDb34(17),reselectThresholdDb36(18),reselectThresholdDb38(19),reselectThresholdDb40(20),reselectThresholdDb42(21),reselectThresholdDb44(22),reselectThresholdDb46(23),reselectThresholdDb48(24),reselectThresholdDb50(25),reselectThresholdDb52(26),reselectThresholdDb54(27),reselectThresholdDb56(28),reselectThresholdDb58(29),reselectThresholdDb60(30),reselectThresholdDb62(31)  }
		MAX-ACCESS			 read-create
		STATUS					 current
		DESCRIPTION			 " -- "
		::=  { cellInterFreqEntry  12 }


	cellInterFreqMeasBandWidth		 OBJECT-TYPE
		SYNTAX					 INTEGER{ val1dot4(0),val3(1),val5(2),val10(3),val15(4),val20(5)  }
		MAX-ACCESS			 read-create
		STATUS					 current
		DESCRIPTION			 " -- "
		::=  { cellInterFreqEntry  13 }


	cellInterFreqPresenceAntePort1		 OBJECT-TYPE
		SYNTAX					 INTEGER{ false(0),true(1)  }
		MAX-ACCESS			 read-create
		STATUS					 current
		DESCRIPTION			 " -- "
		::=  { cellInterFreqEntry  14 }


	cellInterFreqReselPriorityFlag		 OBJECT-TYPE
		SYNTAX					 INTEGER{ false(0),true(1)  }
		MAX-ACCESS			 read-create
		STATUS					 current
		DESCRIPTION			 " -- "
		::=  { cellInterFreqEntry  15 }


	cellInterFreqReselPriority		 OBJECT-TYPE
		SYNTAX					 Integer32( 0 .. 7 )
		MAX-ACCESS			 read-create
		STATUS					 current
		DESCRIPTION			 " -- "
		::=  { cellInterFreqEntry  16 }


	cellInterFreqNeighCellCfg		 OBJECT-TYPE
		SYNTAX					 INTEGER{ neighcellcfg00(0),neighcellcfg01(1),neighcellcfg10(2),neighcellcfg11(3)  }
		MAX-ACCESS			 read-create
		STATUS					 current
		DESCRIPTION			 " -- "
		::=  { cellInterFreqEntry  17 }


	cellInterFreqQOffsetFreq		 OBJECT-TYPE
		SYNTAX					 INTEGER{ n24dB(0),n22dB(1),n20dB(2),n18dB(3),n16dB(4),n14dB(5),n12dB(6),n10dB(7),n8dB(8),n6dB(9),n5dB(10),n4dB(11),n3dB(12),n2dB(13),n1dB(14),p0dB(15),p1dB(16),p2dB(17),p3dB(18),p4dB(19),p5dB(20),p6dB(21),p8dB(22),p10dB(23),p12dB(24),p14dB(25),p16dB(26),p18dB(27),p20dB(28),p22dB(29),p24dB(30)  }
		MAX-ACCESS			 read-create
		STATUS					 current
		DESCRIPTION			 " -- "
		::=  { cellInterFreqEntry  18 }


	cellInterFreqPmaxFlag		 OBJECT-TYPE
		SYNTAX					 INTEGER{ false(0),true(1)  }
		MAX-ACCESS			 read-create
		STATUS					 current
		DESCRIPTION			 " -- "
		::=  { cellInterFreqEntry  19 }


	cellInterFreqSpeedStateScaleFactorsFlag		 OBJECT-TYPE
		SYNTAX					 INTEGER{ false(0),true(1)  }
		MAX-ACCESS			 read-create
		STATUS					 current
		DESCRIPTION			 " -- "
		::=  { cellInterFreqEntry  20 }


	cellInterFreqQualMinFlag		 OBJECT-TYPE
		SYNTAX					 INTEGER{ false(0),true(1)  }
		MAX-ACCESS			 read-create
		STATUS					 current
		DESCRIPTION			 " -- "
		::=  { cellInterFreqEntry  21 }


	cellInterFreqQualMin		 OBJECT-TYPE
		SYNTAX					 INTEGER{ qualMinMinusDb34(0),qualMinMinusDb33(1),qualMinMinusDb32(2),qualMinMinusDb31(3),qualMinMinusDb30(4),qualMinMinusDb29(5),qualMinMinusDb28(6),qualMinMinusDb27(7),qualMinMinusDb26(8),qualMinMinusDb25(9),qualMinMinusDb24(10),qualMinMinusDb23(11),qualMinMinusDb22(12),qualMinMinusDb21(13),qualMinMinusDb20(14),qualMinMinusDb19(15),qualMinMinusDb18(16),qualMinMinusDb17(17),qualMinMinusDb16(18),qualMinMinusDb15(19),qualMinMinusDb14(20),qualMinMinusDb13(21),qualMinMinusDb12(22),qualMinMinusDb11(23),qualMinMinusDb10(24),qualMinMinusDb9(25),qualMinMinusDb8(26),qualMinMinusDb7(27),qualMinMinusDb6(28),qualMinMinusDb5(29),qualMinMinusDb4(30),qualMinMinusDb3(31)  }
		MAX-ACCESS			 read-create
		STATUS					 current
		DESCRIPTION			 " -- "
		::=  { cellInterFreqEntry  22 }


	cellInterFreqThreshXQFlag		 OBJECT-TYPE
		SYNTAX					 INTEGER{ false(0),true(1)  }
		MAX-ACCESS			 read-create
		STATUS					 current
		DESCRIPTION			 " -- "
		::=  { cellInterFreqEntry  23 }


	cellInterFreqThreshXHighQ		 OBJECT-TYPE
		SYNTAX					 INTEGER{ reselectThresholdDb0(0),reselectThresholdDb1(1),reselectThresholdDb2(2),reselectThresholdDb3(3),reselectThresholdDb4(4),reselectThresholdDb5(5),reselectThresholdDb6(6),reselectThresholdDb7(7),reselectThresholdDb8(8),reselectThresholdDb9(9),reselectThresholdDb10(10),reselectThresholdDb11(11),reselectThresholdDb12(12),reselectThresholdDb13(13),reselectThresholdDb14(14),reselectThresholdDb15(15),reselectThresholdDb16(16),reselectThresholdDb17(17),reselectThresholdDb18(18),reselectThresholdDb19(19),reselectThresholdDb20(20),reselectThresholdDb21(21),reselectThresholdDb22(22),reselectThresholdDb23(23),reselectThresholdDb24(24),reselectThresholdDb25(25),reselectThresholdDb26(26),reselectThresholdDb27(27),reselectThresholdDb28(28),reselectThresholdDb29(29),reselectThresholdDb30(30),reselectThresholdDb31(31)  }
		MAX-ACCESS			 read-create
		STATUS					 current
		DESCRIPTION			 " -- "
		::=  { cellInterFreqEntry  24 }


	cellInterFreqThreshXLowQ		 OBJECT-TYPE
		SYNTAX					 INTEGER{ reselectThresholdDb0(0),reselectThresholdDb1(1),reselectThresholdDb2(2),reselectThresholdDb3(3),reselectThresholdDb4(4),reselectThresholdDb5(5),reselectThresholdDb6(6),reselectThresholdDb7(7),reselectThresholdDb8(8),reselectThresholdDb9(9),reselectThresholdDb10(10),reselectThresholdDb11(11),reselectThresholdDb12(12),reselectThresholdDb13(13),reselectThresholdDb14(14),reselectThresholdDb15(15),reselectThresholdDb16(16),reselectThresholdDb17(17),reselectThresholdDb18(18),reselectThresholdDb19(19),reselectThresholdDb20(20),reselectThresholdDb21(21),reselectThresholdDb22(22),reselectThresholdDb23(23),reselectThresholdDb24(24),reselectThresholdDb25(25),reselectThresholdDb26(26),reselectThresholdDb27(27),reselectThresholdDb28(28),reselectThresholdDb29(29),reselectThresholdDb30(30),reselectThresholdDb31(31)  }
		MAX-ACCESS			 read-create
		STATUS					 current
		DESCRIPTION			 " -- "
		::=  { cellInterFreqEntry  25 }


	cellInterFreqOffsetFreq		 OBJECT-TYPE
		SYNTAX					 INTEGER{ n24dB(0),n22dB(1),n20dB(2),n18dB(3),n16dB(4),n14dB(5),n12dB(6),n10dB(7),n8dB(8),n6dB(9),n5dB(10),n4dB(11),n3dB(12),n2dB(13),n1dB(14),p0dB(15),p1dB(16),p2dB(17),p3dB(18),p4dB(19),p5dB(20),p6dB(21),p8dB(22),p10dB(23),p12dB(24),p14dB(25),p16dB(26),p18dB(27),p20dB(28),p22dB(29),p24dB(30)  }
		MAX-ACCESS			 read-create
		STATUS					 current
		DESCRIPTION			 " -- "
		::=  { cellInterFreqEntry  28 }


	cellInterEARFCN		 OBJECT-TYPE
		SYNTAX					 Integer32( 0 .. 65535 )
		MAX-ACCESS			 read-only
		STATUS					 current
		DESCRIPTION			 " -- "
		::=  { cellInterFreqEntry  29 }


	cellInterFreqEvenType		 OBJECT-TYPE
		SYNTAX					 INTEGER{ invalid(0),a3(1),a4(2),a5(3)  }
		MAX-ACCESS			 read-create
		STATUS					 current
		DESCRIPTION			 " -- "
		::=  { cellInterFreqEntry  30 }


	cellInterFreqCfgPriForIdle		 OBJECT-TYPE
		SYNTAX					 Integer32( 0 .. 255 )
		MAX-ACCESS			 read-create
		STATUS					 current
		DESCRIPTION			 " -- "
		::=  { cellInterFreqEntry  31 }


	cellInterFreqCfgPriForConnect		 OBJECT-TYPE
		SYNTAX					 Integer32( 1 .. 255 )
		MAX-ACCESS			 read-create
		STATUS					 current
		DESCRIPTION			 " -- "
		::=  { cellInterFreqEntry  32 }


	cellInterFreqMrLimitForConnect		 OBJECT-TYPE
		SYNTAX					 INTEGER{ period(0),event(1),both(2),none(3)  }
		MAX-ACCESS			 read-create
		STATUS					 current
		DESCRIPTION			 " -- "
		::=  { cellInterFreqEntry  33 }


	cellUtraFreqTable		 OBJECT-TYPE
		SYNTAX					 SEQUENCE  OF	 CellUtraFreqEntry
		MAX-ACCESS			 not-accessible
		STATUS					 current
		DESCRIPTION			 " -- "
		::=  { cellInterFreqInfo  2 }


	cellUtraFreqEntry		 OBJECT-TYPE
		SYNTAX					 CellUtraFreqEntry
		MAX-ACCESS			 not-accessible
		STATUS					 current
		DESCRIPTION			 " -- "
		INDEX						{ cellUtraFreqLcId,cellUtraFreqIndex }
		::=  { cellUtraFreqTable  1 }


	CellUtraFreqEntry		 ::=  SEQUENCE {
		cellUtraFreqLcId					Integer32,
		cellUtraFreqIndex					Integer32,
		cellUtraFreqRowStatus					RowStatus,
		cellUtraFreqDuplexType					INTEGER,
		cellUtraFreqCarrierFreq					Integer32,
		cellUtraFreqCellReselectionPriorityFlag					INTEGER,
		cellUtraFreqCellReselectionPriority					Integer32,
		cellUtraFreqThreshxHigh					INTEGER,
		cellUtraFreqThreshxLow					INTEGER,
		cellUtraFreqQRxLevMin					INTEGER,
		cellUtraFreqPMaxUtra					Integer32,
		cellUtraFreqQualMin					Integer32,
		cellUtraFreqQoffset					Integer32
		}


	cellUtraFreqLcId		 OBJECT-TYPE
		SYNTAX					 Integer32( 0 .. 23 )
		MAX-ACCESS			 not-accessible
		STATUS					 current
		DESCRIPTION			 " -- "
		::=  { cellUtraFreqEntry  1 }


	cellUtraFreqIndex		 OBJECT-TYPE
		SYNTAX					 Integer32( 1 .. 50 )
		MAX-ACCESS			 not-accessible
		STATUS					 current
		DESCRIPTION			 " -- "
		::=  { cellUtraFreqEntry  2 }


	cellUtraFreqRowStatus		 OBJECT-TYPE
		SYNTAX					 RowStatus
		MAX-ACCESS			 read-create
		STATUS					 current
		DESCRIPTION			 " -- "
		::=  { cellUtraFreqEntry  3 }


	cellUtraFreqDuplexType		 OBJECT-TYPE
		SYNTAX					 INTEGER{ tdd(0),fdd(1)  }
		MAX-ACCESS			 read-create
		STATUS					 current
		DESCRIPTION			 " -- "
		::=  { cellUtraFreqEntry  4 }


	cellUtraFreqCarrierFreq		 OBJECT-TYPE
		SYNTAX					 Integer32( 0 .. 16383 )
		MAX-ACCESS			 read-create
		STATUS					 current
		DESCRIPTION			 " -- "
		::=  { cellUtraFreqEntry  5 }


	cellUtraFreqCellReselectionPriorityFlag		 OBJECT-TYPE
		SYNTAX					 INTEGER{ false(0),true(1)  }
		MAX-ACCESS			 read-create
		STATUS					 current
		DESCRIPTION			 " -- "
		::=  { cellUtraFreqEntry  6 }


	cellUtraFreqCellReselectionPriority		 OBJECT-TYPE
		SYNTAX					 Integer32( 0 .. 7 )
		MAX-ACCESS			 read-create
		STATUS					 current
		DESCRIPTION			 " -- "
		::=  { cellUtraFreqEntry  7 }


	cellUtraFreqThreshxHigh		 OBJECT-TYPE
		SYNTAX					 INTEGER{ reselectThresholdDb0(0),reselectThresholdDb2(1),reselectThresholdDb4(2),reselectThresholdDb6(3),reselectThresholdDb8(4),reselectThresholdDb10(5),reselectThresholdDb12(6),reselectThresholdDb14(7),reselectThresholdDb16(8),reselectThresholdDb18(9),reselectThresholdDb20(10),reselectThresholdDb22(11),reselectThresholdDb24(12),reselectThresholdDb26(13),reselectThresholdDb28(14),reselectThresholdDb30(15),reselectThresholdDb32(16),reselectThresholdDb34(17),reselectThresholdDb36(18),reselectThresholdDb38(19),reselectThresholdDb40(20),reselectThresholdDb42(21),reselectThresholdDb44(22),reselectThresholdDb46(23),reselectThresholdDb48(24),reselectThresholdDb50(25),reselectThresholdDb52(26),reselectThresholdDb54(27),reselectThresholdDb56(28),reselectThresholdDb58(29),reselectThresholdDb60(30),reselectThresholdDb62(31)  }
		MAX-ACCESS			 read-create
		STATUS					 current
		DESCRIPTION			 " -- "
		::=  { cellUtraFreqEntry  8 }


	cellUtraFreqThreshxLow		 OBJECT-TYPE
		SYNTAX					 INTEGER{ reselectThresholdDb0(0),reselectThresholdDb2(1),reselectThresholdDb4(2),reselectThresholdDb6(3),reselectThresholdDb8(4),reselectThresholdDb10(5),reselectThresholdDb12(6),reselectThresholdDb14(7),reselectThresholdDb16(8),reselectThresholdDb18(9),reselectThresholdDb20(10),reselectThresholdDb22(11),reselectThresholdDb24(12),reselectThresholdDb26(13),reselectThresholdDb28(14),reselectThresholdDb30(15),reselectThresholdDb32(16),reselectThresholdDb34(17),reselectThresholdDb36(18),reselectThresholdDb38(19),reselectThresholdDb40(20),reselectThresholdDb42(21),reselectThresholdDb44(22),reselectThresholdDb46(23),reselectThresholdDb48(24),reselectThresholdDb50(25),reselectThresholdDb52(26),reselectThresholdDb54(27),reselectThresholdDb56(28),reselectThresholdDb58(29),reselectThresholdDb60(30),reselectThresholdDb62(31)  }
		MAX-ACCESS			 read-create
		STATUS					 current
		DESCRIPTION			 " -- "
		::=  { cellUtraFreqEntry  9 }


	cellUtraFreqQRxLevMin		 OBJECT-TYPE
		SYNTAX					 INTEGER{ qrxlevminMinus119(0),qrxlevminMinus117(1),qrxlevminMinus115(2),qrxlevminMinus113(3),qrxlevminMinus111(4),qrxlevminMinus109(5),qrxlevminMinus107(6),qrxlevminMinus105(7),qrxlevminMinus103(8),qrxlevminMinus101(9),qrxlevminMinus99(10),qrxlevminMinus97(11),qrxlevminMinus95(12),qrxlevminMinus93(13),qrxlevminMinus91(14),qrxlevminMinus89(15),qrxlevminMinus87(16),qrxlevminMinus85(17),qrxlevminMinus83(18),qrxlevminMinus81(19),qrxlevminMinus79(20),qrxlevminMinus77(21),qrxlevminMinus75(22),qrxlevminMinus73(23),qrxlevminMinus71(24),qrxlevminMinus69(25),qrxlevminMinus67(26),qrxlevminMinus65(27),qrxlevminMinus63(28),qrxlevminMinus61(29),qrxlevminMinus59(30),qrxlevminMinus57(31),qrxlevminMinus55(32),qrxlevminMinus53(33),qrxlevminMinus51(34),qrxlevminMinus49(35),qrxlevminMinus47(36),qrxlevminMinus45(37),qrxlevminMinus43(38),qrxlevminMinus41(39),qrxlevminMinus39(40),qrxlevminMinus37(41),qrxlevminMinus35(42),qrxlevminMinus33(43),qrxlevminMinus31(44),qrxlevminMinus29(45),qrxlevminMinus27(46),qrxlevminMinus25(47)  }
		MAX-ACCESS			 read-create
		STATUS					 current
		DESCRIPTION			 " -- "
		::=  { cellUtraFreqEntry  10 }


	cellUtraFreqPMaxUtra		 OBJECT-TYPE
		SYNTAX					 Integer32( -50 .. 33 )
		MAX-ACCESS			 read-create
		STATUS					 current
		DESCRIPTION			 " -- "
		::=  { cellUtraFreqEntry  11 }


	cellUtraFreqQualMin		 OBJECT-TYPE
		SYNTAX					 Integer32( -20 .. 0 )
		MAX-ACCESS			 read-create
		STATUS					 current
		DESCRIPTION			 " -- "
		::=  { cellUtraFreqEntry  12 }


	cellUtraFreqQoffset		 OBJECT-TYPE
		SYNTAX					 Integer32( -15 .. 15 )
		MAX-ACCESS			 read-create
		STATUS					 current
		DESCRIPTION			 " -- "
		::=  { cellUtraFreqEntry  13 }


	cellGeranFreqTable		 OBJECT-TYPE
		SYNTAX					 SEQUENCE  OF	 CellGeranFreqEntry
		MAX-ACCESS			 not-accessible
		STATUS					 current
		DESCRIPTION			 " -- "
		::=  { cellInterFreqInfo  3 }


	cellGeranFreqEntry		 OBJECT-TYPE
		SYNTAX					 CellGeranFreqEntry
		MAX-ACCESS			 not-accessible
		STATUS					 current
		DESCRIPTION			 " -- "
		INDEX						{ cellGeranFreqLcId,cellGeranFreqIndex }
		::=  { cellGeranFreqTable  1 }


	CellGeranFreqEntry		 ::=  SEQUENCE {
		cellGeranFreqLcId					Integer32,
		cellGeranFreqIndex					Integer32,
		cellGeranFreqRowStatus					RowStatus,
		cellGeranFreqStartingArfcn					Integer32,
		cellGeranFreqGeranBandIndicator					INTEGER,
		cellGeranFreqFollowingArfcnsChoice					INTEGER,
		cellGeranFreqExplicitArfcns1					Integer32,
		cellGeranFreqExplicitArfcns2					Integer32,
		cellGeranFreqExplicitArfcns3					Integer32,
		cellGeranFreqExplicitArfcns4					Integer32,
		cellGeranFreqExplicitArfcns5					Integer32,
		cellGeranFreqExplicitArfcns6					Integer32,
		cellGeranFreqExplicitArfcns7					Integer32,
		cellGeranFreqExplicitArfcns8					Integer32,
		cellGeranFreqExplicitArfcns9					Integer32,
		cellGeranFreqExplicitArfcns10					Integer32,
		cellGeranFreqExplicitArfcns11					Integer32,
		cellGeranFreqExplicitArfcns12					Integer32,
		cellGeranFreqExplicitArfcns13					Integer32,
		cellGeranFreqExplicitArfcns14					Integer32,
		cellGeranFreqExplicitArfcns15					Integer32,
		cellGeranFreqExplicitArfcns16					Integer32,
		cellGeranFreqExplicitArfcns17					Integer32,
		cellGeranFreqExplicitArfcns18					Integer32,
		cellGeranFreqExplicitArfcns19					Integer32,
		cellGeranFreqExplicitArfcns20					Integer32,
		cellGeranFreqExplicitArfcns21					Integer32,
		cellGeranFreqExplicitArfcns22					Integer32,
		cellGeranFreqExplicitArfcns23					Integer32,
		cellGeranFreqExplicitArfcns24					Integer32,
		cellGeranFreqExplicitArfcns25					Integer32,
		cellGeranFreqExplicitArfcns26					Integer32,
		cellGeranFreqExplicitArfcns27					Integer32,
		cellGeranFreqExplicitArfcns28					Integer32,
		cellGeranFreqExplicitArfcns29					Integer32,
		cellGeranFreqExplicitArfcns30					Integer32,
		cellGeranFreqExplicitArfcns31					Integer32,
		cellGeranFreqArfcnSpacing					Integer32,
		cellGeranFreqNumberOfFollowingArfcns					Integer32,
		cellGeranFreqNumberOfVarialbeBitMapArfcns					Integer32,
		cellGeranFreqVariableBitMapOfArfcns1					Integer32,
		cellGeranFreqVariableBitMapOfArfcns2					Integer32,
		cellGeranFreqVariableBitMapOfArfcns3					Integer32,
		cellGeranFreqVariableBitMapOfArfcns4					Integer32,
		cellGeranFreqVariableBitMapOfArfcns5					Integer32,
		cellGeranFreqVariableBitMapOfArfcns6					Integer32,
		cellGeranFreqVariableBitMapOfArfcns7					Integer32,
		cellGeranFreqVariableBitMapOfArfcns8					Integer32,
		cellGeranFreqVariableBitMapOfArfcns9					Integer32,
		cellGeranFreqVariableBitMapOfArfcns10					Integer32,
		cellGeranFreqVariableBitMapOfArfcns11					Integer32,
		cellGeranFreqVariableBitMapOfArfcns12					Integer32,
		cellGeranFreqVariableBitMapOfArfcns13					Integer32,
		cellGeranFreqVariableBitMapOfArfcns14					Integer32,
		cellGeranFreqVariableBitMapOfArfcns15					Integer32,
		cellGeranFreqVariableBitMapOfArfcns16					Integer32,
		cellGeranFreqCellReselectionPriorityFlag					INTEGER,
		cellGeranFreqCellReselectionPriority					Integer32,
		cellGeranFreqNccPermitted					Integer32,
		cellGeranFreqQRxLevMin					Integer32,
		cellGeranFreqPMaxGeranFlag					INTEGER,
		cellGeranFreqPMaxGeran					Integer32,
		cellGeranFreqThreshxHigh					INTEGER,
		cellGeranFreqThreshxLow					INTEGER,
		cellGeranFreqQoffset					Integer32
		}


	cellGeranFreqLcId		 OBJECT-TYPE
		SYNTAX					 Integer32( 0 .. 23 )
		MAX-ACCESS			 not-accessible
		STATUS					 current
		DESCRIPTION			 " -- "
		::=  { cellGeranFreqEntry  1 }


	cellGeranFreqIndex		 OBJECT-TYPE
		SYNTAX					 Integer32( 1 .. 50 )
		MAX-ACCESS			 not-accessible
		STATUS					 current
		DESCRIPTION			 " -- "
		::=  { cellGeranFreqEntry  2 }


	cellGeranFreqRowStatus		 OBJECT-TYPE
		SYNTAX					 RowStatus
		MAX-ACCESS			 read-create
		STATUS					 current
		DESCRIPTION			 " -- "
		::=  { cellGeranFreqEntry  3 }


	cellGeranFreqStartingArfcn		 OBJECT-TYPE
		SYNTAX					 Integer32( 0 .. 1023 )
		MAX-ACCESS			 read-create
		STATUS					 current
		DESCRIPTION			 " -- "
		::=  { cellGeranFreqEntry  4 }


	cellGeranFreqGeranBandIndicator		 OBJECT-TYPE
		SYNTAX					 INTEGER{ dcsl800(0),dcsl900(1)  }
		MAX-ACCESS			 read-create
		STATUS					 current
		DESCRIPTION			 " -- "
		::=  { cellGeranFreqEntry  5 }


	cellGeranFreqFollowingArfcnsChoice		 OBJECT-TYPE
		SYNTAX					 INTEGER{ explicit(1),spacing(2),bitMap(3)  }
		MAX-ACCESS			 read-create
		STATUS					 current
		DESCRIPTION			 " -- "
		::=  { cellGeranFreqEntry  6 }


	cellGeranFreqExplicitArfcns1		 OBJECT-TYPE
		SYNTAX					 Integer32( 0 .. 1023|65535 )
		MAX-ACCESS			 read-create
		STATUS					 current
		DESCRIPTION			 " -- "
		::=  { cellGeranFreqEntry  7 }


	cellGeranFreqExplicitArfcns2		 OBJECT-TYPE
		SYNTAX					 Integer32( 0 .. 1023|65535 )
		MAX-ACCESS			 read-create
		STATUS					 current
		DESCRIPTION			 " -- "
		::=  { cellGeranFreqEntry  8 }


	cellGeranFreqExplicitArfcns3		 OBJECT-TYPE
		SYNTAX					 Integer32( 0 .. 1023|65535 )
		MAX-ACCESS			 read-create
		STATUS					 current
		DESCRIPTION			 " -- "
		::=  { cellGeranFreqEntry  9 }


	cellGeranFreqExplicitArfcns4		 OBJECT-TYPE
		SYNTAX					 Integer32( 0 .. 1023|65535 )
		MAX-ACCESS			 read-create
		STATUS					 current
		DESCRIPTION			 " -- "
		::=  { cellGeranFreqEntry  10 }


	cellGeranFreqExplicitArfcns5		 OBJECT-TYPE
		SYNTAX					 Integer32( 0 .. 1023|65535 )
		MAX-ACCESS			 read-create
		STATUS					 current
		DESCRIPTION			 " -- "
		::=  { cellGeranFreqEntry  11 }


	cellGeranFreqExplicitArfcns6		 OBJECT-TYPE
		SYNTAX					 Integer32( 0 .. 1023|65535 )
		MAX-ACCESS			 read-create
		STATUS					 current
		DESCRIPTION			 " -- "
		::=  { cellGeranFreqEntry  12 }


	cellGeranFreqExplicitArfcns7		 OBJECT-TYPE
		SYNTAX					 Integer32( 0 .. 1023|65535 )
		MAX-ACCESS			 read-create
		STATUS					 current
		DESCRIPTION			 " -- "
		::=  { cellGeranFreqEntry  13 }


	cellGeranFreqExplicitArfcns8		 OBJECT-TYPE
		SYNTAX					 Integer32( 0 .. 1023|65535 )
		MAX-ACCESS			 read-create
		STATUS					 current
		DESCRIPTION			 " -- "
		::=  { cellGeranFreqEntry  14 }


	cellGeranFreqExplicitArfcns9		 OBJECT-TYPE
		SYNTAX					 Integer32( 0 .. 1023|65535 )
		MAX-ACCESS			 read-create
		STATUS					 current
		DESCRIPTION			 " -- "
		::=  { cellGeranFreqEntry  15 }


	cellGeranFreqExplicitArfcns10		 OBJECT-TYPE
		SYNTAX					 Integer32( 0 .. 1023|65535 )
		MAX-ACCESS			 read-create
		STATUS					 current
		DESCRIPTION			 " -- "
		::=  { cellGeranFreqEntry  16 }


	cellGeranFreqExplicitArfcns11		 OBJECT-TYPE
		SYNTAX					 Integer32( 0 .. 1023|65535 )
		MAX-ACCESS			 read-create
		STATUS					 current
		DESCRIPTION			 " -- "
		::=  { cellGeranFreqEntry  17 }


	cellGeranFreqExplicitArfcns12		 OBJECT-TYPE
		SYNTAX					 Integer32( 0 .. 1023|65535 )
		MAX-ACCESS			 read-create
		STATUS					 current
		DESCRIPTION			 " -- "
		::=  { cellGeranFreqEntry  18 }


	cellGeranFreqExplicitArfcns13		 OBJECT-TYPE
		SYNTAX					 Integer32( 0 .. 1023|65535 )
		MAX-ACCESS			 read-create
		STATUS					 current
		DESCRIPTION			 " -- "
		::=  { cellGeranFreqEntry  19 }


	cellGeranFreqExplicitArfcns14		 OBJECT-TYPE
		SYNTAX					 Integer32( 0 .. 1023|65535 )
		MAX-ACCESS			 read-create
		STATUS					 current
		DESCRIPTION			 " -- "
		::=  { cellGeranFreqEntry  20 }


	cellGeranFreqExplicitArfcns15		 OBJECT-TYPE
		SYNTAX					 Integer32( 0 .. 1023|65535 )
		MAX-ACCESS			 read-create
		STATUS					 current
		DESCRIPTION			 " -- "
		::=  { cellGeranFreqEntry  21 }


	cellGeranFreqExplicitArfcns16		 OBJECT-TYPE
		SYNTAX					 Integer32( 0 .. 1023|65535 )
		MAX-ACCESS			 read-create
		STATUS					 current
		DESCRIPTION			 " -- "
		::=  { cellGeranFreqEntry  22 }


	cellGeranFreqExplicitArfcns17		 OBJECT-TYPE
		SYNTAX					 Integer32( 0 .. 1023|65535 )
		MAX-ACCESS			 read-create
		STATUS					 current
		DESCRIPTION			 " -- "
		::=  { cellGeranFreqEntry  23 }


	cellGeranFreqExplicitArfcns18		 OBJECT-TYPE
		SYNTAX					 Integer32( 0 .. 1023|65535 )
		MAX-ACCESS			 read-create
		STATUS					 current
		DESCRIPTION			 " -- "
		::=  { cellGeranFreqEntry  24 }


	cellGeranFreqExplicitArfcns19		 OBJECT-TYPE
		SYNTAX					 Integer32( 0 .. 1023|65535 )
		MAX-ACCESS			 read-create
		STATUS					 current
		DESCRIPTION			 " -- "
		::=  { cellGeranFreqEntry  25 }


	cellGeranFreqExplicitArfcns20		 OBJECT-TYPE
		SYNTAX					 Integer32( 0 .. 1023|65535 )
		MAX-ACCESS			 read-create
		STATUS					 current
		DESCRIPTION			 " -- "
		::=  { cellGeranFreqEntry  26 }


	cellGeranFreqExplicitArfcns21		 OBJECT-TYPE
		SYNTAX					 Integer32( 0 .. 1023|65535 )
		MAX-ACCESS			 read-create
		STATUS					 current
		DESCRIPTION			 " -- "
		::=  { cellGeranFreqEntry  27 }


	cellGeranFreqExplicitArfcns22		 OBJECT-TYPE
		SYNTAX					 Integer32( 0 .. 1023|65535 )
		MAX-ACCESS			 read-create
		STATUS					 current
		DESCRIPTION			 " -- "
		::=  { cellGeranFreqEntry  28 }


	cellGeranFreqExplicitArfcns23		 OBJECT-TYPE
		SYNTAX					 Integer32( 0 .. 1023|65535 )
		MAX-ACCESS			 read-create
		STATUS					 current
		DESCRIPTION			 " -- "
		::=  { cellGeranFreqEntry  29 }


	cellGeranFreqExplicitArfcns24		 OBJECT-TYPE
		SYNTAX					 Integer32( 0 .. 1023|65535 )
		MAX-ACCESS			 read-create
		STATUS					 current
		DESCRIPTION			 " -- "
		::=  { cellGeranFreqEntry  30 }


	cellGeranFreqExplicitArfcns25		 OBJECT-TYPE
		SYNTAX					 Integer32( 0 .. 1023|65535 )
		MAX-ACCESS			 read-create
		STATUS					 current
		DESCRIPTION			 " -- "
		::=  { cellGeranFreqEntry  31 }


	cellGeranFreqExplicitArfcns26		 OBJECT-TYPE
		SYNTAX					 Integer32( 0 .. 1023|65535 )
		MAX-ACCESS			 read-create
		STATUS					 current
		DESCRIPTION			 " -- "
		::=  { cellGeranFreqEntry  32 }


	cellGeranFreqExplicitArfcns27		 OBJECT-TYPE
		SYNTAX					 Integer32( 0 .. 1023|65535 )
		MAX-ACCESS			 read-create
		STATUS					 current
		DESCRIPTION			 " -- "
		::=  { cellGeranFreqEntry  33 }


	cellGeranFreqExplicitArfcns28		 OBJECT-TYPE
		SYNTAX					 Integer32( 0 .. 1023|65535 )
		MAX-ACCESS			 read-create
		STATUS					 current
		DESCRIPTION			 " -- "
		::=  { cellGeranFreqEntry  34 }


	cellGeranFreqExplicitArfcns29		 OBJECT-TYPE
		SYNTAX					 Integer32( 0 .. 1023|65535 )
		MAX-ACCESS			 read-create
		STATUS					 current
		DESCRIPTION			 " -- "
		::=  { cellGeranFreqEntry  35 }


	cellGeranFreqExplicitArfcns30		 OBJECT-TYPE
		SYNTAX					 Integer32( 0 .. 1023|65535 )
		MAX-ACCESS			 read-create
		STATUS					 current
		DESCRIPTION			 " -- "
		::=  { cellGeranFreqEntry  36 }


	cellGeranFreqExplicitArfcns31		 OBJECT-TYPE
		SYNTAX					 Integer32( 0 .. 1023|65535 )
		MAX-ACCESS			 read-create
		STATUS					 current
		DESCRIPTION			 " -- "
		::=  { cellGeranFreqEntry  37 }


	cellGeranFreqArfcnSpacing		 OBJECT-TYPE
		SYNTAX					 Integer32( 1 .. 8 )
		MAX-ACCESS			 read-create
		STATUS					 current
		DESCRIPTION			 " -- "
		::=  { cellGeranFreqEntry  38 }


	cellGeranFreqNumberOfFollowingArfcns		 OBJECT-TYPE
		SYNTAX					 Integer32( 0 .. 31 )
		MAX-ACCESS			 read-create
		STATUS					 current
		DESCRIPTION			 " -- "
		::=  { cellGeranFreqEntry  39 }


	cellGeranFreqNumberOfVarialbeBitMapArfcns		 OBJECT-TYPE
		SYNTAX					 Integer32( 1 .. 16 )
		MAX-ACCESS			 read-create
		STATUS					 current
		DESCRIPTION			 " -- "
		::=  { cellGeranFreqEntry  40 }


	cellGeranFreqVariableBitMapOfArfcns1		 OBJECT-TYPE
		SYNTAX					 Integer32( 0 .. 255 )
		MAX-ACCESS			 read-create
		STATUS					 current
		DESCRIPTION			 " -- "
		::=  { cellGeranFreqEntry  41 }


	cellGeranFreqVariableBitMapOfArfcns2		 OBJECT-TYPE
		SYNTAX					 Integer32( 0 .. 255 )
		MAX-ACCESS			 read-create
		STATUS					 current
		DESCRIPTION			 " -- "
		::=  { cellGeranFreqEntry  42 }


	cellGeranFreqVariableBitMapOfArfcns3		 OBJECT-TYPE
		SYNTAX					 Integer32( 0 .. 255 )
		MAX-ACCESS			 read-create
		STATUS					 current
		DESCRIPTION			 " -- "
		::=  { cellGeranFreqEntry  43 }


	cellGeranFreqVariableBitMapOfArfcns4		 OBJECT-TYPE
		SYNTAX					 Integer32( 0 .. 255 )
		MAX-ACCESS			 read-create
		STATUS					 current
		DESCRIPTION			 " -- "
		::=  { cellGeranFreqEntry  44 }


	cellGeranFreqVariableBitMapOfArfcns5		 OBJECT-TYPE
		SYNTAX					 Integer32( 0 .. 255 )
		MAX-ACCESS			 read-create
		STATUS					 current
		DESCRIPTION			 " -- "
		::=  { cellGeranFreqEntry  45 }


	cellGeranFreqVariableBitMapOfArfcns6		 OBJECT-TYPE
		SYNTAX					 Integer32( 0 .. 255 )
		MAX-ACCESS			 read-create
		STATUS					 current
		DESCRIPTION			 " -- "
		::=  { cellGeranFreqEntry  46 }


	cellGeranFreqVariableBitMapOfArfcns7		 OBJECT-TYPE
		SYNTAX					 Integer32( 0 .. 255 )
		MAX-ACCESS			 read-create
		STATUS					 current
		DESCRIPTION			 " -- "
		::=  { cellGeranFreqEntry  47 }


	cellGeranFreqVariableBitMapOfArfcns8		 OBJECT-TYPE
		SYNTAX					 Integer32( 0 .. 255 )
		MAX-ACCESS			 read-create
		STATUS					 current
		DESCRIPTION			 " -- "
		::=  { cellGeranFreqEntry  48 }


	cellGeranFreqVariableBitMapOfArfcns9		 OBJECT-TYPE
		SYNTAX					 Integer32( 0 .. 255 )
		MAX-ACCESS			 read-create
		STATUS					 current
		DESCRIPTION			 " -- "
		::=  { cellGeranFreqEntry  49 }


	cellGeranFreqVariableBitMapOfArfcns10		 OBJECT-TYPE
		SYNTAX					 Integer32( 0 .. 255 )
		MAX-ACCESS			 read-create
		STATUS					 current
		DESCRIPTION			 " -- "
		::=  { cellGeranFreqEntry  50 }


	cellGeranFreqVariableBitMapOfArfcns11		 OBJECT-TYPE
		SYNTAX					 Integer32( 0 .. 255 )
		MAX-ACCESS			 read-create
		STATUS					 current
		DESCRIPTION			 " -- "
		::=  { cellGeranFreqEntry  51 }


	cellGeranFreqVariableBitMapOfArfcns12		 OBJECT-TYPE
		SYNTAX					 Integer32( 0 .. 255 )
		MAX-ACCESS			 read-create
		STATUS					 current
		DESCRIPTION			 " -- "
		::=  { cellGeranFreqEntry  52 }


	cellGeranFreqVariableBitMapOfArfcns13		 OBJECT-TYPE
		SYNTAX					 Integer32( 0 .. 255 )
		MAX-ACCESS			 read-create
		STATUS					 current
		DESCRIPTION			 " -- "
		::=  { cellGeranFreqEntry  53 }


	cellGeranFreqVariableBitMapOfArfcns14		 OBJECT-TYPE
		SYNTAX					 Integer32( 0 .. 255 )
		MAX-ACCESS			 read-create
		STATUS					 current
		DESCRIPTION			 " -- "
		::=  { cellGeranFreqEntry  54 }


	cellGeranFreqVariableBitMapOfArfcns15		 OBJECT-TYPE
		SYNTAX					 Integer32( 0 .. 255 )
		MAX-ACCESS			 read-create
		STATUS					 current
		DESCRIPTION			 " -- "
		::=  { cellGeranFreqEntry  55 }


	cellGeranFreqVariableBitMapOfArfcns16		 OBJECT-TYPE
		SYNTAX					 Integer32( 0 .. 255 )
		MAX-ACCESS			 read-create
		STATUS					 current
		DESCRIPTION			 " -- "
		::=  { cellGeranFreqEntry  56 }


	cellGeranFreqCellReselectionPriorityFlag		 OBJECT-TYPE
		SYNTAX					 INTEGER{ false(0),true(1)  }
		MAX-ACCESS			 read-create
		STATUS					 current
		DESCRIPTION			 " -- "
		::=  { cellGeranFreqEntry  57 }


	cellGeranFreqCellReselectionPriority		 OBJECT-TYPE
		SYNTAX					 Integer32( 0 .. 7 )
		MAX-ACCESS			 read-create
		STATUS					 current
		DESCRIPTION			 " -- "
		::=  { cellGeranFreqEntry  58 }


	cellGeranFreqNccPermitted		 OBJECT-TYPE
		SYNTAX					 Integer32( 0 .. 255 )
		MAX-ACCESS			 read-create
		STATUS					 current
		DESCRIPTION			 " -- "
		::=  { cellGeranFreqEntry  59 }


	cellGeranFreqQRxLevMin		 OBJECT-TYPE
		SYNTAX					 Integer32( 0 .. 45 )
		MAX-ACCESS			 read-create
		STATUS					 current
		DESCRIPTION			 " -- "
		::=  { cellGeranFreqEntry  60 }


	cellGeranFreqPMaxGeranFlag		 OBJECT-TYPE
		SYNTAX					 INTEGER{ false(0),true(1)  }
		MAX-ACCESS			 read-create
		STATUS					 current
		DESCRIPTION			 " -- "
		::=  { cellGeranFreqEntry  61 }


	cellGeranFreqPMaxGeran		 OBJECT-TYPE
		SYNTAX					 Integer32( 0 .. 39 )
		MAX-ACCESS			 read-create
		STATUS					 current
		DESCRIPTION			 " -- "
		::=  { cellGeranFreqEntry  62 }


	cellGeranFreqThreshxHigh		 OBJECT-TYPE
		SYNTAX					 INTEGER{ reselectThresholdDb0(0),reselectThresholdDb2(1),reselectThresholdDb4(2),reselectThresholdDb6(3),reselectThresholdDb8(4),reselectThresholdDb10(5),reselectThresholdDb12(6),reselectThresholdDb14(7),reselectThresholdDb16(8),reselectThresholdDb18(9),reselectThresholdDb20(10),reselectThresholdDb22(11),reselectThresholdDb24(12),reselectThresholdDb26(13),reselectThresholdDb28(14),reselectThresholdDb30(15),reselectThresholdDb32(16),reselectThresholdDb34(17),reselectThresholdDb36(18),reselectThresholdDb38(19),reselectThresholdDb40(20),reselectThresholdDb42(21),reselectThresholdDb44(22),reselectThresholdDb46(23),reselectThresholdDb48(24),reselectThresholdDb50(25),reselectThresholdDb52(26),reselectThresholdDb54(27),reselectThresholdDb56(28),reselectThresholdDb58(29),reselectThresholdDb60(30),reselectThresholdDb62(31)  }
		MAX-ACCESS			 read-create
		STATUS					 current
		DESCRIPTION			 " -- "
		::=  { cellGeranFreqEntry  63 }


	cellGeranFreqThreshxLow		 OBJECT-TYPE
		SYNTAX					 INTEGER{ reselectThresholdDb0(0),reselectThresholdDb2(1),reselectThresholdDb4(2),reselectThresholdDb6(3),reselectThresholdDb8(4),reselectThresholdDb10(5),reselectThresholdDb12(6),reselectThresholdDb14(7),reselectThresholdDb16(8),reselectThresholdDb18(9),reselectThresholdDb20(10),reselectThresholdDb22(11),reselectThresholdDb24(12),reselectThresholdDb26(13),reselectThresholdDb28(14),reselectThresholdDb30(15),reselectThresholdDb32(16),reselectThresholdDb34(17),reselectThresholdDb36(18),reselectThresholdDb38(19),reselectThresholdDb40(20),reselectThresholdDb42(21),reselectThresholdDb44(22),reselectThresholdDb46(23),reselectThresholdDb48(24),reselectThresholdDb50(25),reselectThresholdDb52(26),reselectThresholdDb54(27),reselectThresholdDb56(28),reselectThresholdDb58(29),reselectThresholdDb60(30),reselectThresholdDb62(31)  }
		MAX-ACCESS			 read-create
		STATUS					 current
		DESCRIPTION			 " -- "
		::=  { cellGeranFreqEntry  64 }


	cellGeranFreqQoffset		 OBJECT-TYPE
		SYNTAX					 Integer32( -15 .. 15 )
		MAX-ACCESS			 read-create
		STATUS					 current
		DESCRIPTION			 " -- "
		::=  { cellGeranFreqEntry  65 }


	cellAdjCdma2000FreqTable		 OBJECT-TYPE
		SYNTAX					 SEQUENCE  OF	 CellAdjCdma2000FreqEntry
		MAX-ACCESS			 not-accessible
		STATUS					 current
		DESCRIPTION			 " -- "
		::=  { cellInterFreqInfo  4 }


	cellAdjCdma2000FreqEntry		 OBJECT-TYPE
		SYNTAX					 CellAdjCdma2000FreqEntry
		MAX-ACCESS			 not-accessible
		STATUS					 current
		DESCRIPTION			 " -- "
		INDEX						{ cellAdjCdma2000FreqLcId,cellAdjCdma2000FreqIndex }
		::=  { cellAdjCdma2000FreqTable  1 }


	CellAdjCdma2000FreqEntry		 ::=  SEQUENCE {
		cellAdjCdma2000FreqLcId					Integer32,
		cellAdjCdma2000FreqIndex					Integer32,
		cellAdjCdma2000FreqRowStatus					RowStatus,
		cellAdjCdma2000FreqBandClass					INTEGER,
		cellAdjCdma2000FreqArfcn					Integer32,
		cellAdjCdma2000FreqType					INTEGER
		}


	cellAdjCdma2000FreqLcId		 OBJECT-TYPE
		SYNTAX					 Integer32( 0 .. 23 )
		MAX-ACCESS			 not-accessible
		STATUS					 current
		DESCRIPTION			 " -- "
		::=  { cellAdjCdma2000FreqEntry  1 }


	cellAdjCdma2000FreqIndex		 OBJECT-TYPE
		SYNTAX					 Integer32( 1 .. 50 )
		MAX-ACCESS			 not-accessible
		STATUS					 current
		DESCRIPTION			 " -- "
		::=  { cellAdjCdma2000FreqEntry  2 }


	cellAdjCdma2000FreqRowStatus		 OBJECT-TYPE
		SYNTAX					 RowStatus
		MAX-ACCESS			 read-create
		STATUS					 current
		DESCRIPTION			 " -- "
		::=  { cellAdjCdma2000FreqEntry  3 }


	cellAdjCdma2000FreqBandClass		 OBJECT-TYPE
		SYNTAX					 INTEGER{ bc0(0),bc1(1),bc2(2),bc3(3),bc4(4),bc5(5),bc6(6),bc7(7),bc8(8),bc9(9),bc10(10),bc11(11),bc12(12),bc13(13),bc14(14),bc15(15),bc16(16),bc17(17)  }
		MAX-ACCESS			 read-create
		STATUS					 current
		DESCRIPTION			 " -- "
		::=  { cellAdjCdma2000FreqEntry  4 }


	cellAdjCdma2000FreqArfcn		 OBJECT-TYPE
		SYNTAX					 Integer32( 0 .. 2047 )
		MAX-ACCESS			 read-create
		STATUS					 current
		DESCRIPTION			 " -- "
		::=  { cellAdjCdma2000FreqEntry  5 }


	cellAdjCdma2000FreqType		 OBJECT-TYPE
		SYNTAX					 INTEGER{ type1XRTT(0),typeHRPD(1)  }
		MAX-ACCESS			 read-create
		STATUS					 current
		DESCRIPTION			 " -- "
		::=  { cellAdjCdma2000FreqEntry  8 }


	cellSelectReselect		 OBJECT IDENTIFIER
		::=  { networkElementPlanCell  4 }


	cellSelectTable		 OBJECT-TYPE
		SYNTAX					 SEQUENCE  OF	 CellSelectEntry
		MAX-ACCESS			 not-accessible
		STATUS					 current
		DESCRIPTION			 " -- "
		::=  { cellSelectReselect  1 }


	cellSelectEntry		 OBJECT-TYPE
		SYNTAX					 CellSelectEntry
		MAX-ACCESS			 not-accessible
		STATUS					 current
		DESCRIPTION			 " -- "
		INDEX						{ cellSelectLcId }
		::=  { cellSelectTable  1 }


	CellSelectEntry		 ::=  SEQUENCE {
		cellSelectLcId					Integer32,
		cellSelectRowStatus					RowStatus,
		cellSelectIntraFreqCellResel					INTEGER,
		cellSelectCsgInd					INTEGER,
		cellSelectCsgIdentityFlag					INTEGER,
		cellSelectCsgIdentity					Unsigned32,
		cellSelectQRxlevMin					INTEGER,
		cellSelectQRxlevMinOffsetFlag					INTEGER,
		cellSelectQRxlevMinOffset					INTEGER,
		cellSelectPmaxFlag					INTEGER,
		cellSelectPmax					Integer32,
		cellSelectQQualMinFlag					INTEGER,
		cellSelectQQualMin					INTEGER,
		cellSelectQQualMinOffsetFlag					INTEGER,
		cellSelectQQualMinOffset					INTEGER
		}


	cellSelectLcId		 OBJECT-TYPE
		SYNTAX					 Integer32( 0 .. 23 )
		MAX-ACCESS			 not-accessible
		STATUS					 current
		DESCRIPTION			 " -- "
		::=  { cellSelectEntry  1 }


	cellSelectRowStatus		 OBJECT-TYPE
		SYNTAX					 RowStatus
		MAX-ACCESS			 read-create
		STATUS					 current
		DESCRIPTION			 " -- "
		::=  { cellSelectEntry  2 }


	cellSelectIntraFreqCellResel		 OBJECT-TYPE
		SYNTAX					 INTEGER{ allowed(0),notAllowed(1)  }
		MAX-ACCESS			 read-create
		STATUS					 current
		DESCRIPTION			 " -- "
		::=  { cellSelectEntry  3 }


	cellSelectCsgInd		 OBJECT-TYPE
		SYNTAX					 INTEGER{ false(0),true(1)  }
		MAX-ACCESS			 read-create
		STATUS					 current
		DESCRIPTION			 " -- "
		::=  { cellSelectEntry  4 }


	cellSelectCsgIdentityFlag		 OBJECT-TYPE
		SYNTAX					 INTEGER{ false(0),true(1)  }
		MAX-ACCESS			 read-create
		STATUS					 current
		DESCRIPTION			 " -- "
		::=  { cellSelectEntry  5 }


	cellSelectCsgIdentity		 OBJECT-TYPE
		SYNTAX					 Unsigned32( 0 .. 134217727 )
		MAX-ACCESS			 read-create
		STATUS					 current
		DESCRIPTION			 " -- "
		::=  { cellSelectEntry  6 }


	cellSelectQRxlevMin		 OBJECT-TYPE
		SYNTAX					 INTEGER{ rxLevMinMinusDbm140(0),rxLevMinMinusDbm138(1),rxLevMinMinusDbm136(2),rxLevMinMinusDbm134(3),rxLevMinMinusDbm132(4),rxLevMinMinusDbm130(5),rxLevMinMinusDbm128(6),rxLevMinMinusDbm126(7),rxLevMinMinusDbm124(8),rxLevMinMinusDbm122(9),rxLevMinMinusDbm120(10),rxLevMinMinusDbm118(11),rxLevMinMinusDbm116(12),rxLevMinMinusDbm114(13),rxLevMinMinusDbm112(14),rxLevMinMinusDbm110(15),rxLevMinMinusDbm108(16),rxLevMinMinusDbm106(17),rxLevMinMinusDbm104(18),rxLevMinMinusDbm102(19),rxLevMinMinusDbm100(20),rxLevMinMinusDbm98(21),rxLevMinMinusDbm96(22),rxLevMinMinusDbm94(23),rxLevMinMinusDbm92(24),rxLevMinMinusDbm90(25),rxLevMinMinusDbm88(26),rxLevMinMinusDbm86(27),rxLevMinMinusDbm84(28),rxLevMinMinusDbm82(29),rxLevMinMinusDbm80(30),rxLevMinMinusDbm78(31),rxLevMinMinusDbm76(32),rxLevMinMinusDbm74(33),rxLevMinMinusDbm72(34),rxLevMinMinusDbm70(35),rxLevMinMinusDbm68(36),rxLevMinMinusDbm66(37),rxLevMinMinusDbm64(38),rxLevMinMinusDbm62(39),rxLevMinMinusDbm60(40),rxLevMinMinusDbm58(41),rxLevMinMinusDbm56(42),rxLevMinMinusDbm54(43),rxLevMinMinusDbm52(44),rxLevMinMinusDbm50(45),rxLevMinMinusDbm48(46),rxLevMinMinusDbm46(47),rxLevMinMinusDbm44(48)  }
		MAX-ACCESS			 read-create
		STATUS					 current
		DESCRIPTION			 " -- "
		::=  { cellSelectEntry  7 }


	cellSelectQRxlevMinOffsetFlag		 OBJECT-TYPE
		SYNTAX					 INTEGER{ false(0),true(1)  }
		MAX-ACCESS			 read-create
		STATUS					 current
		DESCRIPTION			 " -- "
		::=  { cellSelectEntry  8 }


	cellSelectQRxlevMinOffset		 OBJECT-TYPE
		SYNTAX					 INTEGER{ rxLevDb2(0),rxLevDb4(1),rxLevDb6(2),rxLevDb8(3),rxLevDb10(4),rxLevDb12(5),rxLevDb14(6),rxLevDb16(7)  }
		MAX-ACCESS			 read-create
		STATUS					 current
		DESCRIPTION			 " -- "
		::=  { cellSelectEntry  9 }


	cellSelectPmaxFlag		 OBJECT-TYPE
		SYNTAX					 INTEGER{ false(0),true(1)  }
		MAX-ACCESS			 read-create
		STATUS					 current
		DESCRIPTION			 " -- "
		::=  { cellSelectEntry  10 }


	cellSelectPmax		 OBJECT-TYPE
		SYNTAX					 Integer32( -30 .. 33 )
		MAX-ACCESS			 read-create
		STATUS					 current
		DESCRIPTION			 " -- "
		::=  { cellSelectEntry  11 }


	cellSelectQQualMinFlag		 OBJECT-TYPE
		SYNTAX					 INTEGER{ false(0),true(1)  }
		MAX-ACCESS			 read-create
		STATUS					 current
		DESCRIPTION			 " -- "
		::=  { cellSelectEntry  12 }


	cellSelectQQualMin		 OBJECT-TYPE
		SYNTAX					 INTEGER{ qualMinMinusDb34(0),qualMinMinusDb33(1),qualMinMinusDb32(2),qualMinMinusDb31(3),qualMinMinusDb30(4),qualMinMinusDb29(5),qualMinMinusDb28(6),qualMinMinusDb27(7),qualMinMinusDb26(8),qualMinMinusDb25(9),qualMinMinusDb24(10),qualMinMinusDb23(11),qualMinMinusDb22(12),qualMinMinusDb21(13),qualMinMinusDb20(14),qualMinMinusDb19(15),qualMinMinusDb18(16),qualMinMinusDb17(17),qualMinMinusDb16(18),qualMinMinusDb15(19),qualMinMinusDb14(20),qualMinMinusDb13(21),qualMinMinusDb12(22),qualMinMinusDb11(23),qualMinMinusDb10(24),qualMinMinusDb9(25),qualMinMinusDb8(26),qualMinMinusDb7(27),qualMinMinusDb6(28),qualMinMinusDb5(29),qualMinMinusDb4(30),qualMinMinusDb3(31)  }
		MAX-ACCESS			 read-create
		STATUS					 current
		DESCRIPTION			 " -- "
		::=  { cellSelectEntry  13 }


	cellSelectQQualMinOffsetFlag		 OBJECT-TYPE
		SYNTAX					 INTEGER{ false(0),true(1)  }
		MAX-ACCESS			 read-create
		STATUS					 current
		DESCRIPTION			 " -- "
		::=  { cellSelectEntry  14 }


	cellSelectQQualMinOffset		 OBJECT-TYPE
		SYNTAX					 INTEGER{ qualDb1(0),qualDb2(1),qualDb3(2),qualDb4(3),qualDb5(4),qualDb6(5),qualDb7(6),qualDb8(7)  }
		MAX-ACCESS			 read-create
		STATUS					 current
		DESCRIPTION			 " -- "
		::=  { cellSelectEntry  15 }


	cellReselectCommonTable		 OBJECT-TYPE
		SYNTAX					 SEQUENCE  OF	 CellReselectCommonEntry
		MAX-ACCESS			 not-accessible
		STATUS					 current
		DESCRIPTION			 " -- "
		::=  { cellSelectReselect  2 }


	cellReselectCommonEntry		 OBJECT-TYPE
		SYNTAX					 CellReselectCommonEntry
		MAX-ACCESS			 not-accessible
		STATUS					 current
		DESCRIPTION			 " -- "
		INDEX						{ cellReselComLcId }
		::=  { cellReselectCommonTable  1 }


	CellReselectCommonEntry		 ::=  SEQUENCE {
		cellReselComLcId					Integer32,
		cellReselComRowStatus					RowStatus,
		cellReselComQhyst					INTEGER,
		cellReselComSpeedReselFlag					INTEGER,
		cellReselComTCRmax					INTEGER,
		cellReselComTCRmaxHyst					INTEGER,
		cellReselComNCRM					Integer32,
		cellReselComNCRH					Integer32,
		cellReselComScalFactorMediMoblity					INTEGER,
		cellReselComScalFactorHiMoblity					INTEGER,
		cellReselComSNonIntraSearchFlag					INTEGER,
		cellReselComSNonIntraSearch					INTEGER,
		cellReselComThreshServLow					INTEGER,
		cellReselComReselPriorityFlag					INTEGER,
		cellReselComCellReselPriority					Integer32,
		cellReselComSNonIntraSearchR9Flag					INTEGER,
		cellReselComSNonIntraSearchP					INTEGER,
		cellReselComSNonIntraSearchQ					INTEGER,
		cellReselComThreshServLowQFlag					INTEGER,
		cellReselComThreshServLowQ					INTEGER
		}


	cellReselComLcId		 OBJECT-TYPE
		SYNTAX					 Integer32( 0 .. 23 )
		MAX-ACCESS			 not-accessible
		STATUS					 current
		DESCRIPTION			 " -- "
		::=  { cellReselectCommonEntry  1 }


	cellReselComRowStatus		 OBJECT-TYPE
		SYNTAX					 RowStatus
		MAX-ACCESS			 read-create
		STATUS					 current
		DESCRIPTION			 " -- "
		::=  { cellReselectCommonEntry  2 }


	cellReselComQhyst		 OBJECT-TYPE
		SYNTAX					 INTEGER{ dB0(0),dB1(1),dB2(2),dB3(3),dB4(4),dB5(5),dB6(6),dB8(7),dB10(8),dB12(9),dB14(10),dB16(11),dB18(12),dB20(13),dB22(14),dB24(15)  }
		MAX-ACCESS			 read-create
		STATUS					 current
		DESCRIPTION			 " -- "
		::=  { cellReselectCommonEntry  3 }


	cellReselComSpeedReselFlag		 OBJECT-TYPE
		SYNTAX					 INTEGER{ false(0),true(1)  }
		MAX-ACCESS			 read-create
		STATUS					 current
		DESCRIPTION			 " -- "
		::=  { cellReselectCommonEntry  4 }


	cellReselComTCRmax		 OBJECT-TYPE
		SYNTAX					 INTEGER{ s30(0),s60(1),s120(2),s180(3),s240(4)  }
		MAX-ACCESS			 read-create
		STATUS					 current
		DESCRIPTION			 " -- "
		::=  { cellReselectCommonEntry  5 }


	cellReselComTCRmaxHyst		 OBJECT-TYPE
		SYNTAX					 INTEGER{ s30(0),s60(1),s120(2),s180(3),s240(4)  }
		MAX-ACCESS			 read-create
		STATUS					 current
		DESCRIPTION			 " -- "
		::=  { cellReselectCommonEntry  6 }


	cellReselComNCRM		 OBJECT-TYPE
		SYNTAX					 Integer32( 1 .. 16 )
		MAX-ACCESS			 read-create
		STATUS					 current
		DESCRIPTION			 " -- "
		::=  { cellReselectCommonEntry  7 }


	cellReselComNCRH		 OBJECT-TYPE
		SYNTAX					 Integer32( 1 .. 16 )
		MAX-ACCESS			 read-create
		STATUS					 current
		DESCRIPTION			 " -- "
		::=  { cellReselectCommonEntry  8 }


	cellReselComScalFactorMediMoblity		 OBJECT-TYPE
		SYNTAX					 INTEGER{ dBn6(0),dBn4(1),dBn2(2),dB0(3)  }
		MAX-ACCESS			 read-create
		STATUS					 current
		DESCRIPTION			 " -- "
		::=  { cellReselectCommonEntry  9 }


	cellReselComScalFactorHiMoblity		 OBJECT-TYPE
		SYNTAX					 INTEGER{ dBn6(0),dBn4(1),dBn2(2),dB0(3)  }
		MAX-ACCESS			 read-create
		STATUS					 current
		DESCRIPTION			 " -- "
		::=  { cellReselectCommonEntry  10 }


	cellReselComSNonIntraSearchFlag		 OBJECT-TYPE
		SYNTAX					 INTEGER{ false(0),true(1)  }
		MAX-ACCESS			 read-create
		STATUS					 current
		DESCRIPTION			 " -- "
		::=  { cellReselectCommonEntry  11 }


	cellReselComSNonIntraSearch		 OBJECT-TYPE
		SYNTAX					 INTEGER{ reselectThresholdDb0(0),reselectThresholdDb2(1),reselectThresholdDb4(2),reselectThresholdDb6(3),reselectThresholdDb8(4),reselectThresholdDb10(5),reselectThresholdDb12(6),reselectThresholdDb14(7),reselectThresholdDb16(8),reselectThresholdDb18(9),reselectThresholdDb20(10),reselectThresholdDb22(11),reselectThresholdDb24(12),reselectThresholdDb26(13),reselectThresholdDb28(14),reselectThresholdDb30(15),reselectThresholdDb32(16),reselectThresholdDb34(17),reselectThresholdDb36(18),reselectThresholdDb38(19),reselectThresholdDb40(20),reselectThresholdDb42(21),reselectThresholdDb44(22),reselectThresholdDb46(23),reselectThresholdDb48(24),reselectThresholdDb50(25),reselectThresholdDb52(26),reselectThresholdDb54(27),reselectThresholdDb56(28),reselectThresholdDb58(29),reselectThresholdDb60(30),reselectThresholdDb62(31)  }
		MAX-ACCESS			 read-create
		STATUS					 current
		DESCRIPTION			 " -- "
		::=  { cellReselectCommonEntry  12 }


	cellReselComThreshServLow		 OBJECT-TYPE
		SYNTAX					 INTEGER{ reselectThresholdDb0(0),reselectThresholdDb2(1),reselectThresholdDb4(2),reselectThresholdDb6(3),reselectThresholdDb8(4),reselectThresholdDb10(5),reselectThresholdDb12(6),reselectThresholdDb14(7),reselectThresholdDb16(8),reselectThresholdDb18(9),reselectThresholdDb20(10),reselectThresholdDb22(11),reselectThresholdDb24(12),reselectThresholdDb26(13),reselectThresholdDb28(14),reselectThresholdDb30(15),reselectThresholdDb32(16),reselectThresholdDb34(17),reselectThresholdDb36(18),reselectThresholdDb38(19),reselectThresholdDb40(20),reselectThresholdDb42(21),reselectThresholdDb44(22),reselectThresholdDb46(23),reselectThresholdDb48(24),reselectThresholdDb50(25),reselectThresholdDb52(26),reselectThresholdDb54(27),reselectThresholdDb56(28),reselectThresholdDb58(29),reselectThresholdDb60(30),reselectThresholdDb62(31)  }
		MAX-ACCESS			 read-create
		STATUS					 current
		DESCRIPTION			 " -- "
		::=  { cellReselectCommonEntry  13 }


	cellReselComReselPriorityFlag		 OBJECT-TYPE
		SYNTAX					 INTEGER{ false(0),true(1)  }
		MAX-ACCESS			 read-create
		STATUS					 current
		DESCRIPTION			 " -- "
		::=  { cellReselectCommonEntry  14 }


	cellReselComCellReselPriority		 OBJECT-TYPE
		SYNTAX					 Integer32( 0 .. 7 )
		MAX-ACCESS			 read-create
		STATUS					 current
		DESCRIPTION			 " -- "
		::=  { cellReselectCommonEntry  15 }


	cellReselComSNonIntraSearchR9Flag		 OBJECT-TYPE
		SYNTAX					 INTEGER{ false(0),true(1)  }
		MAX-ACCESS			 read-create
		STATUS					 current
		DESCRIPTION			 " -- "
		::=  { cellReselectCommonEntry  16 }


	cellReselComSNonIntraSearchP		 OBJECT-TYPE
		SYNTAX					 INTEGER{ reselectThresholdDb0(0),reselectThresholdDb2(1),reselectThresholdDb4(2),reselectThresholdDb6(3),reselectThresholdDb8(4),reselectThresholdDb10(5),reselectThresholdDb12(6),reselectThresholdDb14(7),reselectThresholdDb16(8),reselectThresholdDb18(9),reselectThresholdDb20(10),reselectThresholdDb22(11),reselectThresholdDb24(12),reselectThresholdDb26(13),reselectThresholdDb28(14),reselectThresholdDb30(15),reselectThresholdDb32(16),reselectThresholdDb34(17),reselectThresholdDb36(18),reselectThresholdDb38(19),reselectThresholdDb40(20),reselectThresholdDb42(21),reselectThresholdDb44(22),reselectThresholdDb46(23),reselectThresholdDb48(24),reselectThresholdDb50(25),reselectThresholdDb52(26),reselectThresholdDb54(27),reselectThresholdDb56(28),reselectThresholdDb58(29),reselectThresholdDb60(30),reselectThresholdDb62(31)  }
		MAX-ACCESS			 read-create
		STATUS					 current
		DESCRIPTION			 " -- "
		::=  { cellReselectCommonEntry  17 }


	cellReselComSNonIntraSearchQ		 OBJECT-TYPE
		SYNTAX					 INTEGER{ reselectThresholdDb0(0),reselectThresholdDb1(1),reselectThresholdDb2(2),reselectThresholdDb3(3),reselectThresholdDb4(4),reselectThresholdDb5(5),reselectThresholdDb6(6),reselectThresholdDb7(7),reselectThresholdDb8(8),reselectThresholdDb9(9),reselectThresholdDb10(10),reselectThresholdDb11(11),reselectThresholdDb12(12),reselectThresholdDb13(13),reselectThresholdDb14(14),reselectThresholdDb15(15),reselectThresholdDb16(16),reselectThresholdDb17(17),reselectThresholdDb18(18),reselectThresholdDb19(19),reselectThresholdDb20(20),reselectThresholdDb21(21),reselectThresholdDb22(22),reselectThresholdDb23(23),reselectThresholdDb24(24),reselectThresholdDb25(25),reselectThresholdDb26(26),reselectThresholdDb27(27),reselectThresholdDb28(28),reselectThresholdDb29(29),reselectThresholdDb30(30),reselectThresholdDb31(31)  }
		MAX-ACCESS			 read-create
		STATUS					 current
		DESCRIPTION			 " -- "
		::=  { cellReselectCommonEntry  18 }


	cellReselComThreshServLowQFlag		 OBJECT-TYPE
		SYNTAX					 INTEGER{ false(0),true(1)  }
		MAX-ACCESS			 read-create
		STATUS					 current
		DESCRIPTION			 " -- "
		::=  { cellReselectCommonEntry  19 }


	cellReselComThreshServLowQ		 OBJECT-TYPE
		SYNTAX					 INTEGER{ reselectThresholdDb0(0),reselectThresholdDb1(1),reselectThresholdDb2(2),reselectThresholdDb3(3),reselectThresholdDb4(4),reselectThresholdDb5(5),reselectThresholdDb6(6),reselectThresholdDb7(7),reselectThresholdDb8(8),reselectThresholdDb9(9),reselectThresholdDb10(10),reselectThresholdDb11(11),reselectThresholdDb12(12),reselectThresholdDb13(13),reselectThresholdDb14(14),reselectThresholdDb15(15),reselectThresholdDb16(16),reselectThresholdDb17(17),reselectThresholdDb18(18),reselectThresholdDb19(19),reselectThresholdDb20(20),reselectThresholdDb21(21),reselectThresholdDb22(22),reselectThresholdDb23(23),reselectThresholdDb24(24),reselectThresholdDb25(25),reselectThresholdDb26(26),reselectThresholdDb27(27),reselectThresholdDb28(28),reselectThresholdDb29(29),reselectThresholdDb30(30),reselectThresholdDb31(31)  }
		MAX-ACCESS			 read-create
		STATUS					 current
		DESCRIPTION			 " -- "
		::=  { cellReselectCommonEntry  20 }


	cellReselectIntraFreqTable		 OBJECT-TYPE
		SYNTAX					 SEQUENCE  OF	 CellReselectIntraFreqEntry
		MAX-ACCESS			 not-accessible
		STATUS					 current
		DESCRIPTION			 " -- "
		::=  { cellSelectReselect  3 }


	cellReselectIntraFreqEntry		 OBJECT-TYPE
		SYNTAX					 CellReselectIntraFreqEntry
		MAX-ACCESS			 not-accessible
		STATUS					 current
		DESCRIPTION			 " -- "
		INDEX						{ cellReselIntraFreqLcId }
		::=  { cellReselectIntraFreqTable  1 }


	CellReselectIntraFreqEntry		 ::=  SEQUENCE {
		cellReselIntraFreqLcId					Integer32,
		cellReselIntraFreqRowStatus					RowStatus,
		cellReselIntraFreqTreselection					Integer32,
		cellReselIntraFreqQrxLevMin					INTEGER,
		cellReselIntraFreqPmaxFlag					INTEGER,
		cellReselIntraFreqPmax					Integer32,
		cellReselIntraFreqIntraSearchFlag					INTEGER,
		cellReselIntraFreqIntraSearch					INTEGER,
		cellReselIntraFreqMeasBandWidthFlag					INTEGER,
		cellReselIntraFreqMeasBandWidth					INTEGER,
		cellReselIntraFreqPresenceAntennaPort1					INTEGER,
		cellReselIntraFreqSpeedStateScaleFactorsFlag					INTEGER,
		cellReselIntraFreqSpeedStateScaleFactorsMedium					INTEGER,
		cellReselIntraFreqSpeedStateScaleFactorsHigh					INTEGER,
		cellReselIntraFreqNeighbCellCfg					INTEGER,
		cellReselIntraFreqIntraSearchR9Flag					INTEGER,
		cellReselIntraFreqIntraSearchP					INTEGER,
		cellReselIntraFreqIntraSearchQ					INTEGER,
		cellReselIntraFreqQualMinFlag					INTEGER,
		cellReselIntraFreqQualMin					INTEGER
		}


	cellReselIntraFreqLcId		 OBJECT-TYPE
		SYNTAX					 Integer32( 0 .. 23 )
		MAX-ACCESS			 not-accessible
		STATUS					 current
		DESCRIPTION			 " -- "
		::=  { cellReselectIntraFreqEntry  1 }


	cellReselIntraFreqRowStatus		 OBJECT-TYPE
		SYNTAX					 RowStatus
		MAX-ACCESS			 read-create
		STATUS					 current
		DESCRIPTION			 " -- "
		::=  { cellReselectIntraFreqEntry  2 }


	cellReselIntraFreqTreselection		 OBJECT-TYPE
		SYNTAX					 Integer32( 0 .. 7 )
		MAX-ACCESS			 read-create
		STATUS					 current
		DESCRIPTION			 " -- "
		::=  { cellReselectIntraFreqEntry  3 }


	cellReselIntraFreqQrxLevMin		 OBJECT-TYPE
		SYNTAX					 INTEGER{ rxLevMinMinusDbm140(0),rxLevMinMinusDbm138(1),rxLevMinMinusDbm136(2),rxLevMinMinusDbm134(3),rxLevMinMinusDbm132(4),rxLevMinMinusDbm130(5),rxLevMinMinusDbm128(6),rxLevMinMinusDbm126(7),rxLevMinMinusDbm124(8),rxLevMinMinusDbm122(9),rxLevMinMinusDbm120(10),rxLevMinMinusDbm118(11),rxLevMinMinusDbm116(12),rxLevMinMinusDbm114(13),rxLevMinMinusDbm112(14),rxLevMinMinusDbm110(15),rxLevMinMinusDbm108(16),rxLevMinMinusDbm106(17),rxLevMinMinusDbm104(18),rxLevMinMinusDbm102(19),rxLevMinMinusDbm100(20),rxLevMinMinusDbm98(21),rxLevMinMinusDbm96(22),rxLevMinMinusDbm94(23),rxLevMinMinusDbm92(24),rxLevMinMinusDbm90(25),rxLevMinMinusDbm88(26),rxLevMinMinusDbm86(27),rxLevMinMinusDbm84(28),rxLevMinMinusDbm82(29),rxLevMinMinusDbm80(30),rxLevMinMinusDbm78(31),rxLevMinMinusDbm76(32),rxLevMinMinusDbm74(33),rxLevMinMinusDbm72(34),rxLevMinMinusDbm70(35),rxLevMinMinusDbm68(36),rxLevMinMinusDbm66(37),rxLevMinMinusDbm64(38),rxLevMinMinusDbm62(39),rxLevMinMinusDbm60(40),rxLevMinMinusDbm58(41),rxLevMinMinusDbm56(42),rxLevMinMinusDbm54(43),rxLevMinMinusDbm52(44),rxLevMinMinusDbm50(45),rxLevMinMinusDbm48(46),rxLevMinMinusDbm46(47),rxLevMinMinusDbm44(48)  }
		MAX-ACCESS			 read-create
		STATUS					 current
		DESCRIPTION			 " -- "
		::=  { cellReselectIntraFreqEntry  4 }


	cellReselIntraFreqPmaxFlag		 OBJECT-TYPE
		SYNTAX					 INTEGER{ false(0),true(1)  }
		MAX-ACCESS			 read-create
		STATUS					 current
		DESCRIPTION			 " -- "
		::=  { cellReselectIntraFreqEntry  5 }


	cellReselIntraFreqPmax		 OBJECT-TYPE
		SYNTAX					 Integer32( -30 .. 33 )
		MAX-ACCESS			 read-create
		STATUS					 current
		DESCRIPTION			 " -- "
		::=  { cellReselectIntraFreqEntry  6 }


	cellReselIntraFreqIntraSearchFlag		 OBJECT-TYPE
		SYNTAX					 INTEGER{ false(0),true(1)  }
		MAX-ACCESS			 read-create
		STATUS					 current
		DESCRIPTION			 " -- "
		::=  { cellReselectIntraFreqEntry  7 }


	cellReselIntraFreqIntraSearch		 OBJECT-TYPE
		SYNTAX					 INTEGER{ reselectThresholdDb0(0),reselectThresholdDb2(1),reselectThresholdDb4(2),reselectThresholdDb6(3),reselectThresholdDb8(4),reselectThresholdDb10(5),reselectThresholdDb12(6),reselectThresholdDb14(7),reselectThresholdDb16(8),reselectThresholdDb18(9),reselectThresholdDb20(10),reselectThresholdDb22(11),reselectThresholdDb24(12),reselectThresholdDb26(13),reselectThresholdDb28(14),reselectThresholdDb30(15),reselectThresholdDb32(16),reselectThresholdDb34(17),reselectThresholdDb36(18),reselectThresholdDb38(19),reselectThresholdDb40(20),reselectThresholdDb42(21),reselectThresholdDb44(22),reselectThresholdDb46(23),reselectThresholdDb48(24),reselectThresholdDb50(25),reselectThresholdDb52(26),reselectThresholdDb54(27),reselectThresholdDb56(28),reselectThresholdDb58(29),reselectThresholdDb60(30),reselectThresholdDb62(31)  }
		MAX-ACCESS			 read-create
		STATUS					 current
		DESCRIPTION			 " -- "
		::=  { cellReselectIntraFreqEntry  8 }


	cellReselIntraFreqMeasBandWidthFlag		 OBJECT-TYPE
		SYNTAX					 INTEGER{ false(0),true(1)  }
		MAX-ACCESS			 read-create
		STATUS					 current
		DESCRIPTION			 " -- "
		::=  { cellReselectIntraFreqEntry  9 }


	cellReselIntraFreqMeasBandWidth		 OBJECT-TYPE
		SYNTAX					 INTEGER{ mbw6(0),mbw15(1),mbw25(2),mbw50(3),mbw75(4),mbw100(5)  }
		MAX-ACCESS			 read-create
		STATUS					 current
		DESCRIPTION			 " -- "
		::=  { cellReselectIntraFreqEntry  10 }


	cellReselIntraFreqPresenceAntennaPort1		 OBJECT-TYPE
		SYNTAX					 INTEGER{ false(0),true(1)  }
		MAX-ACCESS			 read-create
		STATUS					 current
		DESCRIPTION			 " -- "
		::=  { cellReselectIntraFreqEntry  11 }


	cellReselIntraFreqSpeedStateScaleFactorsFlag		 OBJECT-TYPE
		SYNTAX					 INTEGER{ false(0),true(1)  }
		MAX-ACCESS			 read-create
		STATUS					 current
		DESCRIPTION			 " -- "
		::=  { cellReselectIntraFreqEntry  12 }


	cellReselIntraFreqSpeedStateScaleFactorsMedium		 OBJECT-TYPE
		SYNTAX					 INTEGER{ oDot25(0),oDot5(1),oDot75(2),lDot0(3)  }
		MAX-ACCESS			 read-create
		STATUS					 current
		DESCRIPTION			 " -- "
		::=  { cellReselectIntraFreqEntry  13 }


	cellReselIntraFreqSpeedStateScaleFactorsHigh		 OBJECT-TYPE
		SYNTAX					 INTEGER{ oDot25(0),oDot5(1),oDot75(2),lDot0(3)  }
		MAX-ACCESS			 read-create
		STATUS					 current
		DESCRIPTION			 " -- "
		::=  { cellReselectIntraFreqEntry  14 }


	cellReselIntraFreqNeighbCellCfg		 OBJECT-TYPE
		SYNTAX					 INTEGER{ neighcellcfg00(0),neighcellcfg01(1),neighcellcfg10(2),neighcellcfg11(3)  }
		MAX-ACCESS			 read-create
		STATUS					 current
		DESCRIPTION			 " -- "
		::=  { cellReselectIntraFreqEntry  16 }


	cellReselIntraFreqIntraSearchR9Flag		 OBJECT-TYPE
		SYNTAX					 INTEGER{ false(0),true(1)  }
		MAX-ACCESS			 read-create
		STATUS					 current
		DESCRIPTION			 " -- "
		::=  { cellReselectIntraFreqEntry  17 }


	cellReselIntraFreqIntraSearchP		 OBJECT-TYPE
		SYNTAX					 INTEGER{ reselectThresholdDb0(0),reselectThresholdDb2(1),reselectThresholdDb4(2),reselectThresholdDb6(3),reselectThresholdDb8(4),reselectThresholdDb10(5),reselectThresholdDb12(6),reselectThresholdDb14(7),reselectThresholdDb16(8),reselectThresholdDb18(9),reselectThresholdDb20(10),reselectThresholdDb22(11),reselectThresholdDb24(12),reselectThresholdDb26(13),reselectThresholdDb28(14),reselectThresholdDb30(15),reselectThresholdDb32(16),reselectThresholdDb34(17),reselectThresholdDb36(18),reselectThresholdDb38(19),reselectThresholdDb40(20),reselectThresholdDb42(21),reselectThresholdDb44(22),reselectThresholdDb46(23),reselectThresholdDb48(24),reselectThresholdDb50(25),reselectThresholdDb52(26),reselectThresholdDb54(27),reselectThresholdDb56(28),reselectThresholdDb58(29),reselectThresholdDb60(30),reselectThresholdDb62(31)  }
		MAX-ACCESS			 read-create
		STATUS					 current
		DESCRIPTION			 " -- "
		::=  { cellReselectIntraFreqEntry  18 }


	cellReselIntraFreqIntraSearchQ		 OBJECT-TYPE
		SYNTAX					 INTEGER{ reselectThresholdDb0(0),reselectThresholdDb1(1),reselectThresholdDb2(2),reselectThresholdDb3(3),reselectThresholdDb4(4),reselectThresholdDb5(5),reselectThresholdDb6(6),reselectThresholdDb7(7),reselectThresholdDb8(8),reselectThresholdDb9(9),reselectThresholdDb10(10),reselectThresholdDb11(11),reselectThresholdDb12(12),reselectThresholdDb13(13),reselectThresholdDb14(14),reselectThresholdDb15(15),reselectThresholdDb16(16),reselectThresholdDb17(17),reselectThresholdDb18(18),reselectThresholdDb19(19),reselectThresholdDb20(20),reselectThresholdDb21(21),reselectThresholdDb22(22),reselectThresholdDb23(23),reselectThresholdDb24(24),reselectThresholdDb25(25),reselectThresholdDb26(26),reselectThresholdDb27(27),reselectThresholdDb28(28),reselectThresholdDb29(29),reselectThresholdDb30(30),reselectThresholdDb31(31)  }
		MAX-ACCESS			 read-create
		STATUS					 current
		DESCRIPTION			 " -- "
		::=  { cellReselectIntraFreqEntry  19 }


	cellReselIntraFreqQualMinFlag		 OBJECT-TYPE
		SYNTAX					 INTEGER{ false(0),true(1)  }
		MAX-ACCESS			 read-create
		STATUS					 current
		DESCRIPTION			 " -- "
		::=  { cellReselectIntraFreqEntry  20 }


	cellReselIntraFreqQualMin		 OBJECT-TYPE
		SYNTAX					 INTEGER{ qualMinMinusDb34(0),qualMinMinusDb33(1),qualMinMinusDb32(2),qualMinMinusDb31(3),qualMinMinusDb30(4),qualMinMinusDb29(5),qualMinMinusDb28(6),qualMinMinusDb27(7),qualMinMinusDb26(8),qualMinMinusDb25(9),qualMinMinusDb24(10),qualMinMinusDb23(11),qualMinMinusDb22(12),qualMinMinusDb21(13),qualMinMinusDb20(14),qualMinMinusDb19(15),qualMinMinusDb18(16),qualMinMinusDb17(17),qualMinMinusDb16(18),qualMinMinusDb15(19),qualMinMinusDb14(20),qualMinMinusDb13(21),qualMinMinusDb12(22),qualMinMinusDb11(23),qualMinMinusDb10(24),qualMinMinusDb9(25),qualMinMinusDb8(26),qualMinMinusDb7(27),qualMinMinusDb6(28),qualMinMinusDb5(29),qualMinMinusDb4(30),qualMinMinusDb3(31)  }
		MAX-ACCESS			 read-create
		STATUS					 current
		DESCRIPTION			 " -- "
		::=  { cellReselectIntraFreqEntry  21 }


	cellReselectionInterRatTable		 OBJECT-TYPE
		SYNTAX					 SEQUENCE  OF	 CellReselectionInterRatEntry
		MAX-ACCESS			 not-accessible
		STATUS					 current
		DESCRIPTION			 " -- "
		::=  { cellSelectReselect  4 }


	cellReselectionInterRatEntry		 OBJECT-TYPE
		SYNTAX					 CellReselectionInterRatEntry
		MAX-ACCESS			 not-accessible
		STATUS					 current
		DESCRIPTION			 " -- "
		INDEX						{ cellInterRatLcId }
		::=  { cellReselectionInterRatTable  1 }


	CellReselectionInterRatEntry		 ::=  SEQUENCE {
		cellInterRatLcId					Integer32,
		cellInterRatRowStatus					RowStatus,
		cellInterRatTreselectionUtra					Integer32,
		cellInterRatTreselectionUtraSfFlag					INTEGER,
		cellInterRatUtraSfHigh					INTEGER,
		cellInterRatUtraSfMedium					INTEGER,
		cellInterRatTreselectionGeran					Integer32,
		cellInterRatTreselectionGeranSfFlag					INTEGER,
		cellInterRatGeranSfHigh					INTEGER,
		cellInterRatGeranSfMedium					INTEGER,
		cellInterRatCDMA2000HRPDFlag					INTEGER,
		cellInterRatCDMA20001xRTTFlag					INTEGER,
		cellInterRatTreselectionCdmaHRPD					Integer32,
		cellInterRatTreselectionCdmaHRPDSfFlag					INTEGER,
		cellInterRatCdmaHRPDSfHigh					INTEGER,
		cellInterRatCdmaHRPDSfMedium					INTEGER,
		cellInterRatTreselectionCdma1xRTT					Integer32,
		cellInterRatTreselectionCdma1xRTTSfFlag					INTEGER,
		cellInterRatCdma1xRTTSfHigh					INTEGER,
		cellInterRatCdma1xRTTSfMedium					INTEGER
		}


	cellInterRatLcId		 OBJECT-TYPE
		SYNTAX					 Integer32( 0 .. 23 )
		MAX-ACCESS			 not-accessible
		STATUS					 current
		DESCRIPTION			 " -- "
		::=  { cellReselectionInterRatEntry  1 }


	cellInterRatRowStatus		 OBJECT-TYPE
		SYNTAX					 RowStatus
		MAX-ACCESS			 read-create
		STATUS					 current
		DESCRIPTION			 " -- "
		::=  { cellReselectionInterRatEntry  2 }


	cellInterRatTreselectionUtra		 OBJECT-TYPE
		SYNTAX					 Integer32( 0 .. 7 )
		MAX-ACCESS			 read-create
		STATUS					 current
		DESCRIPTION			 " -- "
		::=  { cellReselectionInterRatEntry  3 }


	cellInterRatTreselectionUtraSfFlag		 OBJECT-TYPE
		SYNTAX					 INTEGER{ false(0),true(1)  }
		MAX-ACCESS			 read-create
		STATUS					 current
		DESCRIPTION			 " -- "
		::=  { cellReselectionInterRatEntry  4 }


	cellInterRatUtraSfHigh		 OBJECT-TYPE
		SYNTAX					 INTEGER{ oDot25(0),oDot5(1),oDot75(2),lDot0(3)  }
		MAX-ACCESS			 read-create
		STATUS					 current
		DESCRIPTION			 " -- "
		::=  { cellReselectionInterRatEntry  5 }


	cellInterRatUtraSfMedium		 OBJECT-TYPE
		SYNTAX					 INTEGER{ oDot25(0),oDot5(1),oDot75(2),lDot0(3)  }
		MAX-ACCESS			 read-create
		STATUS					 current
		DESCRIPTION			 " -- "
		::=  { cellReselectionInterRatEntry  6 }


	cellInterRatTreselectionGeran		 OBJECT-TYPE
		SYNTAX					 Integer32( 0 .. 7 )
		MAX-ACCESS			 read-create
		STATUS					 current
		DESCRIPTION			 " -- "
		::=  { cellReselectionInterRatEntry  7 }


	cellInterRatTreselectionGeranSfFlag		 OBJECT-TYPE
		SYNTAX					 INTEGER{ false(0),true(1)  }
		MAX-ACCESS			 read-create
		STATUS					 current
		DESCRIPTION			 " -- "
		::=  { cellReselectionInterRatEntry  8 }


	cellInterRatGeranSfHigh		 OBJECT-TYPE
		SYNTAX					 INTEGER{ oDot25(0),oDot5(1),oDot75(2),lDot0(3)  }
		MAX-ACCESS			 read-create
		STATUS					 current
		DESCRIPTION			 " -- "
		::=  { cellReselectionInterRatEntry  9 }


	cellInterRatGeranSfMedium		 OBJECT-TYPE
		SYNTAX					 INTEGER{ oDot25(0),oDot5(1),oDot75(2),lDot0(3)  }
		MAX-ACCESS			 read-create
		STATUS					 current
		DESCRIPTION			 " -- "
		::=  { cellReselectionInterRatEntry  10 }


	cellInterRatCDMA2000HRPDFlag		 OBJECT-TYPE
		SYNTAX					 INTEGER{ false(0),true(1)  }
		MAX-ACCESS			 read-create
		STATUS					 current
		DESCRIPTION			 " -- "
		::=  { cellReselectionInterRatEntry  11 }


	cellInterRatCDMA20001xRTTFlag		 OBJECT-TYPE
		SYNTAX					 INTEGER{ false(0),true(1)  }
		MAX-ACCESS			 read-create
		STATUS					 current
		DESCRIPTION			 " -- "
		::=  { cellReselectionInterRatEntry  12 }


	cellInterRatTreselectionCdmaHRPD		 OBJECT-TYPE
		SYNTAX					 Integer32( 0 .. 7 )
		MAX-ACCESS			 read-create
		STATUS					 current
		DESCRIPTION			 " -- "
		::=  { cellReselectionInterRatEntry  13 }


	cellInterRatTreselectionCdmaHRPDSfFlag		 OBJECT-TYPE
		SYNTAX					 INTEGER{ false(0),true(1)  }
		MAX-ACCESS			 read-create
		STATUS					 current
		DESCRIPTION			 " -- "
		::=  { cellReselectionInterRatEntry  14 }


	cellInterRatCdmaHRPDSfHigh		 OBJECT-TYPE
		SYNTAX					 INTEGER{ oDot25(0),oDot5(1),oDot75(2),lDot0(3)  }
		MAX-ACCESS			 read-create
		STATUS					 current
		DESCRIPTION			 " -- "
		::=  { cellReselectionInterRatEntry  15 }


	cellInterRatCdmaHRPDSfMedium		 OBJECT-TYPE
		SYNTAX					 INTEGER{ oDot25(0),oDot5(1),oDot75(2),lDot0(3)  }
		MAX-ACCESS			 read-create
		STATUS					 current
		DESCRIPTION			 " -- "
		::=  { cellReselectionInterRatEntry  16 }


	cellInterRatTreselectionCdma1xRTT		 OBJECT-TYPE
		SYNTAX					 Integer32( 0 .. 7 )
		MAX-ACCESS			 read-create
		STATUS					 current
		DESCRIPTION			 " -- "
		::=  { cellReselectionInterRatEntry  17 }


	cellInterRatTreselectionCdma1xRTTSfFlag		 OBJECT-TYPE
		SYNTAX					 INTEGER{ false(0),true(1)  }
		MAX-ACCESS			 read-create
		STATUS					 current
		DESCRIPTION			 " -- "
		::=  { cellReselectionInterRatEntry  18 }


	cellInterRatCdma1xRTTSfHigh		 OBJECT-TYPE
		SYNTAX					 INTEGER{ oDot25(0),oDot5(1),oDot75(2),lDot0(3)  }
		MAX-ACCESS			 read-create
		STATUS					 current
		DESCRIPTION			 " -- "
		::=  { cellReselectionInterRatEntry  19 }


	cellInterRatCdma1xRTTSfMedium		 OBJECT-TYPE
		SYNTAX					 INTEGER{ oDot25(0),oDot5(1),oDot75(2),lDot0(3)  }
		MAX-ACCESS			 read-create
		STATUS					 current
		DESCRIPTION			 " -- "
		::=  { cellReselectionInterRatEntry  20 }


	cellCdmaBandClassInfoTable		 OBJECT-TYPE
		SYNTAX					 SEQUENCE  OF	 CellCdmaBandClassInfoEntry
		MAX-ACCESS			 not-accessible
		STATUS					 current
		DESCRIPTION			 " -- "
		::=  { cellSelectReselect  5 }


	cellCdmaBandClassInfoEntry		 OBJECT-TYPE
		SYNTAX					 CellCdmaBandClassInfoEntry
		MAX-ACCESS			 not-accessible
		STATUS					 current
		DESCRIPTION			 " -- "
		INDEX						{ cellCdmaBandClassInfoLcId,cellCdmaBandClassInfoIndex }
		::=  { cellCdmaBandClassInfoTable  1 }


	CellCdmaBandClassInfoEntry		 ::=  SEQUENCE {
		cellCdmaBandClassInfoLcId					Integer32,
		cellCdmaBandClassInfoIndex					Integer32,
		cellCdmaBandClassInfoRowStatus					RowStatus,
		cellCdmaBandClassInfoFreqType					INTEGER,
		cellCdmaBandClassInfoBandClass					INTEGER,
		cellCdmaBandClassInfoPriorityFlag					INTEGER,
		cellCdmaBandClassInfoPriority					Integer32,
		cellCdmaBandClassInfoThreshxHigh					Integer32,
		cellCdmaBandClassInfoThreshxLow					Integer32
		}


	cellCdmaBandClassInfoLcId		 OBJECT-TYPE
		SYNTAX					 Integer32( 0 .. 23 )
		MAX-ACCESS			 not-accessible
		STATUS					 current
		DESCRIPTION			 " -- "
		::=  { cellCdmaBandClassInfoEntry  1 }


	cellCdmaBandClassInfoIndex		 OBJECT-TYPE
		SYNTAX					 Integer32( 0 .. 31 )
		MAX-ACCESS			 not-accessible
		STATUS					 current
		DESCRIPTION			 " -- "
		::=  { cellCdmaBandClassInfoEntry  2 }


	cellCdmaBandClassInfoRowStatus		 OBJECT-TYPE
		SYNTAX					 RowStatus
		MAX-ACCESS			 read-create
		STATUS					 current
		DESCRIPTION			 " -- "
		::=  { cellCdmaBandClassInfoEntry  3 }


	cellCdmaBandClassInfoFreqType		 OBJECT-TYPE
		SYNTAX					 INTEGER{ type1XRTT(0),typeHRPD(1)  }
		MAX-ACCESS			 read-create
		STATUS					 current
		DESCRIPTION			 " -- "
		::=  { cellCdmaBandClassInfoEntry  4 }


	cellCdmaBandClassInfoBandClass		 OBJECT-TYPE
		SYNTAX					 INTEGER{ bc0(0),bc1(1),bc2(2),bc3(3),bc4(4),bc5(5),bc6(6),bc7(7),bc8(8),bc9(9),bc10(10),bc11(11),bc12(12),bc13(13),bc14(14),bc15(15),bc16(16),bc17(17),invalid(-1)  }
		MAX-ACCESS			 read-create
		STATUS					 current
		DESCRIPTION			 " -- "
		::=  { cellCdmaBandClassInfoEntry  5 }


	cellCdmaBandClassInfoPriorityFlag		 OBJECT-TYPE
		SYNTAX					 INTEGER{ false(0),true(1)  }
		MAX-ACCESS			 read-create
		STATUS					 current
		DESCRIPTION			 " -- "
		::=  { cellCdmaBandClassInfoEntry  6 }


	cellCdmaBandClassInfoPriority		 OBJECT-TYPE
		SYNTAX					 Integer32( 0 .. 7 )
		MAX-ACCESS			 read-create
		STATUS					 current
		DESCRIPTION			 " -- "
		::=  { cellCdmaBandClassInfoEntry  7 }


	cellCdmaBandClassInfoThreshxHigh		 OBJECT-TYPE
		SYNTAX					 Integer32( 0 .. 63 )
		MAX-ACCESS			 read-create
		STATUS					 current
		DESCRIPTION			 " -- "
		::=  { cellCdmaBandClassInfoEntry  8 }


	cellCdmaBandClassInfoThreshxLow		 OBJECT-TYPE
		SYNTAX					 Integer32( 0 .. 63 )
		MAX-ACCESS			 read-create
		STATUS					 current
		DESCRIPTION			 " -- "
		::=  { cellCdmaBandClassInfoEntry  9 }


	cellSysInfo		 OBJECT IDENTIFIER
		::=  { networkElementPlanCell  5 }


	cellSchedulingTable		 OBJECT-TYPE
		SYNTAX					 SEQUENCE  OF	 CellSchedulingEntry
		MAX-ACCESS			 not-accessible
		STATUS					 current
		DESCRIPTION			 " -- "
		::=  { cellSysInfo  1 }


	cellSchedulingEntry		 OBJECT-TYPE
		SYNTAX					 CellSchedulingEntry
		MAX-ACCESS			 not-accessible
		STATUS					 current
		DESCRIPTION			 " -- "
		INDEX						{ cellShedLcId }
		::=  { cellSchedulingTable  1 }


	CellSchedulingEntry		 ::=  SEQUENCE {
		cellShedLcId					Integer32,
		cellShedRowStatus					RowStatus,
		cellShedSiTransferTime					Integer32,
		cellShedSiWindowLen					INTEGER,
		cellShedRrModifyPeriodCoeff					INTEGER,
		cellShedSib2Period					INTEGER,
		cellShedSib3Period					INTEGER,
		cellShedSib4Period					INTEGER,
		cellShedSib5Period					INTEGER,
		cellShedSib6Period					INTEGER,
		cellShedSib7Period					INTEGER,
		cellShedSib10Period					INTEGER,
		cellShedSib11Period					INTEGER,
		cellShedSib8Period					INTEGER,
		cellShedSib6Flag					INTEGER,
		cellShedSib7Flag					INTEGER,
		cellShedSib8Flag					INTEGER
		}


	cellShedLcId		 OBJECT-TYPE
		SYNTAX					 Integer32( 0 .. 23 )
		MAX-ACCESS			 not-accessible
		STATUS					 current
		DESCRIPTION			 " -- "
		::=  { cellSchedulingEntry  1 }


	cellShedRowStatus		 OBJECT-TYPE
		SYNTAX					 RowStatus
		MAX-ACCESS			 read-create
		STATUS					 current
		DESCRIPTION			 " -- "
		::=  { cellSchedulingEntry  2 }


	cellShedSiTransferTime		 OBJECT-TYPE
		SYNTAX					 Integer32( 0 .. 255 )
		MAX-ACCESS			 read-create
		STATUS					 current
		DESCRIPTION			 " -- "
		::=  { cellSchedulingEntry  3 }


	cellShedSiWindowLen		 OBJECT-TYPE
		SYNTAX					 INTEGER{ ms1(0),ms2(1),ms5(2),ms10(3),ms15(4),ms20(5),ms40(6)  }
		MAX-ACCESS			 read-create
		STATUS					 current
		DESCRIPTION			 " -- "
		::=  { cellSchedulingEntry  4 }


	cellShedRrModifyPeriodCoeff		 OBJECT-TYPE
		SYNTAX					 INTEGER{ n2(0),n4(1),n8(2),n16(3)  }
		MAX-ACCESS			 read-create
		STATUS					 current
		DESCRIPTION			 " -- "
		::=  { cellSchedulingEntry  5 }


	cellShedSib2Period		 OBJECT-TYPE
		SYNTAX					 INTEGER{ rf8(0),rf16(1),rf32(2),rf64(3),rf128(4),rf256(5),rf512(6)  }
		MAX-ACCESS			 read-create
		STATUS					 current
		DESCRIPTION			 " -- "
		::=  { cellSchedulingEntry  6 }


	cellShedSib3Period		 OBJECT-TYPE
		SYNTAX					 INTEGER{ rf8(0),rf16(1),rf32(2),rf64(3),rf128(4),rf256(5),rf512(6)  }
		MAX-ACCESS			 read-create
		STATUS					 current
		DESCRIPTION			 " -- "
		::=  { cellSchedulingEntry  7 }


	cellShedSib4Period		 OBJECT-TYPE
		SYNTAX					 INTEGER{ rf8(0),rf16(1),rf32(2),rf64(3),rf128(4),rf256(5),rf512(6)  }
		MAX-ACCESS			 read-create
		STATUS					 current
		DESCRIPTION			 " -- "
		::=  { cellSchedulingEntry  8 }


	cellShedSib5Period		 OBJECT-TYPE
		SYNTAX					 INTEGER{ rf8(0),rf16(1),rf32(2),rf64(3),rf128(4),rf256(5),rf512(6)  }
		MAX-ACCESS			 read-create
		STATUS					 current
		DESCRIPTION			 " -- "
		::=  { cellSchedulingEntry  9 }


	cellShedSib6Period		 OBJECT-TYPE
		SYNTAX					 INTEGER{ rf8(0),rf16(1),rf32(2),rf64(3),rf128(4),rf256(5),rf512(6)  }
		MAX-ACCESS			 read-create
		STATUS					 current
		DESCRIPTION			 " -- "
		::=  { cellSchedulingEntry  10 }


	cellShedSib7Period		 OBJECT-TYPE
		SYNTAX					 INTEGER{ rf8(0),rf16(1),rf32(2),rf64(3),rf128(4),rf256(5),rf512(6)  }
		MAX-ACCESS			 read-create
		STATUS					 current
		DESCRIPTION			 " -- "
		::=  { cellSchedulingEntry  11 }


	cellShedSib10Period		 OBJECT-TYPE
		SYNTAX					 INTEGER{ rf8(0),rf16(1),rf32(2),rf64(3),rf128(4),rf256(5),rf512(6)  }
		MAX-ACCESS			 read-create
		STATUS					 current
		DESCRIPTION			 " -- "
		::=  { cellSchedulingEntry  12 }


	cellShedSib11Period		 OBJECT-TYPE
		SYNTAX					 INTEGER{ rf8(0),rf16(1),rf32(2),rf64(3),rf128(4),rf256(5),rf512(6)  }
		MAX-ACCESS			 read-create
		STATUS					 current
		DESCRIPTION			 " -- "
		::=  { cellSchedulingEntry  13 }


	cellShedSib8Period		 OBJECT-TYPE
		SYNTAX					 INTEGER{ rf8(0),rf16(1),rf32(2),rf64(3),rf128(4),rf256(5),rf512(6)  }
		MAX-ACCESS			 read-create
		STATUS					 current
		DESCRIPTION			 " -- "
		::=  { cellSchedulingEntry  14 }


	cellShedSib6Flag		 OBJECT-TYPE
		SYNTAX					 INTEGER{ false(0),true(1)  }
		MAX-ACCESS			 read-create
		STATUS					 current
		DESCRIPTION			 " -- "
		::=  { cellSchedulingEntry  15 }


	cellShedSib7Flag		 OBJECT-TYPE
		SYNTAX					 INTEGER{ false(0),true(1)  }
		MAX-ACCESS			 read-create
		STATUS					 current
		DESCRIPTION			 " -- "
		::=  { cellSchedulingEntry  16 }


	cellShedSib8Flag		 OBJECT-TYPE
		SYNTAX					 INTEGER{ false(0),true(1)  }
		MAX-ACCESS			 read-create
		STATUS					 current
		DESCRIPTION			 " -- "
		::=  { cellSchedulingEntry  17 }


	cellAccessRestrict		 OBJECT IDENTIFIER
		::=  { networkElementPlanCell  6 }


	cellAccessRestrictTable		 OBJECT-TYPE
		SYNTAX					 SEQUENCE  OF	 CellAccessRestrictEntry
		MAX-ACCESS			 not-accessible
		STATUS					 current
		DESCRIPTION			 " -- "
		::=  { cellAccessRestrict  1 }


	cellAccessRestrictEntry		 OBJECT-TYPE
		SYNTAX					 CellAccessRestrictEntry
		MAX-ACCESS			 not-accessible
		STATUS					 current
		DESCRIPTION			 " -- "
		INDEX						{ cellAcLcId }
		::=  { cellAccessRestrictTable  1 }


	CellAccessRestrictEntry		 ::=  SEQUENCE {
		cellAcLcId					Integer32,
		cellAcRowStatus					RowStatus,
		cellAcBarFlag					INTEGER,
		cellAcAcBarForEmergcyCalls					INTEGER,
		cellAcBarForSingalFlag					INTEGER,
		cellAcProbFactorForSignal					INTEGER,
		cellAcBarTimeForSigalling					INTEGER,
		cellAcBarList1ForSigalling					INTEGER,
		cellAcBarList2ForSigalling					INTEGER,
		cellAcBarList3ForSigalling					INTEGER,
		cellAcBarList4ForSigalling					INTEGER,
		cellAcBarList5ForSigalling					INTEGER,
		cellAcBarForMocFlag					INTEGER,
		cellAcProbFactorForMoc					INTEGER,
		cellAcBarTimeForOrigiCalls					INTEGER,
		cellAcBarList1ForOrigiCalls					INTEGER,
		cellAcBarList2ForOrigiCalls					INTEGER,
		cellAcBarList3ForOrigiCalls					INTEGER,
		cellAcBarList4ForOrigiCalls					INTEGER,
		cellAcBarList5ForOrigiCalls					INTEGER,
		cellAcBarForVoiceFlag					INTEGER,
		cellAcProbFactorForVoice					INTEGER,
		cellAcBarTimeForVoice					INTEGER,
		cellAcBarList1ForVoice					INTEGER,
		cellAcBarList2ForVoice					INTEGER,
		cellAcBarList3ForVoice					INTEGER,
		cellAcBarList4ForVoice					INTEGER,
		cellAcBarList5ForVoice					INTEGER,
		cellAcBarForVideoFlag					INTEGER,
		cellAcProbFactorForVideo					INTEGER,
		cellAcBarTimeForVideo					INTEGER,
		cellAcBarList1ForVideo					INTEGER,
		cellAcBarList2ForVideo					INTEGER,
		cellAcBarList3ForVideo					INTEGER,
		cellAcBarList4ForVideo					INTEGER,
		cellAcBarList5ForVideo					INTEGER
		}


	cellAcLcId		 OBJECT-TYPE
		SYNTAX					 Integer32( 0 .. 23 )
		MAX-ACCESS			 not-accessible
		STATUS					 current
		DESCRIPTION			 " -- "
		::=  { cellAccessRestrictEntry  1 }


	cellAcRowStatus		 OBJECT-TYPE
		SYNTAX					 RowStatus
		MAX-ACCESS			 read-create
		STATUS					 current
		DESCRIPTION			 " -- "
		::=  { cellAccessRestrictEntry  2 }


	cellAcBarFlag		 OBJECT-TYPE
		SYNTAX					 INTEGER{ false(0),true(1)  }
		MAX-ACCESS			 read-create
		STATUS					 current
		DESCRIPTION			 " -- "
		::=  { cellAccessRestrictEntry  3 }


	cellAcAcBarForEmergcyCalls		 OBJECT-TYPE
		SYNTAX					 INTEGER{ false(0),true(1)  }
		MAX-ACCESS			 read-create
		STATUS					 current
		DESCRIPTION			 " -- "
		::=  { cellAccessRestrictEntry  4 }


	cellAcBarForSingalFlag		 OBJECT-TYPE
		SYNTAX					 INTEGER{ false(0),true(1)  }
		MAX-ACCESS			 read-create
		STATUS					 current
		DESCRIPTION			 " -- "
		::=  { cellAccessRestrictEntry  5 }


	cellAcProbFactorForSignal		 OBJECT-TYPE
		SYNTAX					 INTEGER{ p00(0),p05(1),p10(2),p15(3),p20(4),p25(5),p30(6),p40(7),p50(8),p60(9),p70(10),p75(11),p80(12),p85(13),p90(14),p95(15)  }
		MAX-ACCESS			 read-create
		STATUS					 current
		DESCRIPTION			 " -- "
		::=  { cellAccessRestrictEntry  6 }


	cellAcBarTimeForSigalling		 OBJECT-TYPE
		SYNTAX					 INTEGER{ s4(0),s8(1),s16(2),s32(3),s64(4),s128(5),s256(6),s512(7)  }
		MAX-ACCESS			 read-create
		STATUS					 current
		DESCRIPTION			 " -- "
		::=  { cellAccessRestrictEntry  7 }


	cellAcBarList1ForSigalling		 OBJECT-TYPE
		SYNTAX					 INTEGER{ false(0),true(1)  }
		MAX-ACCESS			 read-create
		STATUS					 current
		DESCRIPTION			 " -- "
		::=  { cellAccessRestrictEntry  8 }


	cellAcBarList2ForSigalling		 OBJECT-TYPE
		SYNTAX					 INTEGER{ false(0),true(1)  }
		MAX-ACCESS			 read-create
		STATUS					 current
		DESCRIPTION			 " -- "
		::=  { cellAccessRestrictEntry  9 }


	cellAcBarList3ForSigalling		 OBJECT-TYPE
		SYNTAX					 INTEGER{ false(0),true(1)  }
		MAX-ACCESS			 read-create
		STATUS					 current
		DESCRIPTION			 " -- "
		::=  { cellAccessRestrictEntry  10 }


	cellAcBarList4ForSigalling		 OBJECT-TYPE
		SYNTAX					 INTEGER{ false(0),true(1)  }
		MAX-ACCESS			 read-create
		STATUS					 current
		DESCRIPTION			 " -- "
		::=  { cellAccessRestrictEntry  11 }


	cellAcBarList5ForSigalling		 OBJECT-TYPE
		SYNTAX					 INTEGER{ false(0),true(1)  }
		MAX-ACCESS			 read-create
		STATUS					 current
		DESCRIPTION			 " -- "
		::=  { cellAccessRestrictEntry  12 }


	cellAcBarForMocFlag		 OBJECT-TYPE
		SYNTAX					 INTEGER{ false(0),true(1)  }
		MAX-ACCESS			 read-create
		STATUS					 current
		DESCRIPTION			 " -- "
		::=  { cellAccessRestrictEntry  13 }


	cellAcProbFactorForMoc		 OBJECT-TYPE
		SYNTAX					 INTEGER{ p00(0),p05(1),p10(2),p15(3),p20(4),p25(5),p30(6),p40(7),p50(8),p60(9),p70(10),p75(11),p80(12),p85(13),p90(14),p95(15)  }
		MAX-ACCESS			 read-create
		STATUS					 current
		DESCRIPTION			 " -- "
		::=  { cellAccessRestrictEntry  14 }


	cellAcBarTimeForOrigiCalls		 OBJECT-TYPE
		SYNTAX					 INTEGER{ s4(0),s8(1),s16(2),s32(3),s64(4),s128(5),s256(6),s512(7)  }
		MAX-ACCESS			 read-create
		STATUS					 current
		DESCRIPTION			 " -- "
		::=  { cellAccessRestrictEntry  15 }


	cellAcBarList1ForOrigiCalls		 OBJECT-TYPE
		SYNTAX					 INTEGER{ false(0),true(1)  }
		MAX-ACCESS			 read-create
		STATUS					 current
		DESCRIPTION			 " -- "
		::=  { cellAccessRestrictEntry  16 }


	cellAcBarList2ForOrigiCalls		 OBJECT-TYPE
		SYNTAX					 INTEGER{ false(0),true(1)  }
		MAX-ACCESS			 read-create
		STATUS					 current
		DESCRIPTION			 " -- "
		::=  { cellAccessRestrictEntry  17 }


	cellAcBarList3ForOrigiCalls		 OBJECT-TYPE
		SYNTAX					 INTEGER{ false(0),true(1)  }
		MAX-ACCESS			 read-create
		STATUS					 current
		DESCRIPTION			 " -- "
		::=  { cellAccessRestrictEntry  18 }


	cellAcBarList4ForOrigiCalls		 OBJECT-TYPE
		SYNTAX					 INTEGER{ false(0),true(1)  }
		MAX-ACCESS			 read-create
		STATUS					 current
		DESCRIPTION			 " -- "
		::=  { cellAccessRestrictEntry  19 }


	cellAcBarList5ForOrigiCalls		 OBJECT-TYPE
		SYNTAX					 INTEGER{ false(0),true(1)  }
		MAX-ACCESS			 read-create
		STATUS					 current
		DESCRIPTION			 " -- "
		::=  { cellAccessRestrictEntry  20 }


	cellAcBarForVoiceFlag		 OBJECT-TYPE
		SYNTAX					 INTEGER{ false(0),true(1)  }
		MAX-ACCESS			 read-create
		STATUS					 current
		DESCRIPTION			 " -- "
		::=  { cellAccessRestrictEntry  21 }


	cellAcProbFactorForVoice		 OBJECT-TYPE
		SYNTAX					 INTEGER{ p00(0),p05(1),p10(2),p15(3),p20(4),p25(5),p30(6),p40(7),p50(8),p60(9),p70(10),p75(11),p80(12),p85(13),p90(14),p95(15)  }
		MAX-ACCESS			 read-create
		STATUS					 current
		DESCRIPTION			 " -- "
		::=  { cellAccessRestrictEntry  22 }


	cellAcBarTimeForVoice		 OBJECT-TYPE
		SYNTAX					 INTEGER{ s4(0),s8(1),s16(2),s32(3),s64(4),s128(5),s256(6),s512(7)  }
		MAX-ACCESS			 read-create
		STATUS					 current
		DESCRIPTION			 " -- "
		::=  { cellAccessRestrictEntry  23 }


	cellAcBarList1ForVoice		 OBJECT-TYPE
		SYNTAX					 INTEGER{ false(0),true(1)  }
		MAX-ACCESS			 read-create
		STATUS					 current
		DESCRIPTION			 " -- "
		::=  { cellAccessRestrictEntry  24 }


	cellAcBarList2ForVoice		 OBJECT-TYPE
		SYNTAX					 INTEGER{ false(0),true(1)  }
		MAX-ACCESS			 read-create
		STATUS					 current
		DESCRIPTION			 " -- "
		::=  { cellAccessRestrictEntry  25 }


	cellAcBarList3ForVoice		 OBJECT-TYPE
		SYNTAX					 INTEGER{ false(0),true(1)  }
		MAX-ACCESS			 read-create
		STATUS					 current
		DESCRIPTION			 " -- "
		::=  { cellAccessRestrictEntry  26 }


	cellAcBarList4ForVoice		 OBJECT-TYPE
		SYNTAX					 INTEGER{ false(0),true(1)  }
		MAX-ACCESS			 read-create
		STATUS					 current
		DESCRIPTION			 " -- "
		::=  { cellAccessRestrictEntry  27 }


	cellAcBarList5ForVoice		 OBJECT-TYPE
		SYNTAX					 INTEGER{ false(0),true(1)  }
		MAX-ACCESS			 read-create
		STATUS					 current
		DESCRIPTION			 " -- "
		::=  { cellAccessRestrictEntry  28 }


	cellAcBarForVideoFlag		 OBJECT-TYPE
		SYNTAX					 INTEGER{ false(0),true(1)  }
		MAX-ACCESS			 read-create
		STATUS					 current
		DESCRIPTION			 " -- "
		::=  { cellAccessRestrictEntry  29 }


	cellAcProbFactorForVideo		 OBJECT-TYPE
		SYNTAX					 INTEGER{ p00(0),p05(1),p10(2),p15(3),p20(4),p25(5),p30(6),p40(7),p50(8),p60(9),p70(10),p75(11),p80(12),p85(13),p90(14),p95(15)  }
		MAX-ACCESS			 read-create
		STATUS					 current
		DESCRIPTION			 " -- "
		::=  { cellAccessRestrictEntry  30 }


	cellAcBarTimeForVideo		 OBJECT-TYPE
		SYNTAX					 INTEGER{ s4(0),s8(1),s16(2),s32(3),s64(4),s128(5),s256(6),s512(7)  }
		MAX-ACCESS			 read-create
		STATUS					 current
		DESCRIPTION			 " -- "
		::=  { cellAccessRestrictEntry  31 }


	cellAcBarList1ForVideo		 OBJECT-TYPE
		SYNTAX					 INTEGER{ false(0),true(1)  }
		MAX-ACCESS			 read-create
		STATUS					 current
		DESCRIPTION			 " -- "
		::=  { cellAccessRestrictEntry  32 }


	cellAcBarList2ForVideo		 OBJECT-TYPE
		SYNTAX					 INTEGER{ false(0),true(1)  }
		MAX-ACCESS			 read-create
		STATUS					 current
		DESCRIPTION			 " -- "
		::=  { cellAccessRestrictEntry  33 }


	cellAcBarList3ForVideo		 OBJECT-TYPE
		SYNTAX					 INTEGER{ false(0),true(1)  }
		MAX-ACCESS			 read-create
		STATUS					 current
		DESCRIPTION			 " -- "
		::=  { cellAccessRestrictEntry  34 }


	cellAcBarList4ForVideo		 OBJECT-TYPE
		SYNTAX					 INTEGER{ false(0),true(1)  }
		MAX-ACCESS			 read-create
		STATUS					 current
		DESCRIPTION			 " -- "
		::=  { cellAccessRestrictEntry  35 }


	cellAcBarList5ForVideo		 OBJECT-TYPE
		SYNTAX					 INTEGER{ false(0),true(1)  }
		MAX-ACCESS			 read-create
		STATUS					 current
		DESCRIPTION			 " -- "
		::=  { cellAccessRestrictEntry  36 }


	chandPrCfg		 OBJECT IDENTIFIER
		::=  { networkElementPlanCell  7 }


	phichTable		 OBJECT-TYPE
		SYNTAX					 SEQUENCE  OF	 PhichEntry
		MAX-ACCESS			 not-accessible
		STATUS					 current
		DESCRIPTION			 " -- "
		::=  { chandPrCfg  1 }


	phichEntry		 OBJECT-TYPE
		SYNTAX					 PhichEntry
		MAX-ACCESS			 not-accessible
		STATUS					 current
		DESCRIPTION			 " -- "
		INDEX						{ phichLcId }
		::=  { phichTable  1 }


	PhichEntry		 ::=  SEQUENCE {
		phichLcId					Integer32,
		phichRowStatus					RowStatus,
		phichDuration					INTEGER,
		phichResource					INTEGER
		}


	phichLcId		 OBJECT-TYPE
		SYNTAX					 Integer32( 0 .. 23 )
		MAX-ACCESS			 not-accessible
		STATUS					 current
		DESCRIPTION			 " -- "
		::=  { phichEntry  1 }


	phichRowStatus		 OBJECT-TYPE
		SYNTAX					 RowStatus
		MAX-ACCESS			 read-create
		STATUS					 current
		DESCRIPTION			 " -- "
		::=  { phichEntry  2 }


	phichDuration		 OBJECT-TYPE
		SYNTAX					 INTEGER{ normal(0),extended(1)  }
		MAX-ACCESS			 read-create
		STATUS					 current
		DESCRIPTION			 " -- "
		::=  { phichEntry  3 }


	phichResource		 OBJECT-TYPE
		SYNTAX					 INTEGER{ oneSixth(0),half(1),one(2),two(3)  }
		MAX-ACCESS			 read-create
		STATUS					 current
		DESCRIPTION			 " -- "
		::=  { phichEntry  4 }


	pdschTable		 OBJECT-TYPE
		SYNTAX					 SEQUENCE  OF	 PdschEntry
		MAX-ACCESS			 not-accessible
		STATUS					 current
		DESCRIPTION			 " -- "
		::=  { chandPrCfg  2 }


	pdschEntry		 OBJECT-TYPE
		SYNTAX					 PdschEntry
		MAX-ACCESS			 not-accessible
		STATUS					 current
		DESCRIPTION			 " -- "
		INDEX						{ pdschLcId }
		::=  { pdschTable  1 }


	PdschEntry		 ::=  SEQUENCE {
		pdschLcId					Integer32,
		pdschRowStatus					RowStatus,
		pdschPb					Integer32,
		pdschPa					INTEGER
		}


	pdschLcId		 OBJECT-TYPE
		SYNTAX					 Integer32( 0 .. 23 )
		MAX-ACCESS			 not-accessible
		STATUS					 current
		DESCRIPTION			 " -- "
		::=  { pdschEntry  1 }


	pdschRowStatus		 OBJECT-TYPE
		SYNTAX					 RowStatus
		MAX-ACCESS			 read-create
		STATUS					 current
		DESCRIPTION			 " -- "
		::=  { pdschEntry  2 }


	pdschPb		 OBJECT-TYPE
		SYNTAX					 Integer32( 0 .. 3 )
		MAX-ACCESS			 read-create
		STATUS					 current
		DESCRIPTION			 " -- "
		::=  { pdschEntry  3 }


	pdschPa		 OBJECT-TYPE
		SYNTAX					 INTEGER{ n6dB(0),n4dot77dB(1),n3dB(2),n1dot77dB(3),p0dB(4),p1dB(5),p2dB(6),p3dB(7)  }
		MAX-ACCESS			 read-create
		STATUS					 current
		DESCRIPTION			 " -- "
		::=  { pdschEntry  4 }


	puschTable		 OBJECT-TYPE
		SYNTAX					 SEQUENCE  OF	 PuschEntry
		MAX-ACCESS			 not-accessible
		STATUS					 current
		DESCRIPTION			 " -- "
		::=  { chandPrCfg  3 }


	puschEntry		 OBJECT-TYPE
		SYNTAX					 PuschEntry
		MAX-ACCESS			 not-accessible
		STATUS					 current
		DESCRIPTION			 " -- "
		INDEX						{ puschLcId }
		::=  { puschTable  1 }


	PuschEntry		 ::=  SEQUENCE {
		puschLcId					Integer32,
		puschRowStatus					RowStatus,
		puschNsb					Integer32,
		puschRrHopMode					INTEGER,
		puschHoppingOffset					Integer32,
		puschEnable64QAM					INTEGER,
		puschRrSeqGroupHopFlag					INTEGER,
		puschRrGroupAssignPusch					Integer32,
		puschRrSeqHopFlag					INTEGER,
		puschRrCycShift					Integer32,
		puschTtiBundling					INTEGER,
		puschbetaOffsetACKIndex					Integer32,
		puschbetaOffsetRIIndex					Integer32,
		puschbetaOffsetCQIIndex					Integer32,
		puschdmrsWithOCCActivedR10Flag					INTEGER,
		puschbetaOffsetACKIndexMC					Integer32,
		puschbetaOffsetRIIndexMC					Integer32,
		puschbetaOffsetCQIIndexMC					Integer32
		}


	puschLcId		 OBJECT-TYPE
		SYNTAX					 Integer32( 0 .. 23 )
		MAX-ACCESS			 not-accessible
		STATUS					 current
		DESCRIPTION			 " -- "
		::=  { puschEntry  1 }


	puschRowStatus		 OBJECT-TYPE
		SYNTAX					 RowStatus
		MAX-ACCESS			 read-create
		STATUS					 current
		DESCRIPTION			 " -- "
		::=  { puschEntry  2 }


	puschNsb		 OBJECT-TYPE
		SYNTAX					 Integer32( 1 .. 4 )
		MAX-ACCESS			 read-create
		STATUS					 current
		DESCRIPTION			 " -- "
		::=  { puschEntry  3 }


	puschRrHopMode		 OBJECT-TYPE
		SYNTAX					 INTEGER{ interSubFrame(0),interIntraSubFrame(1)  }
		MAX-ACCESS			 read-create
		STATUS					 current
		DESCRIPTION			 " -- "
		::=  { puschEntry  4 }


	puschHoppingOffset		 OBJECT-TYPE
		SYNTAX					 Integer32( 0 .. 98 )
		MAX-ACCESS			 read-create
		STATUS					 current
		DESCRIPTION			 " -- "
		::=  { puschEntry  5 }


	puschEnable64QAM		 OBJECT-TYPE
		SYNTAX					 INTEGER{ false(0),true(1)  }
		MAX-ACCESS			 read-create
		STATUS					 current
		DESCRIPTION			 " -- "
		::=  { puschEntry  6 }


	puschRrSeqGroupHopFlag		 OBJECT-TYPE
		SYNTAX					 INTEGER{ false(0),true(1)  }
		MAX-ACCESS			 read-create
		STATUS					 current
		DESCRIPTION			 " -- "
		::=  { puschEntry  7 }


	puschRrGroupAssignPusch		 OBJECT-TYPE
		SYNTAX					 Integer32( 0 .. 29 )
		MAX-ACCESS			 read-create
		STATUS					 current
		DESCRIPTION			 " -- "
		::=  { puschEntry  8 }


	puschRrSeqHopFlag		 OBJECT-TYPE
		SYNTAX					 INTEGER{ false(0),true(1)  }
		MAX-ACCESS			 read-create
		STATUS					 current
		DESCRIPTION			 " -- "
		::=  { puschEntry  9 }


	puschRrCycShift		 OBJECT-TYPE
		SYNTAX					 Integer32( 0 .. 7 )
		MAX-ACCESS			 read-create
		STATUS					 current
		DESCRIPTION			 " -- "
		::=  { puschEntry  10 }


	puschTtiBundling		 OBJECT-TYPE
		SYNTAX					 INTEGER{ false(0),true(1)  }
		MAX-ACCESS			 read-create
		STATUS					 current
		DESCRIPTION			 " -- "
		::=  { puschEntry  11 }


	puschbetaOffsetACKIndex		 OBJECT-TYPE
		SYNTAX					 Integer32( 0 .. 15 )
		MAX-ACCESS			 read-create
		STATUS					 current
		DESCRIPTION			 " -- "
		::=  { puschEntry  12 }


	puschbetaOffsetRIIndex		 OBJECT-TYPE
		SYNTAX					 Integer32( 0 .. 15 )
		MAX-ACCESS			 read-create
		STATUS					 current
		DESCRIPTION			 " -- "
		::=  { puschEntry  13 }


	puschbetaOffsetCQIIndex		 OBJECT-TYPE
		SYNTAX					 Integer32( 0 .. 15 )
		MAX-ACCESS			 read-create
		STATUS					 current
		DESCRIPTION			 " -- "
		::=  { puschEntry  14 }


	puschdmrsWithOCCActivedR10Flag		 OBJECT-TYPE
		SYNTAX					 INTEGER{ false(0),true(1)  }
		MAX-ACCESS			 read-create
		STATUS					 current
		DESCRIPTION			 " -- "
		::=  { puschEntry  15 }


	puschbetaOffsetACKIndexMC		 OBJECT-TYPE
		SYNTAX					 Integer32( 0 .. 15 )
		MAX-ACCESS			 read-create
		STATUS					 current
		DESCRIPTION			 " -- "
		::=  { puschEntry  16 }


	puschbetaOffsetRIIndexMC		 OBJECT-TYPE
		SYNTAX					 Integer32( 0 .. 15 )
		MAX-ACCESS			 read-create
		STATUS					 current
		DESCRIPTION			 " -- "
		::=  { puschEntry  17 }


	puschbetaOffsetCQIIndexMC		 OBJECT-TYPE
		SYNTAX					 Integer32( 0 .. 15 )
		MAX-ACCESS			 read-create
		STATUS					 current
		DESCRIPTION			 " -- "
		::=  { puschEntry  18 }


	pucchTable		 OBJECT-TYPE
		SYNTAX					 SEQUENCE  OF	 PucchEntry
		MAX-ACCESS			 not-accessible
		STATUS					 current
		DESCRIPTION			 " -- "
		::=  { chandPrCfg  4 }


	pucchEntry		 OBJECT-TYPE
		SYNTAX					 PucchEntry
		MAX-ACCESS			 not-accessible
		STATUS					 current
		DESCRIPTION			 " -- "
		INDEX						{ pucchLcId }
		::=  { pucchTable  1 }


	PucchEntry		 ::=  SEQUENCE {
		pucchLcId					Integer32,
		pucchRowStatus					RowStatus,
		pucchRrDeltaShift					INTEGER,
		pucchRrANCS					Integer32,
		pucchRrN1PucchAN					Integer32,
		pucchAckNackFeedbackMode					INTEGER,
		pucchReptFactor					INTEGER,
		pucch3ResSize					Integer32,
		pucch2AntePortActivatedPUCCHFormat1a1bR10Flag					INTEGER,
		pucch2AntePortActivatedPUCCHFormat3R10Flag					INTEGER,
		pucchFormatR10Choice					INTEGER,
		pucch2AntePortActivatedPUCCH2Flag					INTEGER,
		pucchSimUlPucchAndPusch					INTEGER,
		pucchCellSrPucchNum					Integer32,
		pucchCellSpsAckPucchNum					Integer32,
		pucchCellPucch1bcsNum					Integer32,
		pucchSrPucchNumPerPRB					INTEGER
		}


	pucchLcId		 OBJECT-TYPE
		SYNTAX					 Integer32( 0 .. 23 )
		MAX-ACCESS			 not-accessible
		STATUS					 current
		DESCRIPTION			 " -- "
		::=  { pucchEntry  1 }


	pucchRowStatus		 OBJECT-TYPE
		SYNTAX					 RowStatus
		MAX-ACCESS			 read-create
		STATUS					 current
		DESCRIPTION			 " -- "
		::=  { pucchEntry  2 }


	pucchRrDeltaShift		 OBJECT-TYPE
		SYNTAX					 INTEGER{ ds1(0),ds2(1),ds3(2)  }
		MAX-ACCESS			 read-create
		STATUS					 current
		DESCRIPTION			 " -- "
		::=  { pucchEntry  4 }


	pucchRrANCS		 OBJECT-TYPE
		SYNTAX					 Integer32( 0 .. 7 )
		MAX-ACCESS			 read-create
		STATUS					 current
		DESCRIPTION			 " -- "
		::=  { pucchEntry  5 }


	pucchRrN1PucchAN		 OBJECT-TYPE
		SYNTAX					 Integer32( 0 .. 2047 )
		MAX-ACCESS			 read-create
		STATUS					 current
		DESCRIPTION			 " -- "
		::=  { pucchEntry  6 }


	pucchAckNackFeedbackMode		 OBJECT-TYPE
		SYNTAX					 INTEGER{ bundling(0),multiplexing(1)  }
		MAX-ACCESS			 read-create
		STATUS					 current
		DESCRIPTION			 " -- "
		::=  { pucchEntry  7 }


	pucchReptFactor		 OBJECT-TYPE
		SYNTAX					 INTEGER{ n2(0),n4(1),n6(2)  }
		MAX-ACCESS			 read-create
		STATUS					 current
		DESCRIPTION			 " -- "
		::=  { pucchEntry  8 }


	pucch3ResSize		 OBJECT-TYPE
		SYNTAX					 Integer32( 0 .. 5 )
		MAX-ACCESS			 read-create
		STATUS					 current
		DESCRIPTION			 " -- "
		::=  { pucchEntry  10 }


	pucch2AntePortActivatedPUCCHFormat1a1bR10Flag		 OBJECT-TYPE
		SYNTAX					 INTEGER{ false(0),true(1)  }
		MAX-ACCESS			 read-create
		STATUS					 current
		DESCRIPTION			 " -- "
		::=  { pucchEntry  11 }


	pucch2AntePortActivatedPUCCHFormat3R10Flag		 OBJECT-TYPE
		SYNTAX					 INTEGER{ false(0),true(1)  }
		MAX-ACCESS			 read-create
		STATUS					 current
		DESCRIPTION			 " -- "
		::=  { pucchEntry  12 }


	pucchFormatR10Choice		 OBJECT-TYPE
		SYNTAX					 INTEGER{ pucch1a1b(0),pucch3(1)  }
		MAX-ACCESS			 read-create
		STATUS					 current
		DESCRIPTION			 " -- "
		::=  { pucchEntry  13 }


	pucch2AntePortActivatedPUCCH2Flag		 OBJECT-TYPE
		SYNTAX					 INTEGER{ false(0),true(1)  }
		MAX-ACCESS			 read-create
		STATUS					 current
		DESCRIPTION			 " -- "
		::=  { pucchEntry  14 }


	pucchSimUlPucchAndPusch		 OBJECT-TYPE
		SYNTAX					 INTEGER{ false(0),true(1)  }
		MAX-ACCESS			 read-create
		STATUS					 current
		DESCRIPTION			 " -- "
		::=  { pucchEntry  15 }


	pucchCellSrPucchNum		 OBJECT-TYPE
		SYNTAX					 Integer32( 0 .. 400 )
		MAX-ACCESS			 read-create
		STATUS					 current
		DESCRIPTION			 " -- "
		::=  { pucchEntry  16 }


	pucchCellSpsAckPucchNum		 OBJECT-TYPE
		SYNTAX					 Integer32( 0 .. 200 )
		MAX-ACCESS			 read-create
		STATUS					 current
		DESCRIPTION			 " -- "
		::=  { pucchEntry  17 }


	pucchCellPucch1bcsNum		 OBJECT-TYPE
		SYNTAX					 Integer32( 0 .. 200 )
		MAX-ACCESS			 read-create
		STATUS					 current
		DESCRIPTION			 " -- "
		::=  { pucchEntry  18 }


	pucchSrPucchNumPerPRB		 OBJECT-TYPE
		SYNTAX					 INTEGER{ num12(0),num18(1),num36(2)  }
		MAX-ACCESS			 read-create
		STATUS					 current
		DESCRIPTION			 " -- "
		::=  { pucchEntry  19 }


	raTable		 OBJECT-TYPE
		SYNTAX					 SEQUENCE  OF	 RaEntry
		MAX-ACCESS			 not-accessible
		STATUS					 current
		DESCRIPTION			 " -- "
		::=  { chandPrCfg  5 }


	raEntry		 OBJECT-TYPE
		SYNTAX					 RaEntry
		MAX-ACCESS			 not-accessible
		STATUS					 current
		DESCRIPTION			 " -- "
		INDEX						{ raLcId }
		::=  { raTable  1 }


	RaEntry		 ::=  SEQUENCE {
		raLcId					Integer32,
		raRowStatus					RowStatus,
		raPreamblesNum					INTEGER,
		raSizeofPreamblesAFlag					INTEGER,
		raSizeofPreamblesGroupA					INTEGER,
		raMessageSizeGroupA					INTEGER,
		raMessagePowerOffsetGroupB					INTEGER,
		raPowerRampStep					INTEGER,
		raPreambleInitRcvTargetPow					INTEGER,
		raPreambleTrMax					INTEGER,
		raRspWindowSize					INTEGER,
		raMaxContentRslutTimer					INTEGER,
		raMaxMsg3Tx					Integer32,
		raRootSeqIndex					Integer32,
		raPrachCfgIndex					Integer32,
		raHiSpeedFlag					INTEGER,
		raZeroCorrelatZoneCfg					Integer32,
		raPrachFreqOffset					Integer32
		}


	raLcId		 OBJECT-TYPE
		SYNTAX					 Integer32( 0 .. 23 )
		MAX-ACCESS			 not-accessible
		STATUS					 current
		DESCRIPTION			 " -- "
		::=  { raEntry  1 }


	raRowStatus		 OBJECT-TYPE
		SYNTAX					 RowStatus
		MAX-ACCESS			 read-create
		STATUS					 current
		DESCRIPTION			 " -- "
		::=  { raEntry  2 }


	raPreamblesNum		 OBJECT-TYPE
		SYNTAX					 INTEGER{ n4(0),n8(1),n12(2),n16(3),n20(4),n24(5),n28(6),n32(7),n36(8),n40(9),n44(10),n48(11),n52(12),n56(13),n60(14),n64(15)  }
		MAX-ACCESS			 read-create
		STATUS					 current
		DESCRIPTION			 " -- "
		::=  { raEntry  3 }


	raSizeofPreamblesAFlag		 OBJECT-TYPE
		SYNTAX					 INTEGER{ false(0),true(1)  }
		MAX-ACCESS			 read-create
		STATUS					 current
		DESCRIPTION			 " -- "
		::=  { raEntry  4 }


	raSizeofPreamblesGroupA		 OBJECT-TYPE
		SYNTAX					 INTEGER{ n4(0),n8(1),n12(2),n16(3),n20(4),n24(5),n28(6),n32(7),n36(8),n40(9),n44(10),n48(11),n52(12),n56(13),n60(14)  }
		MAX-ACCESS			 read-create
		STATUS					 current
		DESCRIPTION			 " -- "
		::=  { raEntry  5 }


	raMessageSizeGroupA		 OBJECT-TYPE
		SYNTAX					 INTEGER{ b56(0),b144(1),b208(2),b256(3)  }
		MAX-ACCESS			 read-create
		STATUS					 current
		DESCRIPTION			 " -- "
		::=  { raEntry  6 }


	raMessagePowerOffsetGroupB		 OBJECT-TYPE
		SYNTAX					 INTEGER{ minusinfinity(0),dB0(1),dB5(2),dB8(3),dB10(4),dB12(5),dB15(6),dB18(7)  }
		MAX-ACCESS			 read-create
		STATUS					 current
		DESCRIPTION			 " -- "
		::=  { raEntry  7 }


	raPowerRampStep		 OBJECT-TYPE
		SYNTAX					 INTEGER{ dB0(0),dB2(1),dB4(2),dB6(3)  }
		MAX-ACCESS			 read-create
		STATUS					 current
		DESCRIPTION			 " -- "
		::=  { raEntry  8 }


	raPreambleInitRcvTargetPow		 OBJECT-TYPE
		SYNTAX					 INTEGER{ n120dBm(0),n118dBm(1),n116dBm(2),n114dBm(3),n112dBm(4),n110dBm(5),n108dBm(6),n106dBm(7),n104dBm(8),n102dBm(9),n100dBm(10),n98dBm(11),n96dBm(12),n94dBm(13),n92dBm(14),n90dBm(15)  }
		MAX-ACCESS			 read-create
		STATUS					 current
		DESCRIPTION			 " -- "
		::=  { raEntry  9 }


	raPreambleTrMax		 OBJECT-TYPE
		SYNTAX					 INTEGER{ n3(0),n4(1),n5(2),n6(3),n7(4),n8(5),n10(6),n20(7),n50(8),n100(9),n200(10)  }
		MAX-ACCESS			 read-create
		STATUS					 current
		DESCRIPTION			 " -- "
		::=  { raEntry  10 }


	raRspWindowSize		 OBJECT-TYPE
		SYNTAX					 INTEGER{ sf2(0),sf3(1),sf4(2),sf5(3),sf6(4),sf7(5),sf8(6),sf10(7)  }
		MAX-ACCESS			 read-create
		STATUS					 current
		DESCRIPTION			 " -- "
		::=  { raEntry  11 }


	raMaxContentRslutTimer		 OBJECT-TYPE
		SYNTAX					 INTEGER{ sf8(0),sf16(1),sf24(2),sf32(3),sf40(4),sf48(5),sf56(6),sf64(7)  }
		MAX-ACCESS			 read-create
		STATUS					 current
		DESCRIPTION			 " -- "
		::=  { raEntry  12 }


	raMaxMsg3Tx		 OBJECT-TYPE
		SYNTAX					 Integer32( 1 .. 8 )
		MAX-ACCESS			 read-create
		STATUS					 current
		DESCRIPTION			 " -- "
		::=  { raEntry  13 }


	raRootSeqIndex		 OBJECT-TYPE
		SYNTAX					 Integer32( 0 .. 837 )
		MAX-ACCESS			 read-create
		STATUS					 current
		DESCRIPTION			 " -- "
		::=  { raEntry  14 }


	raPrachCfgIndex		 OBJECT-TYPE
		SYNTAX					 Integer32( 0 .. 63 )
		MAX-ACCESS			 read-create
		STATUS					 current
		DESCRIPTION			 " -- "
		::=  { raEntry  15 }


	raHiSpeedFlag		 OBJECT-TYPE
		SYNTAX					 INTEGER{ false(0),true(1)  }
		MAX-ACCESS			 read-create
		STATUS					 current
		DESCRIPTION			 " -- "
		::=  { raEntry  16 }


	raZeroCorrelatZoneCfg		 OBJECT-TYPE
		SYNTAX					 Integer32( 0 .. 15 )
		MAX-ACCESS			 read-create
		STATUS					 current
		DESCRIPTION			 " -- "
		::=  { raEntry  17 }


	raPrachFreqOffset		 OBJECT-TYPE
		SYNTAX					 Integer32( 0 .. 94 )
		MAX-ACCESS			 read-create
		STATUS					 current
		DESCRIPTION			 " -- "
		::=  { raEntry  18 }


	soundingRSTable		 OBJECT-TYPE
		SYNTAX					 SEQUENCE  OF	 SoundingRSEntry
		MAX-ACCESS			 not-accessible
		STATUS					 current
		DESCRIPTION			 " -- "
		::=  { chandPrCfg  6 }


	soundingRSEntry		 OBJECT-TYPE
		SYNTAX					 SoundingRSEntry
		MAX-ACCESS			 not-accessible
		STATUS					 current
		DESCRIPTION			 " -- "
		INDEX						{ srsLcId }
		::=  { soundingRSTable  1 }


	SoundingRSEntry		 ::=  SEQUENCE {
		srsLcId					Integer32,
		srsRowStatus					RowStatus,
		srsSimTXAckNackAndSRS					INTEGER,
		srsMaxUpPtsFlag					INTEGER,
		srsDuration					INTEGER,
		srsHoppingBandWidth					INTEGER,
		srsBandWidthCenter					INTEGER,
		srsBandWidthEdge					INTEGER,
		srsValidNofCycShift					Integer32,
		srsCycshift0					INTEGER,
		srsCycshift1					INTEGER,
		srsCycshift2					INTEGER,
		srsCycshift3					INTEGER,
		srsCycshift4					INTEGER,
		srsCycshift5					INTEGER,
		srsCycshift6					INTEGER,
		srsCycshift7					INTEGER,
		srsSubFrmCfgChoice					INTEGER,
		srsAntannePort					INTEGER,
		srsDci4AntannePortAp					INTEGER,
		srsDci0AntannePortAp					INTEGER,
		srsDci1a2b2cAntannePortAp					INTEGER
		}


	srsLcId		 OBJECT-TYPE
		SYNTAX					 Integer32( 0 .. 23 )
		MAX-ACCESS			 not-accessible
		STATUS					 current
		DESCRIPTION			 " -- "
		::=  { soundingRSEntry  1 }


	srsRowStatus		 OBJECT-TYPE
		SYNTAX					 RowStatus
		MAX-ACCESS			 read-create
		STATUS					 current
		DESCRIPTION			 " -- "
		::=  { soundingRSEntry  2 }


	srsSimTXAckNackAndSRS		 OBJECT-TYPE
		SYNTAX					 INTEGER{ false(0),true(1)  }
		MAX-ACCESS			 read-create
		STATUS					 current
		DESCRIPTION			 " -- "
		::=  { soundingRSEntry  3 }


	srsMaxUpPtsFlag		 OBJECT-TYPE
		SYNTAX					 INTEGER{ false(0),true(1)  }
		MAX-ACCESS			 read-create
		STATUS					 current
		DESCRIPTION			 " -- "
		::=  { soundingRSEntry  4 }


	srsDuration		 OBJECT-TYPE
		SYNTAX					 INTEGER{ once(0),forever(1)  }
		MAX-ACCESS			 read-create
		STATUS					 current
		DESCRIPTION			 " -- "
		::=  { soundingRSEntry  5 }


	srsHoppingBandWidth		 OBJECT-TYPE
		SYNTAX					 INTEGER{ bw0(0),bw1(1),bw2(2),bw3(3)  }
		MAX-ACCESS			 read-create
		STATUS					 current
		DESCRIPTION			 " -- "
		::=  { soundingRSEntry  7 }


	srsBandWidthCenter		 OBJECT-TYPE
		SYNTAX					 INTEGER{ bw0(0),bw1(1),bw2(2),bw3(3)  }
		MAX-ACCESS			 read-create
		STATUS					 current
		DESCRIPTION			 " -- "
		::=  { soundingRSEntry  8 }


	srsBandWidthEdge		 OBJECT-TYPE
		SYNTAX					 INTEGER{ bw0(0),bw1(1),bw2(2),bw3(3)  }
		MAX-ACCESS			 read-create
		STATUS					 current
		DESCRIPTION			 " -- "
		::=  { soundingRSEntry  9 }


	srsValidNofCycShift		 OBJECT-TYPE
		SYNTAX					 Integer32( 1 .. 8 )
		MAX-ACCESS			 read-create
		STATUS					 current
		DESCRIPTION			 " -- "
		::=  { soundingRSEntry  10 }


	srsCycshift0		 OBJECT-TYPE
		SYNTAX					 INTEGER{ cs0(0),cs1(1),cs2(2),cs3(3),cs4(4),cs5(5),cs6(6),cs7(7)  }
		MAX-ACCESS			 read-create
		STATUS					 current
		DESCRIPTION			 " -- "
		::=  { soundingRSEntry  11 }


	srsCycshift1		 OBJECT-TYPE
		SYNTAX					 INTEGER{ cs0(0),cs1(1),cs2(2),cs3(3),cs4(4),cs5(5),cs6(6),cs7(7)  }
		MAX-ACCESS			 read-create
		STATUS					 current
		DESCRIPTION			 " -- "
		::=  { soundingRSEntry  12 }


	srsCycshift2		 OBJECT-TYPE
		SYNTAX					 INTEGER{ cs0(0),cs1(1),cs2(2),cs3(3),cs4(4),cs5(5),cs6(6),cs7(7)  }
		MAX-ACCESS			 read-create
		STATUS					 current
		DESCRIPTION			 " -- "
		::=  { soundingRSEntry  13 }


	srsCycshift3		 OBJECT-TYPE
		SYNTAX					 INTEGER{ cs0(0),cs1(1),cs2(2),cs3(3),cs4(4),cs5(5),cs6(6),cs7(7)  }
		MAX-ACCESS			 read-create
		STATUS					 current
		DESCRIPTION			 " -- "
		::=  { soundingRSEntry  14 }


	srsCycshift4		 OBJECT-TYPE
		SYNTAX					 INTEGER{ cs0(0),cs1(1),cs2(2),cs3(3),cs4(4),cs5(5),cs6(6),cs7(7)  }
		MAX-ACCESS			 read-create
		STATUS					 current
		DESCRIPTION			 " -- "
		::=  { soundingRSEntry  15 }


	srsCycshift5		 OBJECT-TYPE
		SYNTAX					 INTEGER{ cs0(0),cs1(1),cs2(2),cs3(3),cs4(4),cs5(5),cs6(6),cs7(7)  }
		MAX-ACCESS			 read-create
		STATUS					 current
		DESCRIPTION			 " -- "
		::=  { soundingRSEntry  16 }


	srsCycshift6		 OBJECT-TYPE
		SYNTAX					 INTEGER{ cs0(0),cs1(1),cs2(2),cs3(3),cs4(4),cs5(5),cs6(6),cs7(7)  }
		MAX-ACCESS			 read-create
		STATUS					 current
		DESCRIPTION			 " -- "
		::=  { soundingRSEntry  17 }


	srsCycshift7		 OBJECT-TYPE
		SYNTAX					 INTEGER{ cs0(0),cs1(1),cs2(2),cs3(3),cs4(4),cs5(5),cs6(6),cs7(7)  }
		MAX-ACCESS			 read-create
		STATUS					 current
		DESCRIPTION			 " -- "
		::=  { soundingRSEntry  18 }


	srsSubFrmCfgChoice		 OBJECT-TYPE
		SYNTAX					 INTEGER{ onlyUppts(0),onlyNormalSubFrame(1),notLimit(2)  }
		MAX-ACCESS			 read-create
		STATUS					 current
		DESCRIPTION			 " -- "
		::=  { soundingRSEntry  23 }


	srsAntannePort		 OBJECT-TYPE
		SYNTAX					 INTEGER{ an0(0),an1(1),an2(2),an4(3)  }
		MAX-ACCESS			 read-create
		STATUS					 current
		DESCRIPTION			 " -- "
		::=  { soundingRSEntry  24 }


	srsDci4AntannePortAp		 OBJECT-TYPE
		SYNTAX					 INTEGER{ an0(0),an1(1),an2(2),an4(3)  }
		MAX-ACCESS			 read-create
		STATUS					 current
		DESCRIPTION			 " -- "
		::=  { soundingRSEntry  25 }


	srsDci0AntannePortAp		 OBJECT-TYPE
		SYNTAX					 INTEGER{ an0(0),an1(1),an2(2),an4(3)  }
		MAX-ACCESS			 read-create
		STATUS					 current
		DESCRIPTION			 " -- "
		::=  { soundingRSEntry  26 }


	srsDci1a2b2cAntannePortAp		 OBJECT-TYPE
		SYNTAX					 INTEGER{ an0(0),an1(1),an2(2),an4(3)  }
		MAX-ACCESS			 read-create
		STATUS					 current
		DESCRIPTION			 " -- "
		::=  { soundingRSEntry  27 }


	schedulingRequestTable		 OBJECT-TYPE
		SYNTAX					 SEQUENCE  OF	 SchedulingRequestEntry
		MAX-ACCESS			 not-accessible
		STATUS					 current
		DESCRIPTION			 " -- "
		::=  { chandPrCfg  7 }


	schedulingRequestEntry		 OBJECT-TYPE
		SYNTAX					 SchedulingRequestEntry
		MAX-ACCESS			 not-accessible
		STATUS					 current
		DESCRIPTION			 " -- "
		INDEX						{ srLcId }
		::=  { schedulingRequestTable  1 }


	SchedulingRequestEntry		 ::=  SEQUENCE {
		srLcId					Integer32,
		srRowStatus					RowStatus,
		srPeriodicity					INTEGER,
		srDsrTransMax					INTEGER,
		srTestSwitchsrAdaptive					INTEGER,
		srShortPeriodicity					INTEGER,
		srLargePeriodicityTh					Integer32,
		srShortPeriodicityTh					Integer32,
		srVolteMaxPeriodicity					INTEGER,
		srVoltePucchNum					Integer32
		}


	srLcId		 OBJECT-TYPE
		SYNTAX					 Integer32( 0 .. 23 )
		MAX-ACCESS			 not-accessible
		STATUS					 current
		DESCRIPTION			 " -- "
		::=  { schedulingRequestEntry  1 }


	srRowStatus		 OBJECT-TYPE
		SYNTAX					 RowStatus
		MAX-ACCESS			 read-create
		STATUS					 current
		DESCRIPTION			 " -- "
		::=  { schedulingRequestEntry  2 }


	srPeriodicity		 OBJECT-TYPE
		SYNTAX					 INTEGER{ ms5(0),ms10(1),ms20(2),ms40(3),ms80(4)  }
		MAX-ACCESS			 read-create
		STATUS					 current
		DESCRIPTION			 " -- "
		::=  { schedulingRequestEntry  3 }


	srDsrTransMax		 OBJECT-TYPE
		SYNTAX					 INTEGER{ n4(0),n8(1),n16(2),n32(3),n64(4)  }
		MAX-ACCESS			 read-create
		STATUS					 current
		DESCRIPTION			 " -- "
		::=  { schedulingRequestEntry  4 }


	srTestSwitchsrAdaptive		 OBJECT-TYPE
		SYNTAX					 INTEGER{ off(0),on(1)  }
		MAX-ACCESS			 read-create
		STATUS					 current
		DESCRIPTION			 " -- "
		::=  { schedulingRequestEntry  5 }


	srShortPeriodicity		 OBJECT-TYPE
		SYNTAX					 INTEGER{ ms5(0),ms10(1),ms20(2),ms40(3),ms80(4)  }
		MAX-ACCESS			 read-create
		STATUS					 current
		DESCRIPTION			 " -- "
		::=  { schedulingRequestEntry  6 }


	srLargePeriodicityTh		 OBJECT-TYPE
		SYNTAX					 Integer32( 0 .. 100 )
		MAX-ACCESS			 read-create
		STATUS					 current
		DESCRIPTION			 " -- "
		::=  { schedulingRequestEntry  7 }


	srShortPeriodicityTh		 OBJECT-TYPE
		SYNTAX					 Integer32( 0 .. 100 )
		MAX-ACCESS			 read-create
		STATUS					 current
		DESCRIPTION			 " -- "
		::=  { schedulingRequestEntry  8 }


	srVolteMaxPeriodicity		 OBJECT-TYPE
		SYNTAX					 INTEGER{ ms5(0),ms10(1),ms20(2),ms40(3),ms80(4)  }
		MAX-ACCESS			 read-create
		STATUS					 current
		DESCRIPTION			 " -- "
		::=  { schedulingRequestEntry  9 }


	srVoltePucchNum		 OBJECT-TYPE
		SYNTAX					 Integer32( 0 .. 400 )
		MAX-ACCESS			 read-create
		STATUS					 current
		DESCRIPTION			 " -- "
		::=  { schedulingRequestEntry  10 }


	cqiCfgTable		 OBJECT-TYPE
		SYNTAX					 SEQUENCE  OF	 CqiCfgEntry
		MAX-ACCESS			 not-accessible
		STATUS					 current
		DESCRIPTION			 " -- "
		::=  { chandPrCfg  8 }


	cqiCfgEntry		 OBJECT-TYPE
		SYNTAX					 CqiCfgEntry
		MAX-ACCESS			 not-accessible
		STATUS					 current
		DESCRIPTION			 " -- "
		INDEX						{ cqiLcId }
		::=  { cqiCfgTable  1 }


	CqiCfgEntry		 ::=  SEQUENCE {
		cqiLcId					Integer32,
		cqiRowStatus					RowStatus,
		cqiRbNum					Integer32,
		cqiFormatIndicatorAPeriodic					INTEGER,
		cqiNp					INTEGER,
		cqiNomPdschRsEpreOffset					INTEGER,
		cqiFormatIndicatorPeriodic					INTEGER,
		cqiK					Integer32,
		cqiM					INTEGER,
		cqiRiOffset					Integer32,
		cqiSimultaneousAckNackAndCqi					INTEGER,
		cqiValidNofPucch2PerPrb					Integer32,
		cqiPucch2Index0					Integer32,
		cqiPucch2Index1					Integer32,
		cqiPucch2Index2					Integer32,
		cqiPucch2Index3					Integer32,
		cqiPucch2Index4					Integer32,
		cqiPucch2Index5					Integer32,
		cqiPucch2Index6					Integer32,
		cqiPucch2Index7					Integer32,
		cqiPucch2Index8					Integer32,
		cqiPucch2Index9					Integer32,
		cqiPucch2Index10					Integer32,
		cqiPucch2Index11					Integer32,
		cqiTm9format1to1Submode					INTEGER,
		cqiTm8PmiRiReport					INTEGER
		}


	cqiLcId		 OBJECT-TYPE
		SYNTAX					 Integer32( 0 .. 23 )
		MAX-ACCESS			 not-accessible
		STATUS					 current
		DESCRIPTION			 " -- "
		::=  { cqiCfgEntry  1 }


	cqiRowStatus		 OBJECT-TYPE
		SYNTAX					 RowStatus
		MAX-ACCESS			 read-create
		STATUS					 current
		DESCRIPTION			 " -- "
		::=  { cqiCfgEntry  2 }


	cqiRbNum		 OBJECT-TYPE
		SYNTAX					 Integer32( 0 .. 98 )
		MAX-ACCESS			 read-create
		STATUS					 current
		DESCRIPTION			 " -- "
		::=  { cqiCfgEntry  3 }


	cqiFormatIndicatorAPeriodic		 OBJECT-TYPE
		SYNTAX					 INTEGER{ cqiAperiodicWideband(0),cqiAperiodicUeselected(1),cqiAperiodicHighlayerConfigured(2)  }
		MAX-ACCESS			 read-create
		STATUS					 current
		DESCRIPTION			 " -- "
		::=  { cqiCfgEntry  4 }


	cqiNp		 OBJECT-TYPE
		SYNTAX					 INTEGER{ ms1(0),ms5(1),ms10(2),ms20(3),ms40(4),ms80(5),ms160(6)  }
		MAX-ACCESS			 read-create
		STATUS					 current
		DESCRIPTION			 " -- "
		::=  { cqiCfgEntry  5 }


	cqiNomPdschRsEpreOffset		 OBJECT-TYPE
		SYNTAX					 INTEGER{ nompdschRsepreOffsetDbn2(0),nompdschRsepreOffsetDb0(1),nompdschRsepreOffsetDb2(2),nompdschRsepreOffsetDb4(3),nompdschRsepreOffsetDb6(4),nompdschRsepreOffsetDb8(5),nompdschRsepreOffsetDb10(6),nompdschRsepreOffsetDb12(7)  }
		MAX-ACCESS			 read-create
		STATUS					 current
		DESCRIPTION			 " -- "
		::=  { cqiCfgEntry  6 }


	cqiFormatIndicatorPeriodic		 OBJECT-TYPE
		SYNTAX					 INTEGER{ wideband(0),subband(1)  }
		MAX-ACCESS			 read-create
		STATUS					 current
		DESCRIPTION			 " -- "
		::=  { cqiCfgEntry  7 }


	cqiK		 OBJECT-TYPE
		SYNTAX					 Integer32( 1 .. 4 )
		MAX-ACCESS			 read-create
		STATUS					 current
		DESCRIPTION			 " -- "
		::=  { cqiCfgEntry  8 }


	cqiM		 OBJECT-TYPE
		SYNTAX					 INTEGER{ t1(0),t2(1),t4(2),t8(3),t16(4),t32(5)  }
		MAX-ACCESS			 read-create
		STATUS					 current
		DESCRIPTION			 " -- "
		::=  { cqiCfgEntry  9 }


	cqiRiOffset		 OBJECT-TYPE
		SYNTAX					 Integer32( -160 .. 0 )
		MAX-ACCESS			 read-create
		STATUS					 current
		DESCRIPTION			 " -- "
		::=  { cqiCfgEntry  10 }


	cqiSimultaneousAckNackAndCqi		 OBJECT-TYPE
		SYNTAX					 INTEGER{ false(0),true(1)  }
		MAX-ACCESS			 read-create
		STATUS					 current
		DESCRIPTION			 " -- "
		::=  { cqiCfgEntry  11 }


	cqiValidNofPucch2PerPrb		 OBJECT-TYPE
		SYNTAX					 Integer32( 1 .. 12 )
		MAX-ACCESS			 read-create
		STATUS					 current
		DESCRIPTION			 " -- "
		::=  { cqiCfgEntry  12 }


	cqiPucch2Index0		 OBJECT-TYPE
		SYNTAX					 Integer32( 0 .. 11 )
		MAX-ACCESS			 read-create
		STATUS					 current
		DESCRIPTION			 " -- "
		::=  { cqiCfgEntry  13 }


	cqiPucch2Index1		 OBJECT-TYPE
		SYNTAX					 Integer32( 0 .. 11 )
		MAX-ACCESS			 read-create
		STATUS					 current
		DESCRIPTION			 " -- "
		::=  { cqiCfgEntry  14 }


	cqiPucch2Index2		 OBJECT-TYPE
		SYNTAX					 Integer32( 0 .. 11 )
		MAX-ACCESS			 read-create
		STATUS					 current
		DESCRIPTION			 " -- "
		::=  { cqiCfgEntry  15 }


	cqiPucch2Index3		 OBJECT-TYPE
		SYNTAX					 Integer32( 0 .. 11 )
		MAX-ACCESS			 read-create
		STATUS					 current
		DESCRIPTION			 " -- "
		::=  { cqiCfgEntry  16 }


	cqiPucch2Index4		 OBJECT-TYPE
		SYNTAX					 Integer32( 0 .. 11 )
		MAX-ACCESS			 read-create
		STATUS					 current
		DESCRIPTION			 " -- "
		::=  { cqiCfgEntry  17 }


	cqiPucch2Index5		 OBJECT-TYPE
		SYNTAX					 Integer32( 0 .. 11 )
		MAX-ACCESS			 read-create
		STATUS					 current
		DESCRIPTION			 " -- "
		::=  { cqiCfgEntry  18 }


	cqiPucch2Index6		 OBJECT-TYPE
		SYNTAX					 Integer32( 0 .. 11 )
		MAX-ACCESS			 read-create
		STATUS					 current
		DESCRIPTION			 " -- "
		::=  { cqiCfgEntry  19 }


	cqiPucch2Index7		 OBJECT-TYPE
		SYNTAX					 Integer32( 0 .. 11 )
		MAX-ACCESS			 read-create
		STATUS					 current
		DESCRIPTION			 " -- "
		::=  { cqiCfgEntry  20 }


	cqiPucch2Index8		 OBJECT-TYPE
		SYNTAX					 Integer32( 0 .. 11 )
		MAX-ACCESS			 read-create
		STATUS					 current
		DESCRIPTION			 " -- "
		::=  { cqiCfgEntry  21 }


	cqiPucch2Index9		 OBJECT-TYPE
		SYNTAX					 Integer32( 0 .. 11 )
		MAX-ACCESS			 read-create
		STATUS					 current
		DESCRIPTION			 " -- "
		::=  { cqiCfgEntry  22 }


	cqiPucch2Index10		 OBJECT-TYPE
		SYNTAX					 Integer32( 0 .. 11 )
		MAX-ACCESS			 read-create
		STATUS					 current
		DESCRIPTION			 " -- "
		::=  { cqiCfgEntry  23 }


	cqiPucch2Index11		 OBJECT-TYPE
		SYNTAX					 Integer32( 0 .. 11 )
		MAX-ACCESS			 read-create
		STATUS					 current
		DESCRIPTION			 " -- "
		::=  { cqiCfgEntry  24 }


	cqiTm9format1to1Submode		 OBJECT-TYPE
		SYNTAX					 INTEGER{ mode1(0),mode2(1)  }
		MAX-ACCESS			 read-create
		STATUS					 current
		DESCRIPTION			 " -- "
		::=  { cqiCfgEntry  25 }


	cqiTm8PmiRiReport		 OBJECT-TYPE
		SYNTAX					 INTEGER{ tm8NoPmiRiReport(0),tm8PmiRiReport(1)  }
		MAX-ACCESS			 read-create
		STATUS					 current
		DESCRIPTION			 " -- "
		::=  { cqiCfgEntry  27 }


	spsCfgTable		 OBJECT-TYPE
		SYNTAX					 SEQUENCE  OF	 SpsCfgEntry
		MAX-ACCESS			 not-accessible
		STATUS					 current
		DESCRIPTION			 " -- "
		::=  { chandPrCfg  9 }


	spsCfgEntry		 OBJECT-TYPE
		SYNTAX					 SpsCfgEntry
		MAX-ACCESS			 not-accessible
		STATUS					 current
		DESCRIPTION			 " -- "
		INDEX						{ spsLcId }
		::=  { spsCfgTable  1 }


	SpsCfgEntry		 ::=  SEQUENCE {
		spsLcId					Integer32,
		spsRowStatus					RowStatus,
		spsIntervalDl					INTEGER,
		spsProcNum					Integer32,
		spsIntervalUl					INTEGER,
		spsImplicitRelAfter					INTEGER,
		spsP0NominalPuschPersist					Integer32,
		spsP0UePuschPersist					Integer32,
		spsTwoIntervalsCfg					INTEGER,
		spsSwitchFlag					INTEGER,
		spsPucchAnPersistent					Integer32,
		spsUeNumAnPersistent					Integer32
		}


	spsLcId		 OBJECT-TYPE
		SYNTAX					 Integer32( 0 .. 23 )
		MAX-ACCESS			 not-accessible
		STATUS					 current
		DESCRIPTION			 " -- "
		::=  { spsCfgEntry  1 }


	spsRowStatus		 OBJECT-TYPE
		SYNTAX					 RowStatus
		MAX-ACCESS			 read-create
		STATUS					 current
		DESCRIPTION			 " -- "
		::=  { spsCfgEntry  2 }


	spsIntervalDl		 OBJECT-TYPE
		SYNTAX					 INTEGER{ sf10(0),sf20(1),sf32(2),sf40(3),sf64(4),sf80(5),sf128(6),sf160(7),sf320(8),sf640(9)  }
		MAX-ACCESS			 read-create
		STATUS					 current
		DESCRIPTION			 " -- "
		::=  { spsCfgEntry  3 }


	spsProcNum		 OBJECT-TYPE
		SYNTAX					 Integer32( 1 .. 8 )
		MAX-ACCESS			 read-create
		STATUS					 current
		DESCRIPTION			 " -- "
		::=  { spsCfgEntry  4 }


	spsIntervalUl		 OBJECT-TYPE
		SYNTAX					 INTEGER{ sf10(0),sf20(1),sf32(2),sf40(3),sf64(4),sf80(5),sf128(6),sf160(7),sf320(8),sf640(9)  }
		MAX-ACCESS			 read-create
		STATUS					 current
		DESCRIPTION			 " -- "
		::=  { spsCfgEntry  5 }


	spsImplicitRelAfter		 OBJECT-TYPE
		SYNTAX					 INTEGER{ e2(0),e3(1),e4(2),e8(3)  }
		MAX-ACCESS			 read-create
		STATUS					 current
		DESCRIPTION			 " -- "
		::=  { spsCfgEntry  6 }


	spsP0NominalPuschPersist		 OBJECT-TYPE
		SYNTAX					 Integer32( -126 .. 24 )
		MAX-ACCESS			 read-create
		STATUS					 current
		DESCRIPTION			 " -- "
		::=  { spsCfgEntry  7 }


	spsP0UePuschPersist		 OBJECT-TYPE
		SYNTAX					 Integer32( -8 .. 7 )
		MAX-ACCESS			 read-create
		STATUS					 current
		DESCRIPTION			 " -- "
		::=  { spsCfgEntry  8 }


	spsTwoIntervalsCfg		 OBJECT-TYPE
		SYNTAX					 INTEGER{ false(0),true(1)  }
		MAX-ACCESS			 read-create
		STATUS					 current
		DESCRIPTION			 " -- "
		::=  { spsCfgEntry  9 }


	spsSwitchFlag		 OBJECT-TYPE
		SYNTAX					 INTEGER{ close(0),open(1)  }
		MAX-ACCESS			 read-create
		STATUS					 current
		DESCRIPTION			 " -- "
		::=  { spsCfgEntry  10 }


	spsPucchAnPersistent		 OBJECT-TYPE
		SYNTAX					 Integer32( 1 .. 4 )
		MAX-ACCESS			 read-create
		STATUS					 current
		DESCRIPTION			 " -- "
		::=  { spsCfgEntry  11 }


	spsUeNumAnPersistent		 OBJECT-TYPE
		SYNTAX					 Integer32( 1 .. 32 )
		MAX-ACCESS			 read-create
		STATUS					 current
		DESCRIPTION			 " -- "
		::=  { spsCfgEntry  12 }


	harqTable		 OBJECT-TYPE
		SYNTAX					 SEQUENCE  OF	 HarqEntry
		MAX-ACCESS			 not-accessible
		STATUS					 current
		DESCRIPTION			 " -- "
		::=  { chandPrCfg  10 }


	harqEntry		 OBJECT-TYPE
		SYNTAX					 HarqEntry
		MAX-ACCESS			 not-accessible
		STATUS					 current
		DESCRIPTION			 " -- "
		INDEX						{ harqLcId }
		::=  { harqTable  1 }


	HarqEntry		 ::=  SEQUENCE {
		harqLcId					Integer32,
		harqRowStatus					RowStatus,
		harqRb0TxNum					Integer32,
		harqMaxUlTx					INTEGER,
		harqMaxDlTx					Integer32,
		harqMaxUlTxTtiBundling					INTEGER
		}


	harqLcId		 OBJECT-TYPE
		SYNTAX					 Integer32( 0 .. 23 )
		MAX-ACCESS			 not-accessible
		STATUS					 current
		DESCRIPTION			 " -- "
		::=  { harqEntry  1 }


	harqRowStatus		 OBJECT-TYPE
		SYNTAX					 RowStatus
		MAX-ACCESS			 read-create
		STATUS					 current
		DESCRIPTION			 " -- "
		::=  { harqEntry  2 }


	harqRb0TxNum		 OBJECT-TYPE
		SYNTAX					 Integer32( 0 .. 255 )
		MAX-ACCESS			 read-create
		STATUS					 current
		DESCRIPTION			 " -- "
		::=  { harqEntry  3 }


	harqMaxUlTx		 OBJECT-TYPE
		SYNTAX					 INTEGER{ n1(0),n2(1),n3(2),n4(3),n5(4),n6(5),n7(6),n8(7),n10(8),n12(9),n16(10),n20(11),n24(12),n28(13)  }
		MAX-ACCESS			 read-create
		STATUS					 current
		DESCRIPTION			 " -- "
		::=  { harqEntry  4 }


	harqMaxDlTx		 OBJECT-TYPE
		SYNTAX					 Integer32( 1 .. 28 )
		MAX-ACCESS			 read-create
		STATUS					 current
		DESCRIPTION			 " -- "
		::=  { harqEntry  5 }


	harqMaxUlTxTtiBundling		 OBJECT-TYPE
		SYNTAX					 INTEGER{ n4(3),n8(7),n12(9),n16(10)  }
		MAX-ACCESS			 read-create
		STATUS					 current
		DESCRIPTION			 " -- "
		::=  { harqEntry  7 }


	phrTable		 OBJECT-TYPE
		SYNTAX					 SEQUENCE  OF	 PhrEntry
		MAX-ACCESS			 not-accessible
		STATUS					 current
		DESCRIPTION			 " -- "
		::=  { chandPrCfg  12 }


	phrEntry		 OBJECT-TYPE
		SYNTAX					 PhrEntry
		MAX-ACCESS			 not-accessible
		STATUS					 current
		DESCRIPTION			 " -- "
		INDEX						{ phrLcId }
		::=  { phrTable  1 }


	PhrEntry		 ::=  SEQUENCE {
		phrLcId					Integer32,
		phrRowStatus					RowStatus,
		phrPeriodicimer					INTEGER,
		phrProhibitTimer					INTEGER,
		phrDlPathlossChange					INTEGER
		}


	phrLcId		 OBJECT-TYPE
		SYNTAX					 Integer32( 0 .. 23 )
		MAX-ACCESS			 not-accessible
		STATUS					 current
		DESCRIPTION			 " -- "
		::=  { phrEntry  1 }


	phrRowStatus		 OBJECT-TYPE
		SYNTAX					 RowStatus
		MAX-ACCESS			 read-create
		STATUS					 current
		DESCRIPTION			 " -- "
		::=  { phrEntry  2 }


	phrPeriodicimer		 OBJECT-TYPE
		SYNTAX					 INTEGER{ sf10(0),sf20(1),sf50(2),sf100(3),sf200(4),sf500(5),sf1000(6),sfInfinity(7)  }
		MAX-ACCESS			 read-create
		STATUS					 current
		DESCRIPTION			 " -- "
		::=  { phrEntry  3 }


	phrProhibitTimer		 OBJECT-TYPE
		SYNTAX					 INTEGER{ sf0(0),sf10(1),sf20(2),sf50(3),sf100(4),sf200(5),sf500(6),sf1000(7)  }
		MAX-ACCESS			 read-create
		STATUS					 current
		DESCRIPTION			 " -- "
		::=  { phrEntry  4 }


	phrDlPathlossChange		 OBJECT-TYPE
		SYNTAX					 INTEGER{ dB1(0),dB3(1),dB6(2),infinity(3)  }
		MAX-ACCESS			 read-create
		STATUS					 current
		DESCRIPTION			 " -- "
		::=  { phrEntry  5 }


	taTable		 OBJECT-TYPE
		SYNTAX					 SEQUENCE  OF	 TaEntry
		MAX-ACCESS			 not-accessible
		STATUS					 current
		DESCRIPTION			 " -- "
		::=  { chandPrCfg  13 }


	taEntry		 OBJECT-TYPE
		SYNTAX					 TaEntry
		MAX-ACCESS			 not-accessible
		STATUS					 current
		DESCRIPTION			 " -- "
		INDEX						{ taLcId }
		::=  { taTable  1 }


	TaEntry		 ::=  SEQUENCE {
		taLcId					Integer32,
		taRowStatus					RowStatus,
		tatimerCommon					INTEGER,
		tatimerDedicated					INTEGER
		}


	taLcId		 OBJECT-TYPE
		SYNTAX					 Integer32( 0 .. 23 )
		MAX-ACCESS			 not-accessible
		STATUS					 current
		DESCRIPTION			 " -- "
		::=  { taEntry  1 }


	taRowStatus		 OBJECT-TYPE
		SYNTAX					 RowStatus
		MAX-ACCESS			 read-create
		STATUS					 current
		DESCRIPTION			 " -- "
		::=  { taEntry  2 }


	tatimerCommon		 OBJECT-TYPE
		SYNTAX					 INTEGER{ sf500(0),sf750(1),sf1280(2),sf1920(3),sf2560(4),sf5120(5),sf10240(6),infinity(7)  }
		MAX-ACCESS			 read-create
		STATUS					 current
		DESCRIPTION			 " -- "
		::=  { taEntry  3 }


	tatimerDedicated		 OBJECT-TYPE
		SYNTAX					 INTEGER{ sf500(0),sf750(1),sf1280(2),sf1920(3),sf2560(4),sf5120(5),sf10240(6),infinity(7)  }
		MAX-ACCESS			 read-create
		STATUS					 current
		DESCRIPTION			 " -- "
		::=  { taEntry  4 }


	bsrTable		 OBJECT-TYPE
		SYNTAX					 SEQUENCE  OF	 BsrEntry
		MAX-ACCESS			 not-accessible
		STATUS					 current
		DESCRIPTION			 " -- "
		::=  { chandPrCfg  14 }


	bsrEntry		 OBJECT-TYPE
		SYNTAX					 BsrEntry
		MAX-ACCESS			 not-accessible
		STATUS					 current
		DESCRIPTION			 " -- "
		INDEX						{ bsrLcId }
		::=  { bsrTable  1 }


	BsrEntry		 ::=  SEQUENCE {
		bsrLcId					Integer32,
		bsrRowStatus					RowStatus,
		bsrReTx					INTEGER,
		bsrPeriodicTimer					INTEGER
		}


	bsrLcId		 OBJECT-TYPE
		SYNTAX					 Integer32( 0 .. 23 )
		MAX-ACCESS			 not-accessible
		STATUS					 current
		DESCRIPTION			 " -- "
		::=  { bsrEntry  1 }


	bsrRowStatus		 OBJECT-TYPE
		SYNTAX					 RowStatus
		MAX-ACCESS			 read-create
		STATUS					 current
		DESCRIPTION			 " -- "
		::=  { bsrEntry  2 }


	bsrReTx		 OBJECT-TYPE
		SYNTAX					 INTEGER{ sf320(0),sf640(1),sf1280(2),sf2560(3),sf5120(4),sf10240(5)  }
		MAX-ACCESS			 read-create
		STATUS					 current
		DESCRIPTION			 " -- "
		::=  { bsrEntry  3 }


	bsrPeriodicTimer		 OBJECT-TYPE
		SYNTAX					 INTEGER{ sf5(0),sf10(1),sf16(2),sf20(3),sf32(4),sf40(5),sf64(6),sf80(7),sf128(8),sf160(9),sf320(10),sf640(11),sf1280(12),sf2560(13),infinity(14)  }
		MAX-ACCESS			 read-create
		STATUS					 current
		DESCRIPTION			 " -- "
		::=  { bsrEntry  4 }


	pagingTable		 OBJECT-TYPE
		SYNTAX					 SEQUENCE  OF	 PagingEntry
		MAX-ACCESS			 not-accessible
		STATUS					 current
		DESCRIPTION			 " -- "
		::=  { chandPrCfg  15 }


	pagingEntry		 OBJECT-TYPE
		SYNTAX					 PagingEntry
		MAX-ACCESS			 not-accessible
		STATUS					 current
		DESCRIPTION			 " -- "
		INDEX						{ pagingLcId }
		::=  { pagingTable  1 }


	PagingEntry		 ::=  SEQUENCE {
		pagingLcId					Integer32,
		pagingRowStatus					RowStatus,
		pagingNB					INTEGER
		}


	pagingLcId		 OBJECT-TYPE
		SYNTAX					 Integer32( 0 .. 23 )
		MAX-ACCESS			 not-accessible
		STATUS					 current
		DESCRIPTION			 " -- "
		::=  { pagingEntry  1 }


	pagingRowStatus		 OBJECT-TYPE
		SYNTAX					 RowStatus
		MAX-ACCESS			 read-create
		STATUS					 current
		DESCRIPTION			 " -- "
		::=  { pagingEntry  2 }


	pagingNB		 OBJECT-TYPE
		SYNTAX					 INTEGER{ fourT(0),twoT(1),oneT(2),halfT(3),quarterT(4),oneEightT(5),onSixteenthT(6),oneThirtySecondT(7)  }
		MAX-ACCESS			 read-create
		STATUS					 current
		DESCRIPTION			 " -- "
		::=  { pagingEntry  3 }


	anteTable		 OBJECT-TYPE
		SYNTAX					 SEQUENCE  OF	 AnteEntry
		MAX-ACCESS			 not-accessible
		STATUS					 current
		DESCRIPTION			 " -- "
		::=  { chandPrCfg  16 }


	anteEntry		 OBJECT-TYPE
		SYNTAX					 AnteEntry
		MAX-ACCESS			 not-accessible
		STATUS					 current
		DESCRIPTION			 " -- "
		INDEX						{ anteLcId }
		::=  { anteTable  1 }


	AnteEntry		 ::=  SEQUENCE {
		anteLcId					Integer32,
		anteRowStatus					RowStatus,
		anteTransmissionMode					INTEGER,
		anteCodeBookSubsetRestrictLow					Unsigned32,
		anteCodeBookSubsetRestrictHigh					Unsigned32,
		anteInfoDediFlag					INTEGER,
		anteTransAntennaSel					INTEGER,
		anteTransmissionModeUL					INTEGER
		}


	anteLcId		 OBJECT-TYPE
		SYNTAX					 Integer32( 0 .. 23 )
		MAX-ACCESS			 not-accessible
		STATUS					 current
		DESCRIPTION			 " -- "
		::=  { anteEntry  1 }


	anteRowStatus		 OBJECT-TYPE
		SYNTAX					 RowStatus
		MAX-ACCESS			 read-create
		STATUS					 current
		DESCRIPTION			 " -- "
		::=  { anteEntry  2 }


	anteTransmissionMode		 OBJECT-TYPE
		SYNTAX					 INTEGER{ tm1(0),tm2(1),tm3(2),tm4(3),tm5(4),tm6(5),tm7(6),tm8(7),tm9(8)  }
		MAX-ACCESS			 read-create
		STATUS					 current
		DESCRIPTION			 " -- "
		::=  { anteEntry  3 }


	anteCodeBookSubsetRestrictLow		 OBJECT-TYPE
		SYNTAX					 Unsigned32( 0 .. 4294967295 )
		MAX-ACCESS			 read-create
		STATUS					 current
		DESCRIPTION			 " -- "
		::=  { anteEntry  4 }


	anteCodeBookSubsetRestrictHigh		 OBJECT-TYPE
		SYNTAX					 Unsigned32( 0 .. 4294967295 )
		MAX-ACCESS			 read-create
		STATUS					 current
		DESCRIPTION			 " -- "
		::=  { anteEntry  5 }


	anteInfoDediFlag		 OBJECT-TYPE
		SYNTAX					 INTEGER{ explicit(0),default(1),notPresent(2)  }
		MAX-ACCESS			 read-create
		STATUS					 current
		DESCRIPTION			 " -- "
		::=  { anteEntry  6 }


	anteTransAntennaSel		 OBJECT-TYPE
		SYNTAX					 INTEGER{ release(-1),closedLoop(0),openLoop(1)  }
		MAX-ACCESS			 read-create
		STATUS					 current
		DESCRIPTION			 " -- "
		::=  { anteEntry  7 }


	anteTransmissionModeUL		 OBJECT-TYPE
		SYNTAX					 INTEGER{ tm1(0),tm2(1)  }
		MAX-ACCESS			 read-create
		STATUS					 current
		DESCRIPTION			 " -- "
		::=  { anteEntry  8 }


	mbmsTable		 OBJECT-TYPE
		SYNTAX					 SEQUENCE  OF	 MbmsEntry
		MAX-ACCESS			 not-accessible
		STATUS					 current
		DESCRIPTION			 " -- "
		::=  { chandPrCfg  17 }


	mbmsEntry		 OBJECT-TYPE
		SYNTAX					 MbmsEntry
		MAX-ACCESS			 not-accessible
		STATUS					 current
		DESCRIPTION			 " -- "
		INDEX						{ mbmsLcId }
		::=  { mbmsTable  1 }


	MbmsEntry		 ::=  SEQUENCE {
		mbmsLcId					Integer32,
		mbmsRowStatus					RowStatus,
		mbmssfnFlag					INTEGER,
		mbmsRadioFrmAllcPeriod					INTEGER,
		mbmsRadioFrmAllcOffset					Integer32,
		mbmsSubFrmAllc					Integer32,
		mbmsSubFrmAllcChoice					INTEGER,
		mbmsSubFrmAllcOneFrame					BITS,
		mbmsSubFrmAllcFourFrames					Unsigned32
		}


	mbmsLcId		 OBJECT-TYPE
		SYNTAX					 Integer32( 0 .. 23 )
		MAX-ACCESS			 not-accessible
		STATUS					 current
		DESCRIPTION			 " -- "
		::=  { mbmsEntry  1 }


	mbmsRowStatus		 OBJECT-TYPE
		SYNTAX					 RowStatus
		MAX-ACCESS			 read-create
		STATUS					 current
		DESCRIPTION			 " -- "
		::=  { mbmsEntry  2 }


	mbmssfnFlag		 OBJECT-TYPE
		SYNTAX					 INTEGER{ false(0),true(1)  }
		MAX-ACCESS			 read-create
		STATUS					 current
		DESCRIPTION			 " -- "
		::=  { mbmsEntry  3 }


	mbmsRadioFrmAllcPeriod		 OBJECT-TYPE
		SYNTAX					 INTEGER{ n1(0),n2(1),n4(2),n8(3),n16(4),n32(5)  }
		MAX-ACCESS			 read-create
		STATUS					 current
		DESCRIPTION			 " -- "
		::=  { mbmsEntry  4 }


	mbmsRadioFrmAllcOffset		 OBJECT-TYPE
		SYNTAX					 Integer32( 0 .. 7 )
		MAX-ACCESS			 read-create
		STATUS					 current
		DESCRIPTION			 " -- "
		::=  { mbmsEntry  5 }


	mbmsSubFrmAllc		 OBJECT-TYPE
		SYNTAX					 Integer32( 1 .. 7 )
		MAX-ACCESS			 read-create
		STATUS					 current
		DESCRIPTION			 " -- "
		::=  { mbmsEntry  6 }


	mbmsSubFrmAllcChoice		 OBJECT-TYPE
		SYNTAX					 INTEGER{ oneframe(0),fourframes(1)  }
		MAX-ACCESS			 read-create
		STATUS					 current
		DESCRIPTION			 " -- "
		::=  { mbmsEntry  7 }


	mbmsSubFrmAllcOneFrame		 OBJECT-TYPE
		SYNTAX					 BITS{ sfn9(1),sfn8(2),sfn7(3),sfn4(4),sfn3(5)  }
		MAX-ACCESS			 read-create
		STATUS					 current
		DESCRIPTION			 " -- "
		::=  { mbmsEntry  8 }


	mbmsSubFrmAllcFourFrames		 OBJECT-TYPE
		SYNTAX					 Unsigned32( 0 .. 16777215 )
		MAX-ACCESS			 read-create
		STATUS					 current
		DESCRIPTION			 " -- "
		::=  { mbmsEntry  9 }


	drxQciTable		 OBJECT-TYPE
		SYNTAX					 SEQUENCE  OF	 DrxQciEntry
		MAX-ACCESS			 not-accessible
		STATUS					 current
		DESCRIPTION			 " -- "
		::=  { chandPrCfg  18 }


	drxQciEntry		 OBJECT-TYPE
		SYNTAX					 DrxQciEntry
		MAX-ACCESS			 not-accessible
		STATUS					 current
		DESCRIPTION			 " -- "
		INDEX						{ drxQciLcId,drxQciQci }
		::=  { drxQciTable  1 }


	DrxQciEntry		 ::=  SEQUENCE {
		drxQciLcId					Integer32,
		drxQciQci					Integer32,
		drxQciRowStatus					RowStatus,
		drxQciFlag					INTEGER,
		drxQciOnDurationTimer					INTEGER,
		drxQciInactivityTimer					INTEGER,
		drxQciRetransmissionTimer					INTEGER,
		drxQciLongCycle					INTEGER,
		drxQciShortCycle					INTEGER,
		drxQciShortCycleTimer					Integer32,
		drxQciShortFlag					INTEGER,
		drxQciOnDurationTimerB					INTEGER,
		drxQciInactivityTimerB					INTEGER,
		drxQciRetransmissionTimerB					INTEGER,
		drxQciLongCycleB					INTEGER
		}


	drxQciLcId		 OBJECT-TYPE
		SYNTAX					 Integer32( 0 .. 23 )
		MAX-ACCESS			 not-accessible
		STATUS					 current
		DESCRIPTION			 " -- "
		::=  { drxQciEntry  1 }


	drxQciQci		 OBJECT-TYPE
		SYNTAX					 Integer32( 1 .. 9 )
		MAX-ACCESS			 not-accessible
		STATUS					 current
		DESCRIPTION			 " -- "
		::=  { drxQciEntry  2 }


	drxQciRowStatus		 OBJECT-TYPE
		SYNTAX					 RowStatus
		MAX-ACCESS			 read-create
		STATUS					 current
		DESCRIPTION			 " -- "
		::=  { drxQciEntry  3 }


	drxQciFlag		 OBJECT-TYPE
		SYNTAX					 INTEGER{ false(0),true(1)  }
		MAX-ACCESS			 read-create
		STATUS					 current
		DESCRIPTION			 " -- "
		::=  { drxQciEntry  4 }


	drxQciOnDurationTimer		 OBJECT-TYPE
		SYNTAX					 INTEGER{ psf1(0),psf2(1),psf3(2),psf4(3),psf5(4),psf6(5),psf8(6),psf10(7),psf20(8),psf30(9),psf40(10),psf50(11),psf60(12),psf80(13),psf100(14),psf200(15)  }
		MAX-ACCESS			 read-create
		STATUS					 current
		DESCRIPTION			 " -- "
		::=  { drxQciEntry  6 }


	drxQciInactivityTimer		 OBJECT-TYPE
		SYNTAX					 INTEGER{ psf1(0),psf2(1),psf3(2),psf4(3),psf5(4),psf6(5),psf8(6),psf10(7),psf20(8),psf30(9),psf40(10),psf50(11),psf60(12),psf80(13),psf100(14),psf200(15),psf300(16),psf500(17),psf750(18),psf1280(19),psf1920(20),psf2560(21)  }
		MAX-ACCESS			 read-create
		STATUS					 current
		DESCRIPTION			 " -- "
		::=  { drxQciEntry  7 }


	drxQciRetransmissionTimer		 OBJECT-TYPE
		SYNTAX					 INTEGER{ psf1(0),psf2(1),psf4(2),psf6(3),psf8(4),psf16(5),psf24(6),psf33(7)  }
		MAX-ACCESS			 read-create
		STATUS					 current
		DESCRIPTION			 " -- "
		::=  { drxQciEntry  8 }


	drxQciLongCycle		 OBJECT-TYPE
		SYNTAX					 INTEGER{ sf10(0),sf20(1),sf32(2),sf40(3),sf64(4),sf80(5),sf128(6),sf160(7),sf256(8),sf320(9),sf512(10),sf640(11),sf1024(12),sf1280(13),sf2048(14),sf2560(15)  }
		MAX-ACCESS			 read-create
		STATUS					 current
		DESCRIPTION			 " -- "
		::=  { drxQciEntry  9 }


	drxQciShortCycle		 OBJECT-TYPE
		SYNTAX					 INTEGER{ sf2(0),sf5(1),sf8(2),sf10(3),sf16(4),sf20(5),sf32(6),sf40(7),sf64(8),sf80(9),sf128(10),sf160(11),sf256(12),sf512(13),sf640(14),sf320(15)  }
		MAX-ACCESS			 read-create
		STATUS					 current
		DESCRIPTION			 " -- "
		::=  { drxQciEntry  10 }


	drxQciShortCycleTimer		 OBJECT-TYPE
		SYNTAX					 Integer32( 1 .. 16 )
		MAX-ACCESS			 read-create
		STATUS					 current
		DESCRIPTION			 " -- "
		::=  { drxQciEntry  11 }


	drxQciShortFlag		 OBJECT-TYPE
		SYNTAX					 INTEGER{ false(0),true(1)  }
		MAX-ACCESS			 read-create
		STATUS					 current
		DESCRIPTION			 " -- "
		::=  { drxQciEntry  12 }


	drxQciOnDurationTimerB		 OBJECT-TYPE
		SYNTAX					 INTEGER{ psf1(0),psf2(1),psf3(2),psf4(3),psf5(4),psf6(5),psf8(6),psf10(7),psf20(8),psf30(9),psf40(10),psf50(11),psf60(12),psf80(13),psf100(14),psf200(15)  }
		MAX-ACCESS			 read-create
		STATUS					 current
		DESCRIPTION			 " -- "
		::=  { drxQciEntry  13 }


	drxQciInactivityTimerB		 OBJECT-TYPE
		SYNTAX					 INTEGER{ psf1(0),psf2(1),psf3(2),psf4(3),psf5(4),psf6(5),psf8(6),psf10(7),psf20(8),psf30(9),psf40(10),psf50(11),psf60(12),psf80(13),psf100(14),psf200(15),psf300(16),psf500(17),psf750(18),psf1280(19),psf1920(20),psf2560(21)  }
		MAX-ACCESS			 read-create
		STATUS					 current
		DESCRIPTION			 " -- "
		::=  { drxQciEntry  14 }


	drxQciRetransmissionTimerB		 OBJECT-TYPE
		SYNTAX					 INTEGER{ psf1(0),psf2(1),psf4(2),psf6(3),psf8(4),psf16(5),psf24(6),psf33(7)  }
		MAX-ACCESS			 read-create
		STATUS					 current
		DESCRIPTION			 " -- "
		::=  { drxQciEntry  15 }


	drxQciLongCycleB		 OBJECT-TYPE
		SYNTAX					 INTEGER{ sf10(0),sf20(1),sf32(2),sf40(3),sf64(4),sf80(5),sf128(6),sf160(7),sf256(8),sf320(9),sf512(10),sf640(11),sf1024(12),sf1280(13),sf2048(14),sf2560(15)  }
		MAX-ACCESS			 read-create
		STATUS					 current
		DESCRIPTION			 " -- "
		::=  { drxQciEntry  16 }


	csirsTable		 OBJECT-TYPE
		SYNTAX					 SEQUENCE  OF	 CsirsEntry
		MAX-ACCESS			 not-accessible
		STATUS					 current
		DESCRIPTION			 " -- "
		::=  { chandPrCfg  19 }


	csirsEntry		 OBJECT-TYPE
		SYNTAX					 CsirsEntry
		MAX-ACCESS			 not-accessible
		STATUS					 current
		DESCRIPTION			 " -- "
		INDEX						{ csirsLcId }
		::=  { csirsTable  1 }


	CsirsEntry		 ::=  SEQUENCE {
		csirsLcId					Integer32,
		csirsRowStatus					RowStatus,
		csirsInfoSwitch					INTEGER,
		csirsPortnum					INTEGER,
		csirsSignalConfig					Integer32,
		csirsSubsfnConfig					Integer32,
		csirsPc					Integer32,
		csirsZeropowerConfig					Integer32,
		csirsZeropowersubsfnConfig					Integer32,
		csirsTransmitFlag					INTEGER,
		csirstm9PmiRiReportFlag					INTEGER
		}


	csirsLcId		 OBJECT-TYPE
		SYNTAX					 Integer32( 0 .. 23 )
		MAX-ACCESS			 not-accessible
		STATUS					 current
		DESCRIPTION			 " -- "
		::=  { csirsEntry  1 }


	csirsRowStatus		 OBJECT-TYPE
		SYNTAX					 RowStatus
		MAX-ACCESS			 read-create
		STATUS					 current
		DESCRIPTION			 " -- "
		::=  { csirsEntry  2 }


	csirsInfoSwitch		 OBJECT-TYPE
		SYNTAX					 INTEGER{ lmtConfig(0),algorithm(1)  }
		MAX-ACCESS			 read-create
		STATUS					 current
		DESCRIPTION			 " -- "
		::=  { csirsEntry  3 }


	csirsPortnum		 OBJECT-TYPE
		SYNTAX					 INTEGER{ pnum1(0),pnum2(1),pnum4(2),pnum8(3)  }
		MAX-ACCESS			 read-create
		STATUS					 current
		DESCRIPTION			 " -- "
		::=  { csirsEntry  4 }


	csirsSignalConfig		 OBJECT-TYPE
		SYNTAX					 Integer32( 0 .. 31 )
		MAX-ACCESS			 read-create
		STATUS					 current
		DESCRIPTION			 " -- "
		::=  { csirsEntry  5 }


	csirsSubsfnConfig		 OBJECT-TYPE
		SYNTAX					 Integer32( 0 .. 154 )
		MAX-ACCESS			 read-create
		STATUS					 current
		DESCRIPTION			 " -- "
		::=  { csirsEntry  6 }


	csirsPc		 OBJECT-TYPE
		SYNTAX					 Integer32( -8 .. 15 )
		MAX-ACCESS			 read-create
		STATUS					 current
		DESCRIPTION			 " -- "
		::=  { csirsEntry  7 }


	csirsZeropowerConfig		 OBJECT-TYPE
		SYNTAX					 Integer32( 0 .. 65535 )
		MAX-ACCESS			 read-create
		STATUS					 current
		DESCRIPTION			 " -- "
		::=  { csirsEntry  8 }


	csirsZeropowersubsfnConfig		 OBJECT-TYPE
		SYNTAX					 Integer32( 0 .. 154 )
		MAX-ACCESS			 read-create
		STATUS					 current
		DESCRIPTION			 " -- "
		::=  { csirsEntry  9 }


	csirsTransmitFlag		 OBJECT-TYPE
		SYNTAX					 INTEGER{ off(0),on(1)  }
		MAX-ACCESS			 read-create
		STATUS					 current
		DESCRIPTION			 " -- "
		::=  { csirsEntry  10 }


	csirstm9PmiRiReportFlag		 OBJECT-TYPE
		SYNTAX					 INTEGER{ off(0),on(1)  }
		MAX-ACCESS			 read-create
		STATUS					 current
		DESCRIPTION			 " -- "
		::=  { csirsEntry  11 }


	cacPositionTable		 OBJECT-TYPE
		SYNTAX					 SEQUENCE  OF	 CacPositionEntry
		MAX-ACCESS			 not-accessible
		STATUS					 current
		DESCRIPTION			 " -- "
		::=  { chandPrCfg  20 }


	cacPositionEntry		 OBJECT-TYPE
		SYNTAX					 CacPositionEntry
		MAX-ACCESS			 not-accessible
		STATUS					 current
		DESCRIPTION			 " -- "
		INDEX						{ cacPositionLcId }
		::=  { cacPositionTable  1 }


	CacPositionEntry		 ::=  SEQUENCE {
		cacPositionLcId					Integer32,
		cacPositionRowStatus					RowStatus,
		cacPositionSwitch					INTEGER,
		cacPositionTAMeasType					INTEGER,
		cacPositionTA1MeasNum					Integer32,
		cacPositionAoAStartTreshhold					Integer32,
		cacPositionAoAEndTreshhold					Integer32,
		cacPositionDistanceTreshhold					Integer32,
		cacPositionRedirectionSwith					INTEGER,
		cacPositionRedirectionNet					INTEGER,
		cacPositionReaccesNum					Integer32
		}


	cacPositionLcId		 OBJECT-TYPE
		SYNTAX					 Integer32( 0 .. 23 )
		MAX-ACCESS			 not-accessible
		STATUS					 current
		DESCRIPTION			 " -- "
		::=  { cacPositionEntry  1 }


	cacPositionRowStatus		 OBJECT-TYPE
		SYNTAX					 RowStatus
		MAX-ACCESS			 read-create
		STATUS					 current
		DESCRIPTION			 " -- "
		::=  { cacPositionEntry  2 }


	cacPositionSwitch		 OBJECT-TYPE
		SYNTAX					 INTEGER{ false(0),true(1)  }
		MAX-ACCESS			 read-create
		STATUS					 current
		DESCRIPTION			 " -- "
		::=  { cacPositionEntry  3 }


	cacPositionTAMeasType		 OBJECT-TYPE
		SYNTAX					 INTEGER{ tatype1(0),tatype2(1)  }
		MAX-ACCESS			 read-create
		STATUS					 current
		DESCRIPTION			 " -- "
		::=  { cacPositionEntry  4 }


	cacPositionTA1MeasNum		 OBJECT-TYPE
		SYNTAX					 Integer32( 1 .. 10 )
		MAX-ACCESS			 read-create
		STATUS					 current
		DESCRIPTION			 " -- "
		::=  { cacPositionEntry  5 }


	cacPositionAoAStartTreshhold		 OBJECT-TYPE
		SYNTAX					 Integer32( 0 .. 360 )
		MAX-ACCESS			 read-create
		STATUS					 current
		DESCRIPTION			 " -- "
		::=  { cacPositionEntry  6 }


	cacPositionAoAEndTreshhold		 OBJECT-TYPE
		SYNTAX					 Integer32( 0 .. 360 )
		MAX-ACCESS			 read-create
		STATUS					 current
		DESCRIPTION			 " -- "
		::=  { cacPositionEntry  7 }


	cacPositionDistanceTreshhold		 OBJECT-TYPE
		SYNTAX					 Integer32( 0 .. 5000 )
		MAX-ACCESS			 read-create
		STATUS					 current
		DESCRIPTION			 " -- "
		::=  { cacPositionEntry  8 }


	cacPositionRedirectionSwith		 OBJECT-TYPE
		SYNTAX					 INTEGER{ false(0),true(1)  }
		MAX-ACCESS			 read-create
		STATUS					 current
		DESCRIPTION			 " -- "
		::=  { cacPositionEntry  9 }


	cacPositionRedirectionNet		 OBJECT-TYPE
		SYNTAX					 INTEGER{ geran(0),utraTdd(1)  }
		MAX-ACCESS			 read-create
		STATUS					 current
		DESCRIPTION			 " -- "
		::=  { cacPositionEntry  10 }


	cacPositionReaccesNum		 OBJECT-TYPE
		SYNTAX					 Integer32( 1 .. 10 )
		MAX-ACCESS			 read-create
		STATUS					 current
		DESCRIPTION			 " -- "
		::=  { cacPositionEntry  11 }


	cellAlgorithm		 OBJECT IDENTIFIER
		::=  { networkElementPlanCell  8 }


	cac		 OBJECT IDENTIFIER
		::=  { cellAlgorithm  1 }


	cacTable		 OBJECT-TYPE
		SYNTAX					 SEQUENCE  OF	 CacEntry
		MAX-ACCESS			 not-accessible
		STATUS					 current
		DESCRIPTION			 " -- "
		::=  { cac  1 }


	cacEntry		 OBJECT-TYPE
		SYNTAX					 CacEntry
		MAX-ACCESS			 not-accessible
		STATUS					 current
		DESCRIPTION			 " -- "
		INDEX						{ cacLcId }
		::=  { cacTable  1 }


	CacEntry		 ::=  SEQUENCE {
		cacLcId					Integer32,
		cacRowStatus					RowStatus,
		cacAlgorithmTag					INTEGER,
		cacType					INTEGER,
		cacUlPrbTh					Integer32,
		cacDlPrbTh					Integer32,
		cacUlHcReservePrb					Integer32,
		cacDlHcReservePrb					Integer32,
		cacArpTag					INTEGER,
		cacTestMode					INTEGER,
		cacMaxActiveUeNumPerCell					Integer32,
		cacMaxActiveBearNumPerUe					Integer32,
		cacGbrThFlag					INTEGER,
		cacUlGbrPrbTh					Integer32,
		cacDlGbrPrbTh					Integer32,
		cacNgbrThFlag					INTEGER,
		cacUlNgbrPrbTh					Integer32,
		cacDlNgbrPrbTh					Integer32,
		cacS1BandwidthTag					INTEGER,
		cacPriForReestablishUe					INTEGER,
		cacMaxActiveUeNumTag					INTEGER,
		cacMaxActiveBearNumPerCellTag					INTEGER,
		cacMaxActiveBearNumPerCell					Integer32,
		cacPrbThFlag					INTEGER,
		cacEmergencyPriorTag					INTEGER,
		cacNominalActiveUeNumPerCell					Integer32,
		cacMaxQci1NumTag					INTEGER,
		cacMaxQci1BearNumPerCell					Integer32,
		cacQci1LicenseFlag					INTEGER
		}


	cacLcId		 OBJECT-TYPE
		SYNTAX					 Integer32( 0 .. 23 )
		MAX-ACCESS			 not-accessible
		STATUS					 current
		DESCRIPTION			 " -- "
		::=  { cacEntry  1 }


	cacRowStatus		 OBJECT-TYPE
		SYNTAX					 RowStatus
		MAX-ACCESS			 read-create
		STATUS					 current
		DESCRIPTION			 " -- "
		::=  { cacEntry  2 }


	cacAlgorithmTag		 OBJECT-TYPE
		SYNTAX					 INTEGER{ off(0),on(1)  }
		MAX-ACCESS			 read-create
		STATUS					 current
		DESCRIPTION			 " -- "
		::=  { cacEntry  3 }


	cacType		 OBJECT-TYPE
		SYNTAX					 INTEGER{ uePositionUnconcern(1),uePositionConcerned(2)  }
		MAX-ACCESS			 read-create
		STATUS					 current
		DESCRIPTION			 " -- "
		::=  { cacEntry  4 }


	cacUlPrbTh		 OBJECT-TYPE
		SYNTAX					 Integer32( 0 .. 100 )
		MAX-ACCESS			 read-create
		STATUS					 current
		DESCRIPTION			 " -- "
		::=  { cacEntry  5 }


	cacDlPrbTh		 OBJECT-TYPE
		SYNTAX					 Integer32( 0 .. 100 )
		MAX-ACCESS			 read-create
		STATUS					 current
		DESCRIPTION			 " -- "
		::=  { cacEntry  6 }


	cacUlHcReservePrb		 OBJECT-TYPE
		SYNTAX					 Integer32( 0 .. 100 )
		MAX-ACCESS			 read-create
		STATUS					 current
		DESCRIPTION			 " -- "
		::=  { cacEntry  7 }


	cacDlHcReservePrb		 OBJECT-TYPE
		SYNTAX					 Integer32( 0 .. 100 )
		MAX-ACCESS			 read-create
		STATUS					 current
		DESCRIPTION			 " -- "
		::=  { cacEntry  8 }


	cacArpTag		 OBJECT-TYPE
		SYNTAX					 INTEGER{ off(0),on(1)  }
		MAX-ACCESS			 read-create
		STATUS					 current
		DESCRIPTION			 " -- "
		::=  { cacEntry  10 }


	cacTestMode		 OBJECT-TYPE
		SYNTAX					 INTEGER{ cacTestModeOpen(0),cacTestModeClose(1)  }
		MAX-ACCESS			 read-create
		STATUS					 current
		DESCRIPTION			 " -- "
		::=  { cacEntry  11 }


	cacMaxActiveUeNumPerCell		 OBJECT-TYPE
		SYNTAX					 Integer32( 0 .. 1200 )
		MAX-ACCESS			 read-create
		STATUS					 current
		DESCRIPTION			 " -- "
		::=  { cacEntry  12 }


	cacMaxActiveBearNumPerUe		 OBJECT-TYPE
		SYNTAX					 Integer32( 0 .. 8 )
		MAX-ACCESS			 read-create
		STATUS					 current
		DESCRIPTION			 " -- "
		::=  { cacEntry  13 }


	cacGbrThFlag		 OBJECT-TYPE
		SYNTAX					 INTEGER{ off(0),on(1)  }
		MAX-ACCESS			 read-create
		STATUS					 current
		DESCRIPTION			 " -- "
		::=  { cacEntry  14 }


	cacUlGbrPrbTh		 OBJECT-TYPE
		SYNTAX					 Integer32( 0 .. 100 )
		MAX-ACCESS			 read-create
		STATUS					 current
		DESCRIPTION			 " -- "
		::=  { cacEntry  15 }


	cacDlGbrPrbTh		 OBJECT-TYPE
		SYNTAX					 Integer32( 0 .. 100 )
		MAX-ACCESS			 read-create
		STATUS					 current
		DESCRIPTION			 " -- "
		::=  { cacEntry  16 }


	cacNgbrThFlag		 OBJECT-TYPE
		SYNTAX					 INTEGER{ off(0),on(1)  }
		MAX-ACCESS			 read-create
		STATUS					 current
		DESCRIPTION			 " -- "
		::=  { cacEntry  17 }


	cacUlNgbrPrbTh		 OBJECT-TYPE
		SYNTAX					 Integer32( 0 .. 100 )
		MAX-ACCESS			 read-create
		STATUS					 current
		DESCRIPTION			 " -- "
		::=  { cacEntry  18 }


	cacDlNgbrPrbTh		 OBJECT-TYPE
		SYNTAX					 Integer32( 0 .. 100 )
		MAX-ACCESS			 read-create
		STATUS					 current
		DESCRIPTION			 " -- "
		::=  { cacEntry  19 }


	cacS1BandwidthTag		 OBJECT-TYPE
		SYNTAX					 INTEGER{ off(0),on(1)  }
		MAX-ACCESS			 read-create
		STATUS					 current
		DESCRIPTION			 " -- "
		::=  { cacEntry  20 }


	cacPriForReestablishUe		 OBJECT-TYPE
		SYNTAX					 INTEGER{ high(0),low(1)  }
		MAX-ACCESS			 read-create
		STATUS					 current
		DESCRIPTION			 " -- "
		::=  { cacEntry  21 }


	cacMaxActiveUeNumTag		 OBJECT-TYPE
		SYNTAX					 INTEGER{ off(0),on(1)  }
		MAX-ACCESS			 read-create
		STATUS					 current
		DESCRIPTION			 " -- "
		::=  { cacEntry  22 }


	cacMaxActiveBearNumPerCellTag		 OBJECT-TYPE
		SYNTAX					 INTEGER{ off(0),on(1)  }
		MAX-ACCESS			 read-create
		STATUS					 current
		DESCRIPTION			 " -- "
		::=  { cacEntry  23 }


	cacMaxActiveBearNumPerCell		 OBJECT-TYPE
		SYNTAX					 Integer32( 0 .. 9600 )
		MAX-ACCESS			 read-create
		STATUS					 current
		DESCRIPTION			 " -- "
		::=  { cacEntry  24 }


	cacPrbThFlag		 OBJECT-TYPE
		SYNTAX					 INTEGER{ off(0),on(1)  }
		MAX-ACCESS			 read-create
		STATUS					 current
		DESCRIPTION			 " -- "
		::=  { cacEntry  25 }


	cacEmergencyPriorTag		 OBJECT-TYPE
		SYNTAX					 INTEGER{ off(0),on(1)  }
		MAX-ACCESS			 read-create
		STATUS					 current
		DESCRIPTION			 " -- "
		::=  { cacEntry  26 }


	cacNominalActiveUeNumPerCell		 OBJECT-TYPE
		SYNTAX					 Integer32( 0 .. 1200 )
		MAX-ACCESS			 read-create
		STATUS					 current
		DESCRIPTION			 " -- "
		::=  { cacEntry  27 }


	cacMaxQci1NumTag		 OBJECT-TYPE
		SYNTAX					 INTEGER{ off(0),on(1)  }
		MAX-ACCESS			 read-create
		STATUS					 current
		DESCRIPTION			 " -- "
		::=  { cacEntry  28 }


	cacMaxQci1BearNumPerCell		 OBJECT-TYPE
		SYNTAX					 Integer32( 0 .. 1000 )
		MAX-ACCESS			 read-create
		STATUS					 current
		DESCRIPTION			 " -- "
		::=  { cacEntry  29 }


	cacQci1LicenseFlag		 OBJECT-TYPE
		SYNTAX					 INTEGER{ off(0),on(1)  }
		MAX-ACCESS			 read-create
		STATUS					 current
		DESCRIPTION			 " -- "
		::=  { cacEntry  30 }


	chacTable		 OBJECT-TYPE
		SYNTAX					 SEQUENCE  OF	 ChacEntry
		MAX-ACCESS			 not-accessible
		STATUS					 current
		DESCRIPTION			 " -- "
		::=  { cac  2 }


	chacEntry		 OBJECT-TYPE
		SYNTAX					 ChacEntry
		MAX-ACCESS			 not-accessible
		STATUS					 current
		DESCRIPTION			 " -- "
		INDEX						{ chacLcId }
		::=  { chacTable  1 }


	ChacEntry		 ::=  SEQUENCE {
		chacLcId					Integer32,
		chacRowStatus					RowStatus,
		chacPrbTag					INTEGER,
		chacUlPrbTh					Integer32,
		chacDlPrbTh					Integer32,
		chacPrbThTimeToTrig					Integer32,
		chacUlPrbRBTh					Integer32,
		chacDlPrbRBTh					Integer32,
		chacRBThTimeToTrig					Integer32,
		chacActiveUeTag					INTEGER,
		chacActiveUeHighLoadTh					Integer32,
		chacActiveUeSuperHighLoadTh					Integer32,
		chacActiveUeUltraLoadTh					Integer32,
		chacActiveUeRBTh					Integer32,
		chacHighLoadT302					Integer32,
		chacAcBarTag					INTEGER,
		chacHighLoadAcBarFactorRate					Integer32,
		chacHighLoadAcBarTimeRate					Integer32,
		chacAcBarActInterval					Integer32,
		chacCpuLoadTag					INTEGER,
		chacRejectdepriType					INTEGER,
		chacRejectdepriTimer					INTEGER
		}


	chacLcId		 OBJECT-TYPE
		SYNTAX					 Integer32( 0 .. 23 )
		MAX-ACCESS			 not-accessible
		STATUS					 current
		DESCRIPTION			 " -- "
		::=  { chacEntry  1 }


	chacRowStatus		 OBJECT-TYPE
		SYNTAX					 RowStatus
		MAX-ACCESS			 read-create
		STATUS					 current
		DESCRIPTION			 " -- "
		::=  { chacEntry  2 }


	chacPrbTag		 OBJECT-TYPE
		SYNTAX					 INTEGER{ off(0),on(1)  }
		MAX-ACCESS			 read-create
		STATUS					 current
		DESCRIPTION			 " -- "
		::=  { chacEntry  3 }


	chacUlPrbTh		 OBJECT-TYPE
		SYNTAX					 Integer32( 0 .. 100 )
		MAX-ACCESS			 read-create
		STATUS					 current
		DESCRIPTION			 " -- "
		::=  { chacEntry  4 }


	chacDlPrbTh		 OBJECT-TYPE
		SYNTAX					 Integer32( 0 .. 100 )
		MAX-ACCESS			 read-create
		STATUS					 current
		DESCRIPTION			 " -- "
		::=  { chacEntry  5 }


	chacPrbThTimeToTrig		 OBJECT-TYPE
		SYNTAX					 Integer32( 1 .. 3600 )
		MAX-ACCESS			 read-create
		STATUS					 current
		DESCRIPTION			 " -- "
		::=  { chacEntry  6 }


	chacUlPrbRBTh		 OBJECT-TYPE
		SYNTAX					 Integer32( 0 .. 100 )
		MAX-ACCESS			 read-create
		STATUS					 current
		DESCRIPTION			 " -- "
		::=  { chacEntry  7 }


	chacDlPrbRBTh		 OBJECT-TYPE
		SYNTAX					 Integer32( 0 .. 100 )
		MAX-ACCESS			 read-create
		STATUS					 current
		DESCRIPTION			 " -- "
		::=  { chacEntry  8 }


	chacRBThTimeToTrig		 OBJECT-TYPE
		SYNTAX					 Integer32( 1 .. 3600 )
		MAX-ACCESS			 read-create
		STATUS					 current
		DESCRIPTION			 " -- "
		::=  { chacEntry  9 }


	chacActiveUeTag		 OBJECT-TYPE
		SYNTAX					 INTEGER{ off(0),on(1)  }
		MAX-ACCESS			 read-create
		STATUS					 current
		DESCRIPTION			 " -- "
		::=  { chacEntry  10 }


	chacActiveUeHighLoadTh		 OBJECT-TYPE
		SYNTAX					 Integer32( 0 .. 1200 )
		MAX-ACCESS			 read-create
		STATUS					 current
		DESCRIPTION			 " -- "
		::=  { chacEntry  11 }


	chacActiveUeSuperHighLoadTh		 OBJECT-TYPE
		SYNTAX					 Integer32( 0 .. 1200 )
		MAX-ACCESS			 read-create
		STATUS					 current
		DESCRIPTION			 " -- "
		::=  { chacEntry  12 }


	chacActiveUeUltraLoadTh		 OBJECT-TYPE
		SYNTAX					 Integer32( 0 .. 1200 )
		MAX-ACCESS			 read-create
		STATUS					 current
		DESCRIPTION			 " -- "
		::=  { chacEntry  13 }


	chacActiveUeRBTh		 OBJECT-TYPE
		SYNTAX					 Integer32( 0 .. 1200 )
		MAX-ACCESS			 read-create
		STATUS					 current
		DESCRIPTION			 " -- "
		::=  { chacEntry  14 }


	chacHighLoadT302		 OBJECT-TYPE
		SYNTAX					 Integer32( 1 .. 16 )
		MAX-ACCESS			 read-create
		STATUS					 current
		DESCRIPTION			 " -- "
		::=  { chacEntry  15 }


	chacAcBarTag		 OBJECT-TYPE
		SYNTAX					 INTEGER{ off(0),on(1)  }
		MAX-ACCESS			 read-create
		STATUS					 current
		DESCRIPTION			 " -- "
		::=  { chacEntry  16 }


	chacHighLoadAcBarFactorRate		 OBJECT-TYPE
		SYNTAX					 Integer32( 0 .. 100 )
		MAX-ACCESS			 read-create
		STATUS					 current
		DESCRIPTION			 " -- "
		::=  { chacEntry  17 }


	chacHighLoadAcBarTimeRate		 OBJECT-TYPE
		SYNTAX					 Integer32( 100 .. 200 )
		MAX-ACCESS			 read-create
		STATUS					 current
		DESCRIPTION			 " -- "
		::=  { chacEntry  18 }


	chacAcBarActInterval		 OBJECT-TYPE
		SYNTAX					 Integer32( 1 .. 3600 )
		MAX-ACCESS			 read-create
		STATUS					 current
		DESCRIPTION			 " -- "
		::=  { chacEntry  19 }


	chacCpuLoadTag		 OBJECT-TYPE
		SYNTAX					 INTEGER{ off(0),on(1)  }
		MAX-ACCESS			 read-create
		STATUS					 current
		DESCRIPTION			 " -- "
		::=  { chacEntry  20 }


	chacRejectdepriType		 OBJECT-TYPE
		SYNTAX					 INTEGER{ frequency(0),eutra(1)  }
		MAX-ACCESS			 read-create
		STATUS					 current
		DESCRIPTION			 " -- "
		::=  { chacEntry  21 }


	chacRejectdepriTimer		 OBJECT-TYPE
		SYNTAX					 INTEGER{ min5(0),min10(1),min15(2),min30(3)  }
		MAX-ACCESS			 read-create
		STATUS					 current
		DESCRIPTION			 " -- "
		::=  { chacEntry  22 }


	hc		 OBJECT IDENTIFIER
		::=  { cellAlgorithm  2 }


	hcTable		 OBJECT-TYPE
		SYNTAX					 SEQUENCE  OF	 HcEntry
		MAX-ACCESS			 not-accessible
		STATUS					 current
		DESCRIPTION			 " -- "
		::=  { hc  1 }


	hcEntry		 OBJECT-TYPE
		SYNTAX					 HcEntry
		MAX-ACCESS			 not-accessible
		STATUS					 current
		DESCRIPTION			 " -- "
		INDEX						{ hcLcId }
		::=  { hcTable  1 }


	HcEntry		 ::=  SEQUENCE {
		hcLcId					Integer32,
		hcRowStatus					RowStatus,
		hcTag					INTEGER,
		hcJudgeType					INTEGER,
		hcCellSelectType					INTEGER,
		hcServRsrpTh					Integer32,
		hcServRsrqTh					Integer32,
		hcAdjRsrpTh					Integer32,
		hcAdjRsrqTh					Integer32,
		hcAdjCellNum					Integer32,
		hcFreqEffCqiTh					Integer32,
		hcPcellScellRsrpTh					INTEGER,
		hcDirectedHCTag					INTEGER,
		hcTimeAntiShake					Integer32,
		hcTagBasedSpeed					INTEGER,
		hcPubAlgorithmParaHSpdCellStatus					INTEGER,
		hcLowSpeedUeShiftType					INTEGER,
		hcBlerHcIotTh					Integer32,
		hcBlerHcRsrqTh					Integer32,
		hcCSHoCfgSwitch					INTEGER,
		hcBlerWaitA4Time					Integer32,
		hcBlerBasedHcTag					INTEGER
		}


	hcLcId		 OBJECT-TYPE
		SYNTAX					 Integer32( 0 .. 23 )
		MAX-ACCESS			 not-accessible
		STATUS					 current
		DESCRIPTION			 " -- "
		::=  { hcEntry  1 }


	hcRowStatus		 OBJECT-TYPE
		SYNTAX					 RowStatus
		MAX-ACCESS			 read-create
		STATUS					 current
		DESCRIPTION			 " -- "
		::=  { hcEntry  2 }


	hcTag		 OBJECT-TYPE
		SYNTAX					 INTEGER{ off(0),on(1)  }
		MAX-ACCESS			 read-create
		STATUS					 current
		DESCRIPTION			 " -- "
		::=  { hcEntry  3 }


	hcJudgeType		 OBJECT-TYPE
		SYNTAX					 INTEGER{ l3HcTypeRsrpTh(1),l3HcTypeRsrqTh(2),l3HcTypeRsrqRsrqTh(3)  }
		MAX-ACCESS			 read-create
		STATUS					 current
		DESCRIPTION			 " -- "
		::=  { hcEntry  4 }


	hcCellSelectType		 OBJECT-TYPE
		SYNTAX					 INTEGER{ atLeastOneErabAdmit(0),mustAllGbrErabAdmit(1),mustAllErabAdmit(2)  }
		MAX-ACCESS			 read-create
		STATUS					 current
		DESCRIPTION			 " -- "
		::=  { hcEntry  5 }


	hcServRsrpTh		 OBJECT-TYPE
		SYNTAX					 Integer32( 0 .. 97 )
		MAX-ACCESS			 read-create
		STATUS					 current
		DESCRIPTION			 " -- "
		::=  { hcEntry  6 }


	hcServRsrqTh		 OBJECT-TYPE
		SYNTAX					 Integer32( 0 .. 34 )
		MAX-ACCESS			 read-create
		STATUS					 current
		DESCRIPTION			 " -- "
		::=  { hcEntry  7 }


	hcAdjRsrpTh		 OBJECT-TYPE
		SYNTAX					 Integer32( 0 .. 97 )
		MAX-ACCESS			 read-create
		STATUS					 current
		DESCRIPTION			 " -- "
		::=  { hcEntry  8 }


	hcAdjRsrqTh		 OBJECT-TYPE
		SYNTAX					 Integer32( 0 .. 34 )
		MAX-ACCESS			 read-create
		STATUS					 current
		DESCRIPTION			 " -- "
		::=  { hcEntry  9 }


	hcAdjCellNum		 OBJECT-TYPE
		SYNTAX					 Integer32( 1 .. 10 )
		MAX-ACCESS			 read-create
		STATUS					 current
		DESCRIPTION			 " -- "
		::=  { hcEntry  10 }


	hcFreqEffCqiTh		 OBJECT-TYPE
		SYNTAX					 Integer32( 1 .. 15 )
		MAX-ACCESS			 read-create
		STATUS					 current
		DESCRIPTION			 " -- "
		::=  { hcEntry  13 }


	hcPcellScellRsrpTh		 OBJECT-TYPE
		SYNTAX					 INTEGER{ rsrpTh0(0),rsrpThPoint5(1),rsrpTh1(2),rsrpTh1point5(3),rsrpTh2(4),rsrpTh2point5(5),rsrpTh3(6),rsrpTh3point5(7),rsrpTh4(8),rsrpTh4point5(9),rsrpTh5(10),rsrpTh5point5(11),rsrpTh6(12),rsrpTh6point5(13),rsrpTh7(14),rsrpTh7point5(15),rsrpTh8(16),rsrpTh8point5(17),rsrpTh9(18),rsrpTh9point5(19),rsrpTh10(20),rsrpTh10point5(21),rsrpTh11(22),rsrpTh11point5(23),rsrpTh12(24),rsrpTh12point5(25),rsrpTh13(26),rsrpTh13point5(27),rsrpTh14(28),rsrpTh14point5(29),rsrpTh15(30)  }
		MAX-ACCESS			 read-create
		STATUS					 current
		DESCRIPTION			 " -- "
		::=  { hcEntry  14 }


	hcDirectedHCTag		 OBJECT-TYPE
		SYNTAX					 INTEGER{ off(0),on(1)  }
		MAX-ACCESS			 read-create
		STATUS					 current
		DESCRIPTION			 " -- "
		::=  { hcEntry  15 }


	hcTimeAntiShake		 OBJECT-TYPE
		SYNTAX					 Integer32( 0 .. 65535 )
		MAX-ACCESS			 read-create
		STATUS					 current
		DESCRIPTION			 " -- "
		::=  { hcEntry  16 }


	hcTagBasedSpeed		 OBJECT-TYPE
		SYNTAX					 INTEGER{ off(0),lowSpeedUserOut(1),highSpeedUserOut(2)  }
		MAX-ACCESS			 read-create
		STATUS					 current
		DESCRIPTION			 " -- "
		::=  { hcEntry  17 }


	hcPubAlgorithmParaHSpdCellStatus		 OBJECT-TYPE
		SYNTAX					 INTEGER{ lowSpeedCell(0),highSpeedCell(1)  }
		MAX-ACCESS			 read-create
		STATUS					 current
		DESCRIPTION			 " -- "
		::=  { hcEntry  18 }


	hcLowSpeedUeShiftType		 OBJECT-TYPE
		SYNTAX					 INTEGER{ redirect(0),handover(1)  }
		MAX-ACCESS			 read-create
		STATUS					 current
		DESCRIPTION			 " -- "
		::=  { hcEntry  19 }


	hcBlerHcIotTh		 OBJECT-TYPE
		SYNTAX					 Integer32( 0 .. 500 )
		MAX-ACCESS			 read-create
		STATUS					 current
		DESCRIPTION			 " -- "
		::=  { hcEntry  21 }


	hcBlerHcRsrqTh		 OBJECT-TYPE
		SYNTAX					 Integer32( 0 .. 34 )
		MAX-ACCESS			 read-create
		STATUS					 current
		DESCRIPTION			 " -- "
		::=  { hcEntry  22 }


	hcCSHoCfgSwitch		 OBJECT-TYPE
		SYNTAX					 INTEGER{ off(0),on(1)  }
		MAX-ACCESS			 read-create
		STATUS					 current
		DESCRIPTION			 " -- "
		::=  { hcEntry  23 }


	hcBlerWaitA4Time		 OBJECT-TYPE
		SYNTAX					 Integer32( 1 .. 600 )
		MAX-ACCESS			 read-create
		STATUS					 current
		DESCRIPTION			 " -- "
		::=  { hcEntry  24 }


	hcBlerBasedHcTag		 OBJECT-TYPE
		SYNTAX					 INTEGER{ sRVCC(0),intraLteHcAndSRVCC(1),intraLteHc(2)  }
		MAX-ACCESS			 read-create
		STATUS					 current
		DESCRIPTION			 " -- "
		::=  { hcEntry  25 }


	interRatHcTable		 OBJECT-TYPE
		SYNTAX					 SEQUENCE  OF	 InterRatHcEntry
		MAX-ACCESS			 not-accessible
		STATUS					 current
		DESCRIPTION			 " -- "
		::=  { hc  2 }


	interRatHcEntry		 OBJECT-TYPE
		SYNTAX					 InterRatHcEntry
		MAX-ACCESS			 not-accessible
		STATUS					 current
		DESCRIPTION			 " -- "
		INDEX						{ interRatHcLcId }
		::=  { interRatHcTable  1 }


	InterRatHcEntry		 ::=  SEQUENCE {
		interRatHcLcId					Integer32,
		interRatHcRowStatus					RowStatus,
		interRatCsfbSwitch					INTEGER,
		interRatCsfbMeasFlag					INTEGER,
		interRatCsHandleNetwork					INTEGER,
		interRatSrvccTag					INTEGER,
		interRatSrvccLackOfConditionStrategy					INTEGER,
		interRatPsHandleNetwork					INTEGER,
		interRatPsHandleSwitch					INTEGER,
		interRatCsfbHandlePattern					INTEGER,
		interRatPsHandlePattern					INTEGER,
		interRatPsR8R9FinalNetwork					INTEGER,
		interRatPsR10FinalNetwork					INTEGER,
		interRatPsMeasCtrlSwitch					INTEGER,
		interRatDelInterMeasSwitch					INTEGER,
		interRatBlindSrvccSwitch					INTEGER
		}


	interRatHcLcId		 OBJECT-TYPE
		SYNTAX					 Integer32( 0 .. 23 )
		MAX-ACCESS			 not-accessible
		STATUS					 current
		DESCRIPTION			 " -- "
		::=  { interRatHcEntry  1 }


	interRatHcRowStatus		 OBJECT-TYPE
		SYNTAX					 RowStatus
		MAX-ACCESS			 read-create
		STATUS					 current
		DESCRIPTION			 " -- "
		::=  { interRatHcEntry  2 }


	interRatCsfbSwitch		 OBJECT-TYPE
		SYNTAX					 INTEGER{ off(0),on(1)  }
		MAX-ACCESS			 read-create
		STATUS					 current
		DESCRIPTION			 " -- "
		::=  { interRatHcEntry  11 }


	interRatCsfbMeasFlag		 OBJECT-TYPE
		SYNTAX					 INTEGER{ off(0),on(1)  }
		MAX-ACCESS			 read-create
		STATUS					 current
		DESCRIPTION			 " -- "
		::=  { interRatHcEntry  13 }


	interRatCsHandleNetwork		 OBJECT-TYPE
		SYNTAX					 INTEGER{ notSpecific(0),utraFdd(1),utraTdd(2),geran(3),cdma20001XRTT(4)  }
		MAX-ACCESS			 read-create
		STATUS					 current
		DESCRIPTION			 " -- "
		::=  { interRatHcEntry  17 }


	interRatSrvccTag		 OBJECT-TYPE
		SYNTAX					 INTEGER{ off(0),on(1)  }
		MAX-ACCESS			 read-create
		STATUS					 current
		DESCRIPTION			 " -- "
		::=  { interRatHcEntry  19 }


	interRatSrvccLackOfConditionStrategy		 OBJECT-TYPE
		SYNTAX					 INTEGER{ cs(0),ps(1)  }
		MAX-ACCESS			 read-create
		STATUS					 current
		DESCRIPTION			 " -- "
		::=  { interRatHcEntry  21 }


	interRatPsHandleNetwork		 OBJECT-TYPE
		SYNTAX					 INTEGER{ utraFdd(1),utraTdd(2),geran(3),cdma2000HRPD(4)  }
		MAX-ACCESS			 read-create
		STATUS					 current
		DESCRIPTION			 " -- "
		::=  { interRatHcEntry  22 }


	interRatPsHandleSwitch		 OBJECT-TYPE
		SYNTAX					 INTEGER{ off(0),on(1)  }
		MAX-ACCESS			 read-create
		STATUS					 current
		DESCRIPTION			 " -- "
		::=  { interRatHcEntry  23 }


	interRatCsfbHandlePattern		 OBJECT-TYPE
		SYNTAX					 INTEGER{ ho(0),redirect(1)  }
		MAX-ACCESS			 read-create
		STATUS					 current
		DESCRIPTION			 " -- "
		::=  { interRatHcEntry  24 }


	interRatPsHandlePattern		 OBJECT-TYPE
		SYNTAX					 INTEGER{ ho(0),redirect(1)  }
		MAX-ACCESS			 read-create
		STATUS					 current
		DESCRIPTION			 " -- "
		::=  { interRatHcEntry  25 }


	interRatPsR8R9FinalNetwork		 OBJECT-TYPE
		SYNTAX					 INTEGER{ utraFdd(1),utraTdd(2),geran(3),cdma2000HRPD(4)  }
		MAX-ACCESS			 read-create
		STATUS					 current
		DESCRIPTION			 " -- "
		::=  { interRatHcEntry  26 }


	interRatPsR10FinalNetwork		 OBJECT-TYPE
		SYNTAX					 INTEGER{ utraFdd(1),utraTdd(2),geran(3),cdma2000HRPD(4)  }
		MAX-ACCESS			 read-create
		STATUS					 current
		DESCRIPTION			 " -- "
		::=  { interRatHcEntry  27 }


	interRatPsMeasCtrlSwitch		 OBJECT-TYPE
		SYNTAX					 INTEGER{ off(0),on(1)  }
		MAX-ACCESS			 read-create
		STATUS					 current
		DESCRIPTION			 " -- "
		::=  { interRatHcEntry  28 }


	interRatDelInterMeasSwitch		 OBJECT-TYPE
		SYNTAX					 INTEGER{ off(0),on(1)  }
		MAX-ACCESS			 read-create
		STATUS					 current
		DESCRIPTION			 " -- "
		::=  { interRatHcEntry  29 }


	interRatBlindSrvccSwitch		 OBJECT-TYPE
		SYNTAX					 INTEGER{ off(0),on(1)  }
		MAX-ACCESS			 read-create
		STATUS					 current
		DESCRIPTION			 " -- "
		::=  { interRatHcEntry  30 }


	ppHcAlgTable		 OBJECT-TYPE
		SYNTAX					 SEQUENCE  OF	 PpHcAlgEntry
		MAX-ACCESS			 not-accessible
		STATUS					 current
		DESCRIPTION			 " -- "
		::=  { hc  3 }


	ppHcAlgEntry		 OBJECT-TYPE
		SYNTAX					 PpHcAlgEntry
		MAX-ACCESS			 not-accessible
		STATUS					 current
		DESCRIPTION			 " -- "
		INDEX						{ ppHcAlgLcId }
		::=  { ppHcAlgTable  1 }


	PpHcAlgEntry		 ::=  SEQUENCE {
		ppHcAlgLcId					Integer32,
		ppHcAlgRowStatus					RowStatus,
		ppHcAlgTag					INTEGER,
		ppHcUeStayTimeTh					Unsigned32,
		ppHcPunishStep					Integer32,
		ppHcPunishMax					Integer32,
		ppHcPunishFreeTimer					Unsigned32
		}


	ppHcAlgLcId		 OBJECT-TYPE
		SYNTAX					 Integer32( 0 .. 23 )
		MAX-ACCESS			 not-accessible
		STATUS					 current
		DESCRIPTION			 " -- "
		::=  { ppHcAlgEntry  1 }


	ppHcAlgRowStatus		 OBJECT-TYPE
		SYNTAX					 RowStatus
		MAX-ACCESS			 read-create
		STATUS					 current
		DESCRIPTION			 " -- "
		::=  { ppHcAlgEntry  2 }


	ppHcAlgTag		 OBJECT-TYPE
		SYNTAX					 INTEGER{ off(0),on(1)  }
		MAX-ACCESS			 read-create
		STATUS					 current
		DESCRIPTION			 " -- "
		::=  { ppHcAlgEntry  3 }


	ppHcUeStayTimeTh		 OBJECT-TYPE
		SYNTAX					 Unsigned32( 0 .. 65535 )
		MAX-ACCESS			 read-create
		STATUS					 current
		DESCRIPTION			 " -- "
		::=  { ppHcAlgEntry  4 }


	ppHcPunishStep		 OBJECT-TYPE
		SYNTAX					 Integer32( 1 .. 15 )
		MAX-ACCESS			 read-create
		STATUS					 current
		DESCRIPTION			 " -- "
		::=  { ppHcAlgEntry  5 }


	ppHcPunishMax		 OBJECT-TYPE
		SYNTAX					 Integer32( 0 .. 60 )
		MAX-ACCESS			 read-create
		STATUS					 current
		DESCRIPTION			 " -- "
		::=  { ppHcAlgEntry  6 }


	ppHcPunishFreeTimer		 OBJECT-TYPE
		SYNTAX					 Unsigned32( 0 .. 65535 )
		MAX-ACCESS			 read-create
		STATUS					 current
		DESCRIPTION			 " -- "
		::=  { ppHcAlgEntry  7 }


	icic		 OBJECT IDENTIFIER
		::=  { cellAlgorithm  3 }


	icicTable		 OBJECT-TYPE
		SYNTAX					 SEQUENCE  OF	 IcicEntry
		MAX-ACCESS			 not-accessible
		STATUS					 current
		DESCRIPTION			 " -- "
		::=  { icic  1 }


	icicEntry		 OBJECT-TYPE
		SYNTAX					 IcicEntry
		MAX-ACCESS			 not-accessible
		STATUS					 current
		DESCRIPTION			 " -- "
		INDEX						{ icicLcId }
		::=  { icicTable  1 }


	IcicEntry		 ::=  SEQUENCE {
		icicLcId					Integer32,
		icicRowStatus					RowStatus,
		icicTag					INTEGER,
		icicAlgoType					INTEGER,
		icicCellType					INTEGER,
		icicUlPmax					Integer32,
		icicDlPamax					INTEGER,
		icicHiiSetPriA1					Integer32,
		icicHiiSetPriA2					Integer32,
		icicEdgeUeUlPrbSchedPri1					Integer32,
		icicEdgeUeUlPrbSchedPri2					Integer32,
		icicEdgeUeUlPrbSchedPri3					Integer32,
		icicEdgeUeUlPrbSchedPri4					Integer32,
		icicCenterUeUlPrbSchedPri1					Integer32,
		icicCenterUeUlPrbSchedPri2					Integer32,
		icicCenterUeUlPrbSchedPri3					Integer32,
		icicCenterUeUlPrbSchedPri4					Integer32,
		icicOiThresholed1					Integer32,
		icicOiThresholed2					Integer32,
		icicEdgeUeDlPrbSchedPri1					Integer32,
		icicEdgeUeDlPrbSchedPri2					Integer32,
		icicCenterUeDlPrbSchedPri1					Integer32,
		icicCenterUeDlPrbSchedPri2					Integer32,
		icicRntpTimer					Integer32,
		icicTestMode					INTEGER,
		icicUlStartPrbNoForEdgeUe					Integer32,
		icicDlStartPrbNoForEdgeUe					Integer32,
		icicUlPrbLenForEdgeUe					Integer32,
		icicDlPrbLenForEdgeUe					Integer32,
		icicMacStaticConfM1					Integer32,
		icicMacStaticConfM2					Integer32,
		icicMacSemiStaticConfUlM1					Integer32,
		icicMacSemiStaticConfDlM1					Integer32,
		icicMacSemiStaticConfM2					Integer32,
		icicEdgeUeDlPrbSchedTag					INTEGER
		}


	icicLcId		 OBJECT-TYPE
		SYNTAX					 Integer32( 0 .. 23 )
		MAX-ACCESS			 not-accessible
		STATUS					 current
		DESCRIPTION			 " -- "
		::=  { icicEntry  1 }


	icicRowStatus		 OBJECT-TYPE
		SYNTAX					 RowStatus
		MAX-ACCESS			 read-create
		STATUS					 current
		DESCRIPTION			 " -- "
		::=  { icicEntry  2 }


	icicTag		 OBJECT-TYPE
		SYNTAX					 INTEGER{ off(0),on(1)  }
		MAX-ACCESS			 read-create
		STATUS					 current
		DESCRIPTION			 " -- "
		::=  { icicEntry  3 }


	icicAlgoType		 OBJECT-TYPE
		SYNTAX					 INTEGER{ icicAlgoTypeSaticType(0),icicAlgoTypeSemiStaticType(1)  }
		MAX-ACCESS			 read-create
		STATUS					 current
		DESCRIPTION			 " -- "
		::=  { icicEntry  4 }


	icicCellType		 OBJECT-TYPE
		SYNTAX					 INTEGER{ icicCellTypeOne(0),icicCellTypeTwo(1),icicCellTypeThree(2)  }
		MAX-ACCESS			 read-create
		STATUS					 current
		DESCRIPTION			 " -- "
		::=  { icicEntry  5 }


	icicUlPmax		 OBJECT-TYPE
		SYNTAX					 Integer32( -30 .. 33 )
		MAX-ACCESS			 read-create
		STATUS					 current
		DESCRIPTION			 " -- "
		::=  { icicEntry  6 }


	icicDlPamax		 OBJECT-TYPE
		SYNTAX					 INTEGER{ db3(0),db2(1),db1(2),db0(3),dbn1(4),dbn2(5),dbn3(6),dbn6(7)  }
		MAX-ACCESS			 read-create
		STATUS					 current
		DESCRIPTION			 " -- "
		::=  { icicEntry  7 }


	icicHiiSetPriA1		 OBJECT-TYPE
		SYNTAX					 Integer32( -128 .. 127 )
		MAX-ACCESS			 read-create
		STATUS					 current
		DESCRIPTION			 " -- "
		::=  { icicEntry  8 }


	icicHiiSetPriA2		 OBJECT-TYPE
		SYNTAX					 Integer32( -128 .. 127 )
		MAX-ACCESS			 read-create
		STATUS					 current
		DESCRIPTION			 " -- "
		::=  { icicEntry  9 }


	icicEdgeUeUlPrbSchedPri1		 OBJECT-TYPE
		SYNTAX					 Integer32( -128 .. 127 )
		MAX-ACCESS			 read-create
		STATUS					 current
		DESCRIPTION			 " -- "
		::=  { icicEntry  10 }


	icicEdgeUeUlPrbSchedPri2		 OBJECT-TYPE
		SYNTAX					 Integer32( -128 .. 127 )
		MAX-ACCESS			 read-create
		STATUS					 current
		DESCRIPTION			 " -- "
		::=  { icicEntry  11 }


	icicEdgeUeUlPrbSchedPri3		 OBJECT-TYPE
		SYNTAX					 Integer32( -128 .. 127 )
		MAX-ACCESS			 read-create
		STATUS					 current
		DESCRIPTION			 " -- "
		::=  { icicEntry  12 }


	icicEdgeUeUlPrbSchedPri4		 OBJECT-TYPE
		SYNTAX					 Integer32( -128 .. 127 )
		MAX-ACCESS			 read-create
		STATUS					 current
		DESCRIPTION			 " -- "
		::=  { icicEntry  13 }


	icicCenterUeUlPrbSchedPri1		 OBJECT-TYPE
		SYNTAX					 Integer32( -128 .. 127 )
		MAX-ACCESS			 read-create
		STATUS					 current
		DESCRIPTION			 " -- "
		::=  { icicEntry  14 }


	icicCenterUeUlPrbSchedPri2		 OBJECT-TYPE
		SYNTAX					 Integer32( -128 .. 127 )
		MAX-ACCESS			 read-create
		STATUS					 current
		DESCRIPTION			 " -- "
		::=  { icicEntry  15 }


	icicCenterUeUlPrbSchedPri3		 OBJECT-TYPE
		SYNTAX					 Integer32( -128 .. 127 )
		MAX-ACCESS			 read-create
		STATUS					 current
		DESCRIPTION			 " -- "
		::=  { icicEntry  16 }


	icicCenterUeUlPrbSchedPri4		 OBJECT-TYPE
		SYNTAX					 Integer32( -128 .. 127 )
		MAX-ACCESS			 read-create
		STATUS					 current
		DESCRIPTION			 " -- "
		::=  { icicEntry  17 }


	icicOiThresholed1		 OBJECT-TYPE
		SYNTAX					 Integer32( 0 .. 20 )
		MAX-ACCESS			 read-create
		STATUS					 current
		DESCRIPTION			 " -- "
		::=  { icicEntry  18 }


	icicOiThresholed2		 OBJECT-TYPE
		SYNTAX					 Integer32( 0 .. 20 )
		MAX-ACCESS			 read-create
		STATUS					 current
		DESCRIPTION			 " -- "
		::=  { icicEntry  19 }


	icicEdgeUeDlPrbSchedPri1		 OBJECT-TYPE
		SYNTAX					 Integer32( -128 .. 127 )
		MAX-ACCESS			 read-create
		STATUS					 current
		DESCRIPTION			 " -- "
		::=  { icicEntry  20 }


	icicEdgeUeDlPrbSchedPri2		 OBJECT-TYPE
		SYNTAX					 Integer32( -128 .. 127 )
		MAX-ACCESS			 read-create
		STATUS					 current
		DESCRIPTION			 " -- "
		::=  { icicEntry  21 }


	icicCenterUeDlPrbSchedPri1		 OBJECT-TYPE
		SYNTAX					 Integer32( -128 .. 127 )
		MAX-ACCESS			 read-create
		STATUS					 current
		DESCRIPTION			 " -- "
		::=  { icicEntry  22 }


	icicCenterUeDlPrbSchedPri2		 OBJECT-TYPE
		SYNTAX					 Integer32( -128 .. 127 )
		MAX-ACCESS			 read-create
		STATUS					 current
		DESCRIPTION			 " -- "
		::=  { icicEntry  23 }


	icicRntpTimer		 OBJECT-TYPE
		SYNTAX					 Integer32( 1 .. 200 )
		MAX-ACCESS			 read-create
		STATUS					 current
		DESCRIPTION			 " -- "
		::=  { icicEntry  24 }


	icicTestMode		 OBJECT-TYPE
		SYNTAX					 INTEGER{ icicTestModeOpen(0),icicTestModeClose(1)  }
		MAX-ACCESS			 read-create
		STATUS					 current
		DESCRIPTION			 " -- "
		::=  { icicEntry  25 }


	icicUlStartPrbNoForEdgeUe		 OBJECT-TYPE
		SYNTAX					 Integer32( 0 .. 99 )
		MAX-ACCESS			 read-create
		STATUS					 current
		DESCRIPTION			 " -- "
		::=  { icicEntry  26 }


	icicDlStartPrbNoForEdgeUe		 OBJECT-TYPE
		SYNTAX					 Integer32( 0 .. 99 )
		MAX-ACCESS			 read-create
		STATUS					 current
		DESCRIPTION			 " -- "
		::=  { icicEntry  27 }


	icicUlPrbLenForEdgeUe		 OBJECT-TYPE
		SYNTAX					 Integer32( 0 .. 100 )
		MAX-ACCESS			 read-create
		STATUS					 current
		DESCRIPTION			 " -- "
		::=  { icicEntry  28 }


	icicDlPrbLenForEdgeUe		 OBJECT-TYPE
		SYNTAX					 Integer32( 0 .. 100 )
		MAX-ACCESS			 read-create
		STATUS					 current
		DESCRIPTION			 " -- "
		::=  { icicEntry  29 }


	icicMacStaticConfM1		 OBJECT-TYPE
		SYNTAX					 Integer32( 0 .. 255 )
		MAX-ACCESS			 read-create
		STATUS					 current
		DESCRIPTION			 " -- "
		::=  { icicEntry  30 }


	icicMacStaticConfM2		 OBJECT-TYPE
		SYNTAX					 Integer32( 0 .. 255 )
		MAX-ACCESS			 read-create
		STATUS					 current
		DESCRIPTION			 " -- "
		::=  { icicEntry  31 }


	icicMacSemiStaticConfUlM1		 OBJECT-TYPE
		SYNTAX					 Integer32( 0 .. 255 )
		MAX-ACCESS			 read-create
		STATUS					 current
		DESCRIPTION			 " -- "
		::=  { icicEntry  32 }


	icicMacSemiStaticConfDlM1		 OBJECT-TYPE
		SYNTAX					 Integer32( 0 .. 255 )
		MAX-ACCESS			 read-create
		STATUS					 current
		DESCRIPTION			 " -- "
		::=  { icicEntry  33 }


	icicMacSemiStaticConfM2		 OBJECT-TYPE
		SYNTAX					 Integer32( 0 .. 255 )
		MAX-ACCESS			 read-create
		STATUS					 current
		DESCRIPTION			 " -- "
		::=  { icicEntry  34 }


	icicEdgeUeDlPrbSchedTag		 OBJECT-TYPE
		SYNTAX					 INTEGER{ off(0),on(1)  }
		MAX-ACCESS			 read-create
		STATUS					 current
		DESCRIPTION			 " -- "
		::=  { icicEntry  35 }


	lbc		 OBJECT IDENTIFIER
		::=  { cellAlgorithm  4 }


	lbcTable		 OBJECT-TYPE
		SYNTAX					 SEQUENCE  OF	 LbcEntry
		MAX-ACCESS			 not-accessible
		STATUS					 current
		DESCRIPTION			 " -- "
		::=  { lbc  1 }


	lbcEntry		 OBJECT-TYPE
		SYNTAX					 LbcEntry
		MAX-ACCESS			 not-accessible
		STATUS					 current
		DESCRIPTION			 " -- "
		INDEX						{ lbcLcId }
		::=  { lbcTable  1 }


	LbcEntry		 ::=  SEQUENCE {
		lbcLcId					Integer32,
		lbcRowStatus					RowStatus,
		lbcAdjCellBlanceAlgoType					INTEGER,
		lbcAdjCellBlanceRecoverAlgoType					INTEGER,
		lbcUlHardwardTh1					INTEGER,
		lbcDlHardwardTh1					INTEGER,
		lbcUlS1TnlTh1					INTEGER,
		lbcDlS1TnlTh1					INTEGER,
		lbcUlHardwardTh2					INTEGER,
		lbcDlHardwardTh2					INTEGER,
		lbcUlS1TnlTh2					INTEGER,
		lbcDlS1TnlTh2					INTEGER,
		lbcAdjCellUlHardwardTh3					INTEGER,
		lbcAdjCellDlHardwardTh3					INTEGER,
		lbcAdjCellUlS1TnlTh3					INTEGER,
		lbcAdjCellDlS1TnlTh3					INTEGER,
		lbcAdjCellUlPrbUsageTh3					Integer32,
		lbcAdjCellDlPrbUsageTh3					Integer32,
		lbcAdjCellUlHardwardTh4					INTEGER,
		lbcAdjCellDlHardwardTh4					INTEGER,
		lbcAdjCellUlS1TnlTh4					INTEGER,
		lbcAdjCellDlS1TnlTh4					INTEGER,
		lbcAdjCellUlPrbUsageTh4					Integer32,
		lbcAdjCellDlPrbUsageTh4					Integer32,
		lbcRedirectionFreqBand					INTEGER,
		lbcRedirectionCenterFreq					Integer32,
		lbcEveryMigrationTh					Integer32,
		lbcRedirectionMultiBandInfoFlag					INTEGER,
		lbcRedirectionMultiBandInfo					Integer32,
		lbcRedirectionEARFCN					Integer32
		}


	lbcLcId		 OBJECT-TYPE
		SYNTAX					 Integer32( 0 .. 23 )
		MAX-ACCESS			 not-accessible
		STATUS					 current
		DESCRIPTION			 " -- "
		::=  { lbcEntry  1 }


	lbcRowStatus		 OBJECT-TYPE
		SYNTAX					 RowStatus
		MAX-ACCESS			 read-create
		STATUS					 current
		DESCRIPTION			 " -- "
		::=  { lbcEntry  2 }


	lbcAdjCellBlanceAlgoType		 OBJECT-TYPE
		SYNTAX					 INTEGER{ balanceFixThresholdAlgoType(0),balanceDeltaThresholdAlgoType(1)  }
		MAX-ACCESS			 read-create
		STATUS					 current
		DESCRIPTION			 " -- "
		::=  { lbcEntry  4 }


	lbcAdjCellBlanceRecoverAlgoType		 OBJECT-TYPE
		SYNTAX					 INTEGER{ balanceRecoverFixThresholdAlgoType(0),balanceRecoverDeltaThresholdAlgoType(1)  }
		MAX-ACCESS			 read-create
		STATUS					 current
		DESCRIPTION			 " -- "
		::=  { lbcEntry  5 }


	lbcUlHardwardTh1		 OBJECT-TYPE
		SYNTAX					 INTEGER{ lbcLowLoad(0),lbcMediumLoad(1),lbcHighLoad(2),lbcOverLoad(3)  }
		MAX-ACCESS			 read-create
		STATUS					 current
		DESCRIPTION			 " -- "
		::=  { lbcEntry  9 }


	lbcDlHardwardTh1		 OBJECT-TYPE
		SYNTAX					 INTEGER{ lbcLowLoad(0),lbcMediumLoad(1),lbcHighLoad(2),lbcOverLoad(3)  }
		MAX-ACCESS			 read-create
		STATUS					 current
		DESCRIPTION			 " -- "
		::=  { lbcEntry  10 }


	lbcUlS1TnlTh1		 OBJECT-TYPE
		SYNTAX					 INTEGER{ lbcLowLoad(0),lbcMediumLoad(1),lbcHighLoad(2),lbcOverLoad(3)  }
		MAX-ACCESS			 read-create
		STATUS					 current
		DESCRIPTION			 " -- "
		::=  { lbcEntry  11 }


	lbcDlS1TnlTh1		 OBJECT-TYPE
		SYNTAX					 INTEGER{ lbcLowLoad(0),lbcMediumLoad(1),lbcHighLoad(2),lbcOverLoad(3)  }
		MAX-ACCESS			 read-create
		STATUS					 current
		DESCRIPTION			 " -- "
		::=  { lbcEntry  12 }


	lbcUlHardwardTh2		 OBJECT-TYPE
		SYNTAX					 INTEGER{ lbcLowLoad(0),lbcMediumLoad(1),lbcHighLoad(2),lbcOverLoad(3)  }
		MAX-ACCESS			 read-create
		STATUS					 current
		DESCRIPTION			 " -- "
		::=  { lbcEntry  15 }


	lbcDlHardwardTh2		 OBJECT-TYPE
		SYNTAX					 INTEGER{ lbcLowLoad(0),lbcMediumLoad(1),lbcHighLoad(2),lbcOverLoad(3)  }
		MAX-ACCESS			 read-create
		STATUS					 current
		DESCRIPTION			 " -- "
		::=  { lbcEntry  16 }


	lbcUlS1TnlTh2		 OBJECT-TYPE
		SYNTAX					 INTEGER{ lbcLowLoad(0),lbcMediumLoad(1),lbcHighLoad(2),lbcOverLoad(3)  }
		MAX-ACCESS			 read-create
		STATUS					 current
		DESCRIPTION			 " -- "
		::=  { lbcEntry  17 }


	lbcDlS1TnlTh2		 OBJECT-TYPE
		SYNTAX					 INTEGER{ lbcLowLoad(0),lbcMediumLoad(1),lbcHighLoad(2),lbcOverLoad(3)  }
		MAX-ACCESS			 read-create
		STATUS					 current
		DESCRIPTION			 " -- "
		::=  { lbcEntry  18 }


	lbcAdjCellUlHardwardTh3		 OBJECT-TYPE
		SYNTAX					 INTEGER{ lbcLowLoad(0),lbcMediumLoad(1),lbcHighLoad(2),lbcOverLoad(3)  }
		MAX-ACCESS			 read-create
		STATUS					 current
		DESCRIPTION			 " -- "
		::=  { lbcEntry  21 }


	lbcAdjCellDlHardwardTh3		 OBJECT-TYPE
		SYNTAX					 INTEGER{ lbcLowLoad(0),lbcMediumLoad(1),lbcHighLoad(2),lbcOverLoad(3)  }
		MAX-ACCESS			 read-create
		STATUS					 current
		DESCRIPTION			 " -- "
		::=  { lbcEntry  22 }


	lbcAdjCellUlS1TnlTh3		 OBJECT-TYPE
		SYNTAX					 INTEGER{ lbcLowLoad(0),lbcMediumLoad(1),lbcHighLoad(2),lbcOverLoad(3)  }
		MAX-ACCESS			 read-create
		STATUS					 current
		DESCRIPTION			 " -- "
		::=  { lbcEntry  23 }


	lbcAdjCellDlS1TnlTh3		 OBJECT-TYPE
		SYNTAX					 INTEGER{ lbcLowLoad(0),lbcMediumLoad(1),lbcHighLoad(2),lbcOverLoad(3)  }
		MAX-ACCESS			 read-create
		STATUS					 current
		DESCRIPTION			 " -- "
		::=  { lbcEntry  24 }


	lbcAdjCellUlPrbUsageTh3		 OBJECT-TYPE
		SYNTAX					 Integer32( 0 .. 100 )
		MAX-ACCESS			 read-create
		STATUS					 current
		DESCRIPTION			 " -- "
		::=  { lbcEntry  25 }


	lbcAdjCellDlPrbUsageTh3		 OBJECT-TYPE
		SYNTAX					 Integer32( 0 .. 100 )
		MAX-ACCESS			 read-create
		STATUS					 current
		DESCRIPTION			 " -- "
		::=  { lbcEntry  26 }


	lbcAdjCellUlHardwardTh4		 OBJECT-TYPE
		SYNTAX					 INTEGER{ lbcLowLoad(0),lbcMediumLoad(1),lbcHighLoad(2),lbcOverLoad(3)  }
		MAX-ACCESS			 read-create
		STATUS					 current
		DESCRIPTION			 " -- "
		::=  { lbcEntry  27 }


	lbcAdjCellDlHardwardTh4		 OBJECT-TYPE
		SYNTAX					 INTEGER{ lbcLowLoad(0),lbcMediumLoad(1),lbcHighLoad(2),lbcOverLoad(3)  }
		MAX-ACCESS			 read-create
		STATUS					 current
		DESCRIPTION			 " -- "
		::=  { lbcEntry  28 }


	lbcAdjCellUlS1TnlTh4		 OBJECT-TYPE
		SYNTAX					 INTEGER{ lbcLowLoad(0),lbcMediumLoad(1),lbcHighLoad(2),lbcOverLoad(3)  }
		MAX-ACCESS			 read-create
		STATUS					 current
		DESCRIPTION			 " -- "
		::=  { lbcEntry  29 }


	lbcAdjCellDlS1TnlTh4		 OBJECT-TYPE
		SYNTAX					 INTEGER{ lbcLowLoad(0),lbcMediumLoad(1),lbcHighLoad(2),lbcOverLoad(3)  }
		MAX-ACCESS			 read-create
		STATUS					 current
		DESCRIPTION			 " -- "
		::=  { lbcEntry  30 }


	lbcAdjCellUlPrbUsageTh4		 OBJECT-TYPE
		SYNTAX					 Integer32( 0 .. 100 )
		MAX-ACCESS			 read-create
		STATUS					 current
		DESCRIPTION			 " -- "
		::=  { lbcEntry  31 }


	lbcAdjCellDlPrbUsageTh4		 OBJECT-TYPE
		SYNTAX					 Integer32( 0 .. 100 )
		MAX-ACCESS			 read-create
		STATUS					 current
		DESCRIPTION			 " -- "
		::=  { lbcEntry  32 }


	lbcRedirectionFreqBand		 OBJECT-TYPE
		SYNTAX					 INTEGER{ band1(1),band2(2),band3(3),band4(4),band5(5),band7(7),band8(8),band9(9),band10(10),band11(11),band12(12),band13(13),band14(14),band17(17),band18(18),band19(19),band20(20),band21(21),band22(22),band23(23),band24(24),band25(25),band26(26),band33(33),band34(34),band35(35),band36(36),band37(37),band38(38),band39(39),band40(40),band41(41),band44(44),band61(61),band62(62)  }
		MAX-ACCESS			 read-create
		STATUS					 current
		DESCRIPTION			 " -- "
		::=  { lbcEntry  33 }


	lbcRedirectionCenterFreq		 OBJECT-TYPE
		SYNTAX					 Integer32( 0 .. 65535 )
		MAX-ACCESS			 read-create
		STATUS					 current
		DESCRIPTION			 " -- "
		::=  { lbcEntry  34 }


	lbcEveryMigrationTh		 OBJECT-TYPE
		SYNTAX					 Integer32( 0 .. 100 )
		MAX-ACCESS			 read-create
		STATUS					 current
		DESCRIPTION			 " -- "
		::=  { lbcEntry  37 }


	lbcRedirectionMultiBandInfoFlag		 OBJECT-TYPE
		SYNTAX					 INTEGER{ false(0),true(1)  }
		MAX-ACCESS			 read-create
		STATUS					 current
		DESCRIPTION			 " -- "
		::=  { lbcEntry  42 }


	lbcRedirectionMultiBandInfo		 OBJECT-TYPE
		SYNTAX					 Integer32( 38|41 )
		MAX-ACCESS			 read-create
		STATUS					 current
		DESCRIPTION			 " -- "
		::=  { lbcEntry  43 }


	lbcRedirectionEARFCN		 OBJECT-TYPE
		SYNTAX					 Integer32( 0 .. 65535 )
		MAX-ACCESS			 read-only
		STATUS					 current
		DESCRIPTION			 " -- "
		::=  { lbcEntry  44 }


	ulPowerControl		 OBJECT IDENTIFIER
		::=  { cellAlgorithm  5 }


	ulPowerControlTable		 OBJECT-TYPE
		SYNTAX					 SEQUENCE  OF	 UlPowerControlEntry
		MAX-ACCESS			 not-accessible
		STATUS					 current
		DESCRIPTION			 " -- "
		::=  { ulPowerControl  1 }


	ulPowerControlEntry		 OBJECT-TYPE
		SYNTAX					 UlPowerControlEntry
		MAX-ACCESS			 not-accessible
		STATUS					 current
		DESCRIPTION			 " -- "
		INDEX						{ ulPwrLcId }
		::=  { ulPowerControlTable  1 }


	UlPowerControlEntry		 ::=  SEQUENCE {
		ulPwrLcId					Integer32,
		ulPwrRowStatus					RowStatus,
		ulPwrPucchSinrTarget					Integer32,
		ulPwrAlpha					INTEGER,
		ulPwrP0NominalPusch					Integer32,
		ulPwrP0NominalPucch					Integer32,
		ulPwrDeltaFPucchFormat1					INTEGER,
		ulPwrDeltaFPucchFormat1b					INTEGER,
		ulPwrDeltaFPucchFormat2					INTEGER,
		ulPwrDeltaFPucchFormat2a					INTEGER,
		ulPwrDeltaFPucchFormat2b					INTEGER,
		ulPwrDeltaPreambleMsg3					INTEGER,
		ulPwrP0UePuschNonPersistantSched					Integer32,
		ulPwrDeltaMcsEnabled					INTEGER,
		ulPwrAccumulationEnabled					INTEGER,
		ulPwrP0uePucch					Integer32,
		ulPwrSrsOffset					Integer32,
		ulPwrFilterCoeff					INTEGER,
		ulPwrPuschTpcFormatChoice					INTEGER,
		ulPwrPucchTpcFormatChoice					INTEGER,
		ulPwrPuschPowerSwitch					INTEGER,
		ulPwrPucchPowerSwitch					INTEGER,
		ulPwrMsg3PowerCtrlSwitch					INTEGER,
		ulPwrPowerCtrlDci3Switch					INTEGER,
		ulPwrPHRSwitch					INTEGER,
		ulPwrDeltaFPUCCHFormat3R10					INTEGER,
		ulPwrDeltaFPUCCHFormat1bCSR10					INTEGER,
		ulPwrDeltaTXDoffsetPUCCHFormat3R10					INTEGER,
		ulPwrDeltaTXDoffsetPUCCHFormat22a2bR10					INTEGER,
		ulPwrDeltaTXDoffsetPUCCHFormat1a1bR10					INTEGER,
		ulPwrDeltaTXDoffsetPUCCHFormat1R10					INTEGER,
		ulPwrSrsOffsetAp					Integer32,
		ulPwrPuschDci3or3aMinPeriod					Integer32,
		ulPwrPucchDci3or3aMinPeriod					Integer32,
		ulPwrCtrlOptSwitch					INTEGER
		}


	ulPwrLcId		 OBJECT-TYPE
		SYNTAX					 Integer32( 0 .. 23 )
		MAX-ACCESS			 not-accessible
		STATUS					 current
		DESCRIPTION			 " -- "
		::=  { ulPowerControlEntry  1 }


	ulPwrRowStatus		 OBJECT-TYPE
		SYNTAX					 RowStatus
		MAX-ACCESS			 read-create
		STATUS					 current
		DESCRIPTION			 " -- "
		::=  { ulPowerControlEntry  2 }


	ulPwrPucchSinrTarget		 OBJECT-TYPE
		SYNTAX					 Integer32( -128 .. 127 )
		MAX-ACCESS			 read-create
		STATUS					 current
		DESCRIPTION			 " -- "
		::=  { ulPowerControlEntry  3 }


	ulPwrAlpha		 OBJECT-TYPE
		SYNTAX					 INTEGER{ al0(0),al04(1),al05(2),al06(3),al07(4),al08(5),al09(6),al1(7)  }
		MAX-ACCESS			 read-create
		STATUS					 current
		DESCRIPTION			 " -- "
		::=  { ulPowerControlEntry  4 }


	ulPwrP0NominalPusch		 OBJECT-TYPE
		SYNTAX					 Integer32( -126 .. 24 )
		MAX-ACCESS			 read-create
		STATUS					 current
		DESCRIPTION			 " -- "
		::=  { ulPowerControlEntry  5 }


	ulPwrP0NominalPucch		 OBJECT-TYPE
		SYNTAX					 Integer32( -127 .. -96 )
		MAX-ACCESS			 read-create
		STATUS					 current
		DESCRIPTION			 " -- "
		::=  { ulPowerControlEntry  6 }


	ulPwrDeltaFPucchFormat1		 OBJECT-TYPE
		SYNTAX					 INTEGER{ deltaFn2(0),deltaF0(1),deltaF2(2)  }
		MAX-ACCESS			 read-create
		STATUS					 current
		DESCRIPTION			 " -- "
		::=  { ulPowerControlEntry  7 }


	ulPwrDeltaFPucchFormat1b		 OBJECT-TYPE
		SYNTAX					 INTEGER{ deltaF1(0),deltaF3(1),deltaF5(2)  }
		MAX-ACCESS			 read-create
		STATUS					 current
		DESCRIPTION			 " -- "
		::=  { ulPowerControlEntry  8 }


	ulPwrDeltaFPucchFormat2		 OBJECT-TYPE
		SYNTAX					 INTEGER{ deltaFn2(0),deltaF0(1),deltaF1(2),deltaF2(3)  }
		MAX-ACCESS			 read-create
		STATUS					 current
		DESCRIPTION			 " -- "
		::=  { ulPowerControlEntry  9 }


	ulPwrDeltaFPucchFormat2a		 OBJECT-TYPE
		SYNTAX					 INTEGER{ deltaFn2(0),deltaF0(1),deltaF2(2)  }
		MAX-ACCESS			 read-create
		STATUS					 current
		DESCRIPTION			 " -- "
		::=  { ulPowerControlEntry  10 }


	ulPwrDeltaFPucchFormat2b		 OBJECT-TYPE
		SYNTAX					 INTEGER{ deltaFn2(0),deltaF0(1),deltaF2(2)  }
		MAX-ACCESS			 read-create
		STATUS					 current
		DESCRIPTION			 " -- "
		::=  { ulPowerControlEntry  11 }


	ulPwrDeltaPreambleMsg3		 OBJECT-TYPE
		SYNTAX					 INTEGER{ deltaPreambleMsg3DbN2(0),deltaPreambleMsg3Db0(1),deltaPreambleMsg3Db2(2),deltaPreambleMsg3Db4(3),deltaPreambleMsg3Db6(4),deltaPreambleMsg3Db8(5),deltaPreambleMsg3Db10(6),deltaPreambleMsg3Db12(7)  }
		MAX-ACCESS			 read-create
		STATUS					 current
		DESCRIPTION			 " -- "
		::=  { ulPowerControlEntry  12 }


	ulPwrP0UePuschNonPersistantSched		 OBJECT-TYPE
		SYNTAX					 Integer32( -8 .. 7 )
		MAX-ACCESS			 read-create
		STATUS					 current
		DESCRIPTION			 " -- "
		::=  { ulPowerControlEntry  13 }


	ulPwrDeltaMcsEnabled		 OBJECT-TYPE
		SYNTAX					 INTEGER{ en0(0),en1(1)  }
		MAX-ACCESS			 read-create
		STATUS					 current
		DESCRIPTION			 " -- "
		::=  { ulPowerControlEntry  14 }


	ulPwrAccumulationEnabled		 OBJECT-TYPE
		SYNTAX					 INTEGER{ true(1),false(0)  }
		MAX-ACCESS			 read-create
		STATUS					 current
		DESCRIPTION			 " -- "
		::=  { ulPowerControlEntry  15 }


	ulPwrP0uePucch		 OBJECT-TYPE
		SYNTAX					 Integer32( -8 .. 7 )
		MAX-ACCESS			 read-create
		STATUS					 current
		DESCRIPTION			 " -- "
		::=  { ulPowerControlEntry  16 }


	ulPwrSrsOffset		 OBJECT-TYPE
		SYNTAX					 Integer32( 0 .. 15 )
		MAX-ACCESS			 read-create
		STATUS					 current
		DESCRIPTION			 " -- "
		::=  { ulPowerControlEntry  17 }


	ulPwrFilterCoeff		 OBJECT-TYPE
		SYNTAX					 INTEGER{ fc0(0),fc1(1),fc2(2),fc3(3),fc4(4),fc5(5),fc6(6),fc7(7),fc8(8),fc9(9),fc11(10),fc13(11),fc15(12),fc17(13),fc19(14)  }
		MAX-ACCESS			 read-create
		STATUS					 current
		DESCRIPTION			 " -- "
		::=  { ulPowerControlEntry  18 }


	ulPwrPuschTpcFormatChoice		 OBJECT-TYPE
		SYNTAX					 INTEGER{ format3(0),format3A(1)  }
		MAX-ACCESS			 read-create
		STATUS					 current
		DESCRIPTION			 " -- "
		::=  { ulPowerControlEntry  20 }


	ulPwrPucchTpcFormatChoice		 OBJECT-TYPE
		SYNTAX					 INTEGER{ format3(0),format3A(1)  }
		MAX-ACCESS			 read-create
		STATUS					 current
		DESCRIPTION			 " -- "
		::=  { ulPowerControlEntry  21 }


	ulPwrPuschPowerSwitch		 OBJECT-TYPE
		SYNTAX					 INTEGER{ off(0),on(1)  }
		MAX-ACCESS			 read-create
		STATUS					 current
		DESCRIPTION			 " -- "
		::=  { ulPowerControlEntry  22 }


	ulPwrPucchPowerSwitch		 OBJECT-TYPE
		SYNTAX					 INTEGER{ off(0),on(1)  }
		MAX-ACCESS			 read-create
		STATUS					 current
		DESCRIPTION			 " -- "
		::=  { ulPowerControlEntry  23 }


	ulPwrMsg3PowerCtrlSwitch		 OBJECT-TYPE
		SYNTAX					 INTEGER{ off(0),on(1)  }
		MAX-ACCESS			 read-create
		STATUS					 current
		DESCRIPTION			 " -- "
		::=  { ulPowerControlEntry  24 }


	ulPwrPowerCtrlDci3Switch		 OBJECT-TYPE
		SYNTAX					 INTEGER{ off(0),on(1)  }
		MAX-ACCESS			 read-create
		STATUS					 current
		DESCRIPTION			 " -- "
		::=  { ulPowerControlEntry  25 }


	ulPwrPHRSwitch		 OBJECT-TYPE
		SYNTAX					 INTEGER{ off(0),on(1)  }
		MAX-ACCESS			 read-create
		STATUS					 current
		DESCRIPTION			 " -- "
		::=  { ulPowerControlEntry  26 }


	ulPwrDeltaFPUCCHFormat3R10		 OBJECT-TYPE
		SYNTAX					 INTEGER{ deltaFn1(0),delataF0(1),delataF1(2),delataF2(3),delataF3(4),delataF4(5),delataF5(6),delataF6(7)  }
		MAX-ACCESS			 read-create
		STATUS					 current
		DESCRIPTION			 " -- "
		::=  { ulPowerControlEntry  27 }


	ulPwrDeltaFPUCCHFormat1bCSR10		 OBJECT-TYPE
		SYNTAX					 INTEGER{ delataF1(0),delataF2(1)  }
		MAX-ACCESS			 read-create
		STATUS					 current
		DESCRIPTION			 " -- "
		::=  { ulPowerControlEntry  28 }


	ulPwrDeltaTXDoffsetPUCCHFormat3R10		 OBJECT-TYPE
		SYNTAX					 INTEGER{ db0(0),dbn2(1)  }
		MAX-ACCESS			 read-create
		STATUS					 current
		DESCRIPTION			 " -- "
		::=  { ulPowerControlEntry  29 }


	ulPwrDeltaTXDoffsetPUCCHFormat22a2bR10		 OBJECT-TYPE
		SYNTAX					 INTEGER{ db0(0),dbn2(1)  }
		MAX-ACCESS			 read-create
		STATUS					 current
		DESCRIPTION			 " -- "
		::=  { ulPowerControlEntry  30 }


	ulPwrDeltaTXDoffsetPUCCHFormat1a1bR10		 OBJECT-TYPE
		SYNTAX					 INTEGER{ db0(0),dbn2(1)  }
		MAX-ACCESS			 read-create
		STATUS					 current
		DESCRIPTION			 " -- "
		::=  { ulPowerControlEntry  31 }


	ulPwrDeltaTXDoffsetPUCCHFormat1R10		 OBJECT-TYPE
		SYNTAX					 INTEGER{ db0(0),dbn2(1)  }
		MAX-ACCESS			 read-create
		STATUS					 current
		DESCRIPTION			 " -- "
		::=  { ulPowerControlEntry  32 }


	ulPwrSrsOffsetAp		 OBJECT-TYPE
		SYNTAX					 Integer32( 0 .. 15 )
		MAX-ACCESS			 read-create
		STATUS					 current
		DESCRIPTION			 " -- "
		::=  { ulPowerControlEntry  33 }


	ulPwrPuschDci3or3aMinPeriod		 OBJECT-TYPE
		SYNTAX					 Integer32( 1 .. 2000 )
		MAX-ACCESS			 read-create
		STATUS					 current
		DESCRIPTION			 " -- "
		::=  { ulPowerControlEntry  34 }


	ulPwrPucchDci3or3aMinPeriod		 OBJECT-TYPE
		SYNTAX					 Integer32( 1 .. 2000 )
		MAX-ACCESS			 read-create
		STATUS					 current
		DESCRIPTION			 " -- "
		::=  { ulPowerControlEntry  35 }


	ulPwrCtrlOptSwitch		 OBJECT-TYPE
		SYNTAX					 INTEGER{ off(0),on(1)  }
		MAX-ACCESS			 read-create
		STATUS					 current
		DESCRIPTION			 " -- "
		::=  { ulPowerControlEntry  36 }


	mroTable		 OBJECT-TYPE
		SYNTAX					 SEQUENCE  OF	 MroEntry
		MAX-ACCESS			 not-accessible
		STATUS					 current
		DESCRIPTION			 " -- "
		::=  { ulPowerControl  2 }


	mroEntry		 OBJECT-TYPE
		SYNTAX					 MroEntry
		MAX-ACCESS			 not-accessible
		STATUS					 current
		DESCRIPTION			 " -- "
		INDEX						{ mroLcId }
		::=  { mroTable  1 }


	MroEntry		 ::=  SEQUENCE {
		mroLcId					Integer32,
		mroRowStatus					RowStatus,
		mroSwitch					INTEGER,
		mroTooEarlyHoTh					Integer32,
		mroTooLateHoTh					Integer32,
		mroWrongHoTh					Integer32,
		mroPingPangHoTh					Integer32,
		mroTotalSucHoTh					Integer32,
		mroOffsetStep					INTEGER,
		mroHysteresisStep					INTEGER,
		mroStage					INTEGER,
		mroRsrpTh					Integer32,
		mroRsrqTh					Integer32,
		mroHoTh					Integer32,
		mroRollBackTrigger					INTEGER,
		mroPingPangTimeTh					Unsigned32,
		mroTotalPingPangTh					Unsigned32,
		mroPeriod					Unsigned32,
		mroTooEarlyHoNumTh					Unsigned32,
		mroTooLateHoNumTh					Unsigned32,
		mroWrongHoNumTh					Unsigned32,
		mroPingPangHoNumTh					Unsigned32,
		mroHoNumRatioRelation					INTEGER,
		mroEventRsrpStep					INTEGER,
		mroA2ThBaseHighTh					Integer32,
		mroA2ThBaseLowTh					Integer32,
		mroA3OffsetThBaseHighTh					INTEGER,
		mroA3OffsetThBaseLowTh					INTEGER,
		mroA3TTTThBaseHighTh					INTEGER,
		mroA3TTTThBaseLowTh					INTEGER,
		mroA3HysBaseHighTh					INTEGER,
		mroA3HysBaseLowTh					INTEGER,
		mroA4ThBaseHighTh					Integer32,
		mroA4ThBaseLowTh					Integer32,
		mroA5Th1BaseHighTh					Integer32,
		mroA5Th1BaseLowTh					Integer32,
		mroA5Th2BaseHighTh					Integer32,
		mroA5Th2BaseLowTh					Integer32,
		mroCellParaAdjRatioTh					Integer32
		}


	mroLcId		 OBJECT-TYPE
		SYNTAX					 Integer32( 0 .. 23 )
		MAX-ACCESS			 not-accessible
		STATUS					 current
		DESCRIPTION			 " -- "
		::=  { mroEntry  1 }


	mroRowStatus		 OBJECT-TYPE
		SYNTAX					 RowStatus
		MAX-ACCESS			 read-create
		STATUS					 current
		DESCRIPTION			 " -- "
		::=  { mroEntry  2 }


	mroSwitch		 OBJECT-TYPE
		SYNTAX					 INTEGER{ off(0),on(1)  }
		MAX-ACCESS			 read-create
		STATUS					 current
		DESCRIPTION			 " -- "
		::=  { mroEntry  3 }


	mroTooEarlyHoTh		 OBJECT-TYPE
		SYNTAX					 Integer32( 0 .. 100 )
		MAX-ACCESS			 read-create
		STATUS					 current
		DESCRIPTION			 " -- "
		::=  { mroEntry  4 }


	mroTooLateHoTh		 OBJECT-TYPE
		SYNTAX					 Integer32( 0 .. 100 )
		MAX-ACCESS			 read-create
		STATUS					 current
		DESCRIPTION			 " -- "
		::=  { mroEntry  5 }


	mroWrongHoTh		 OBJECT-TYPE
		SYNTAX					 Integer32( 0 .. 100 )
		MAX-ACCESS			 read-create
		STATUS					 current
		DESCRIPTION			 " -- "
		::=  { mroEntry  6 }


	mroPingPangHoTh		 OBJECT-TYPE
		SYNTAX					 Integer32( 0 .. 100 )
		MAX-ACCESS			 read-create
		STATUS					 current
		DESCRIPTION			 " -- "
		::=  { mroEntry  7 }


	mroTotalSucHoTh		 OBJECT-TYPE
		SYNTAX					 Integer32( 0 .. 100 )
		MAX-ACCESS			 read-create
		STATUS					 current
		DESCRIPTION			 " -- "
		::=  { mroEntry  8 }


	mroOffsetStep		 OBJECT-TYPE
		SYNTAX					 INTEGER{ offsetStepPoint5(0),offsetStep1(1),offsetStep1Point5(2),offsetStep2(3),offsetStep2Point5(4),offsetStep3(5)  }
		MAX-ACCESS			 read-create
		STATUS					 current
		DESCRIPTION			 " -- "
		::=  { mroEntry  9 }


	mroHysteresisStep		 OBJECT-TYPE
		SYNTAX					 INTEGER{ hysteresisStepPoint5(0),hysteresisStep1(1),hysteresisStep1Point5(2),hysteresisStep2(3),hysteresisStep2Point5(4),hysteresisStep3(5)  }
		MAX-ACCESS			 read-create
		STATUS					 current
		DESCRIPTION			 " -- "
		::=  { mroEntry  10 }


	mroStage		 OBJECT-TYPE
		SYNTAX					 INTEGER{ optimizeTrig(0),pmEvaluate(1)  }
		MAX-ACCESS			 read-create
		STATUS					 current
		DESCRIPTION			 " -- "
		::=  { mroEntry  11 }


	mroRsrpTh		 OBJECT-TYPE
		SYNTAX					 Integer32( 0 .. 97 )
		MAX-ACCESS			 read-create
		STATUS					 current
		DESCRIPTION			 " -- "
		::=  { mroEntry  12 }


	mroRsrqTh		 OBJECT-TYPE
		SYNTAX					 Integer32( 0 .. 34 )
		MAX-ACCESS			 read-create
		STATUS					 current
		DESCRIPTION			 " -- "
		::=  { mroEntry  13 }


	mroHoTh		 OBJECT-TYPE
		SYNTAX					 Integer32( 0 .. 10000 )
		MAX-ACCESS			 read-create
		STATUS					 current
		DESCRIPTION			 " -- "
		::=  { mroEntry  14 }


	mroRollBackTrigger		 OBJECT-TYPE
		SYNTAX					 INTEGER{ off(0),on(1)  }
		MAX-ACCESS			 read-write
		STATUS					 current
		DESCRIPTION			 " -- "
		::=  { mroEntry  15 }


	mroPingPangTimeTh		 OBJECT-TYPE
		SYNTAX					 Unsigned32( 0 .. 65535 )
		MAX-ACCESS			 read-create
		STATUS					 current
		DESCRIPTION			 " -- "
		::=  { mroEntry  16 }


	mroTotalPingPangTh		 OBJECT-TYPE
		SYNTAX					 Unsigned32( 0 .. 100 )
		MAX-ACCESS			 read-create
		STATUS					 current
		DESCRIPTION			 " -- "
		::=  { mroEntry  17 }


	mroPeriod		 OBJECT-TYPE
		SYNTAX					 Unsigned32( 1 .. 960 )
		MAX-ACCESS			 read-create
		STATUS					 current
		DESCRIPTION			 " -- "
		::=  { mroEntry  18 }


	mroTooEarlyHoNumTh		 OBJECT-TYPE
		SYNTAX					 Unsigned32( 0 .. 65535 )
		MAX-ACCESS			 read-create
		STATUS					 current
		DESCRIPTION			 " -- "
		::=  { mroEntry  19 }


	mroTooLateHoNumTh		 OBJECT-TYPE
		SYNTAX					 Unsigned32( 0 .. 65535 )
		MAX-ACCESS			 read-create
		STATUS					 current
		DESCRIPTION			 " -- "
		::=  { mroEntry  20 }


	mroWrongHoNumTh		 OBJECT-TYPE
		SYNTAX					 Unsigned32( 0 .. 65535 )
		MAX-ACCESS			 read-create
		STATUS					 current
		DESCRIPTION			 " -- "
		::=  { mroEntry  21 }


	mroPingPangHoNumTh		 OBJECT-TYPE
		SYNTAX					 Unsigned32( 0 .. 65535 )
		MAX-ACCESS			 read-create
		STATUS					 current
		DESCRIPTION			 " -- "
		::=  { mroEntry  22 }


	mroHoNumRatioRelation		 OBJECT-TYPE
		SYNTAX					 INTEGER{ and(0),or(1)  }
		MAX-ACCESS			 read-create
		STATUS					 current
		DESCRIPTION			 " -- "
		::=  { mroEntry  23 }


	mroEventRsrpStep		 OBJECT-TYPE
		SYNTAX					 INTEGER{ rsrpStep1(1),rsrpStep2(2),rsrpStep3(3),rsrpStep4(4),rsrpStep5(5)  }
		MAX-ACCESS			 read-create
		STATUS					 current
		DESCRIPTION			 " -- "
		::=  { mroEntry  24 }


	mroA2ThBaseHighTh		 OBJECT-TYPE
		SYNTAX					 Integer32( -140 .. -44 )
		MAX-ACCESS			 read-create
		STATUS					 current
		DESCRIPTION			 " -- "
		::=  { mroEntry  25 }


	mroA2ThBaseLowTh		 OBJECT-TYPE
		SYNTAX					 Integer32( -140 .. -44 )
		MAX-ACCESS			 read-create
		STATUS					 current
		DESCRIPTION			 " -- "
		::=  { mroEntry  26 }


	mroA3OffsetThBaseHighTh		 OBJECT-TYPE
		SYNTAX					 INTEGER{ a3OffsetMinus15(0),a3OffsetMinus14Point5(1),a3OffsetMinus14(2),a3OffsetMinus13Point5(3),a3OffsetMinus13(4),a3OffsetMinus12Point5(5),a3OffsetMinus12(6),a3OffsetMinus11Point5(7),a3OffsetMinus11(8),a3OffsetMinus10Point5(9),a3OffsetMinus10(10),a3OffsetMinus9Point5(11),a3OffsetMinus9(12),a3OffsetMinus8Point5(13),a3OffsetMinus8(14),a3OffsetMinus7Point5(15),a3OffsetMinus7(16),a3OffsetMinus6Point5(17),a3OffsetMinus6(18),a3OffsetMinus5Point5(19),a3OffsetMinus5(20),a3OffsetMinus4Point5(21),a3OffsetMinus4(22),a3OffsetMinus3Point5(23),a3OffsetMinus3(24),a3OffsetMinus2Point5(25),a3OffsetMinus2(26),a3OffsetMinus1Point5(27),a3OffsetMinus1(28),a3OffsetMinusPoint5(29),a3Offset0(30),a3OffsetPoint5(31),a3Offset1(32),a3Offset1Point5(33),a3Offset2(34),a3Offset2Point5(35),a3Offset3(36),a3Offset3Point5(37),a3Offset4(38),a3Offset4Point5(39),a3Offset5(40),a3Offset5Point5(41),a3Offset6(42),a3Offset6Point5(43),a3Offset7(44),a3Offset7Point5(45),a3Offset8(46),a3Offset8Point5(47),a3Offset9(48),a3Offset9Point5(49),a3Offset10(50),a3Offset10Point5(51),a3Offset11(52),a3Offset11Point5(53),a3Offset12(54),a3Offset12Point5(55),a3Offset13(56),a3Offset13Point5(57),a3Offset14(58),a3Offset14Point5(59),a3Offset15(60)  }
		MAX-ACCESS			 read-create
		STATUS					 current
		DESCRIPTION			 " -- "
		::=  { mroEntry  27 }


	mroA3OffsetThBaseLowTh		 OBJECT-TYPE
		SYNTAX					 INTEGER{ a3OffsetMinus15(0),a3OffsetMinus14Point5(1),a3OffsetMinus14(2),a3OffsetMinus13Point5(3),a3OffsetMinus13(4),a3OffsetMinus12Point5(5),a3OffsetMinus12(6),a3OffsetMinus11Point5(7),a3OffsetMinus11(8),a3OffsetMinus10Point5(9),a3OffsetMinus10(10),a3OffsetMinus9Point5(11),a3OffsetMinus9(12),a3OffsetMinus8Point5(13),a3OffsetMinus8(14),a3OffsetMinus7Point5(15),a3OffsetMinus7(16),a3OffsetMinus6Point5(17),a3OffsetMinus6(18),a3OffsetMinus5Point5(19),a3OffsetMinus5(20),a3OffsetMinus4Point5(21),a3OffsetMinus4(22),a3OffsetMinus3Point5(23),a3OffsetMinus3(24),a3OffsetMinus2Point5(25),a3OffsetMinus2(26),a3OffsetMinus1Point5(27),a3OffsetMinus1(28),a3OffsetMinusPoint5(29),a3Offset0(30),a3OffsetPoint5(31),a3Offset1(32),a3Offset1Point5(33),a3Offset2(34),a3Offset2Point5(35),a3Offset3(36),a3Offset3Point5(37),a3Offset4(38),a3Offset4Point5(39),a3Offset5(40),a3Offset5Point5(41),a3Offset6(42),a3Offset6Point5(43),a3Offset7(44),a3Offset7Point5(45),a3Offset8(46),a3Offset8Point5(47),a3Offset9(48),a3Offset9Point5(49),a3Offset10(50),a3Offset10Point5(51),a3Offset11(52),a3Offset11Point5(53),a3Offset12(54),a3Offset12Point5(55),a3Offset13(56),a3Offset13Point5(57),a3Offset14(58),a3Offset14Point5(59),a3Offset15(60)  }
		MAX-ACCESS			 read-create
		STATUS					 current
		DESCRIPTION			 " -- "
		::=  { mroEntry  28 }


	mroA3TTTThBaseHighTh		 OBJECT-TYPE
		SYNTAX					 INTEGER{ ms0(0),ms40(1),ms64(2),ms80(3),ms100(4),ms128(5),ms160(6),ms256(7),ms320(8),ms480(9),ms512(10),ms640(11),ms1024(12),ms1280(13),ms2560(14),ms5120(15)  }
		MAX-ACCESS			 read-create
		STATUS					 current
		DESCRIPTION			 " -- "
		::=  { mroEntry  29 }


	mroA3TTTThBaseLowTh		 OBJECT-TYPE
		SYNTAX					 INTEGER{ ms0(0),ms40(1),ms64(2),ms80(3),ms100(4),ms128(5),ms160(6),ms256(7),ms320(8),ms480(9),ms512(10),ms640(11),ms1024(12),ms1280(13),ms2560(14),ms5120(15)  }
		MAX-ACCESS			 read-create
		STATUS					 current
		DESCRIPTION			 " -- "
		::=  { mroEntry  30 }


	mroA3HysBaseHighTh		 OBJECT-TYPE
		SYNTAX					 INTEGER{ hysteresis0(0),hysteresisPoint5(1),hysteresis1(2),hysteresis1point5(3),hysteresis2(4),hysteresis2point5(5),hysteresis3(6),hysteresis3point5(7),hysteresis4(8),hysteresis4point5(9),hysteresis5(10),hysteresis5point5(11),hysteresis6(12),hysteresis6point5(13),hysteresis7(14),hysteresis7point5(15),hysteresis8(16),hysteresis8point5(17),hysteresis9(18),hysteresis9point5(19),hysteresis10(20),hysteresis10point5(21),hysteresis11(22),hysteresis11point5(23),hysteresis12(24),hysteresis12point5(25),hysteresis13(26),hysteresis13point5(27),hysteresis14(28),hysteresis14point5(29),hysteresis15(30)  }
		MAX-ACCESS			 read-create
		STATUS					 current
		DESCRIPTION			 " -- "
		::=  { mroEntry  31 }


	mroA3HysBaseLowTh		 OBJECT-TYPE
		SYNTAX					 INTEGER{ hysteresis0(0),hysteresisPoint5(1),hysteresis1(2),hysteresis1point5(3),hysteresis2(4),hysteresis2point5(5),hysteresis3(6),hysteresis3point5(7),hysteresis4(8),hysteresis4point5(9),hysteresis5(10),hysteresis5point5(11),hysteresis6(12),hysteresis6point5(13),hysteresis7(14),hysteresis7point5(15),hysteresis8(16),hysteresis8point5(17),hysteresis9(18),hysteresis9point5(19),hysteresis10(20),hysteresis10point5(21),hysteresis11(22),hysteresis11point5(23),hysteresis12(24),hysteresis12point5(25),hysteresis13(26),hysteresis13point5(27),hysteresis14(28),hysteresis14point5(29),hysteresis15(30)  }
		MAX-ACCESS			 read-create
		STATUS					 current
		DESCRIPTION			 " -- "
		::=  { mroEntry  32 }


	mroA4ThBaseHighTh		 OBJECT-TYPE
		SYNTAX					 Integer32( -140 .. -44 )
		MAX-ACCESS			 read-create
		STATUS					 current
		DESCRIPTION			 " -- "
		::=  { mroEntry  33 }


	mroA4ThBaseLowTh		 OBJECT-TYPE
		SYNTAX					 Integer32( -140 .. -44 )
		MAX-ACCESS			 read-create
		STATUS					 current
		DESCRIPTION			 " -- "
		::=  { mroEntry  34 }


	mroA5Th1BaseHighTh		 OBJECT-TYPE
		SYNTAX					 Integer32( -140 .. -44 )
		MAX-ACCESS			 read-create
		STATUS					 current
		DESCRIPTION			 " -- "
		::=  { mroEntry  35 }


	mroA5Th1BaseLowTh		 OBJECT-TYPE
		SYNTAX					 Integer32( -140 .. -44 )
		MAX-ACCESS			 read-create
		STATUS					 current
		DESCRIPTION			 " -- "
		::=  { mroEntry  36 }


	mroA5Th2BaseHighTh		 OBJECT-TYPE
		SYNTAX					 Integer32( -140 .. -44 )
		MAX-ACCESS			 read-create
		STATUS					 current
		DESCRIPTION			 " -- "
		::=  { mroEntry  37 }


	mroA5Th2BaseLowTh		 OBJECT-TYPE
		SYNTAX					 Integer32( -140 .. -44 )
		MAX-ACCESS			 read-create
		STATUS					 current
		DESCRIPTION			 " -- "
		::=  { mroEntry  38 }


	mroCellParaAdjRatioTh		 OBJECT-TYPE
		SYNTAX					 Integer32( 0 .. 100 )
		MAX-ACCESS			 read-create
		STATUS					 current
		DESCRIPTION			 " -- "
		::=  { mroEntry  39 }


	optionalFunction		 OBJECT IDENTIFIER
		::=  { cellAlgorithm  6 }


	opFuncTable		 OBJECT-TYPE
		SYNTAX					 SEQUENCE  OF	 OpFuncEntry
		MAX-ACCESS			 not-accessible
		STATUS					 current
		DESCRIPTION			 " -- "
		::=  { optionalFunction  1 }


	opFuncEntry		 OBJECT-TYPE
		SYNTAX					 OpFuncEntry
		MAX-ACCESS			 not-accessible
		STATUS					 current
		DESCRIPTION			 " -- "
		INDEX						{ opFuncLcId }
		::=  { opFuncTable  1 }


	OpFuncEntry		 ::=  SEQUENCE {
		opFuncLcId					Integer32,
		opFuncRowStatus					RowStatus,
		opFuncFeatureGroupFlag					INTEGER,
		opFuncRedirectionFlag					INTEGER,
		opFuncDrxFlag					INTEGER,
		opFuncCdma2000Flag					INTEGER,
		opFuncDrxDelayFlag					INTEGER,
		opFuncDrxDelayTimer					Unsigned32,
		opFuncRueJudgeFlag					INTEGER,
		opFuncDrxDelayFlagForConnect					INTEGER,
		opFuncDrxDelayTimerForConnect					Unsigned32
		}


	opFuncLcId		 OBJECT-TYPE
		SYNTAX					 Integer32( 0 .. 23 )
		MAX-ACCESS			 not-accessible
		STATUS					 current
		DESCRIPTION			 " -- "
		::=  { opFuncEntry  1 }


	opFuncRowStatus		 OBJECT-TYPE
		SYNTAX					 RowStatus
		MAX-ACCESS			 read-create
		STATUS					 current
		DESCRIPTION			 " -- "
		::=  { opFuncEntry  2 }


	opFuncFeatureGroupFlag		 OBJECT-TYPE
		SYNTAX					 INTEGER{ off(0),on(1)  }
		MAX-ACCESS			 read-create
		STATUS					 current
		DESCRIPTION			 " -- "
		::=  { opFuncEntry  4 }


	opFuncRedirectionFlag		 OBJECT-TYPE
		SYNTAX					 INTEGER{ off(0),on(1)  }
		MAX-ACCESS			 read-create
		STATUS					 current
		DESCRIPTION			 " -- "
		::=  { opFuncEntry  5 }


	opFuncDrxFlag		 OBJECT-TYPE
		SYNTAX					 INTEGER{ off(0),on(1)  }
		MAX-ACCESS			 read-create
		STATUS					 current
		DESCRIPTION			 " -- "
		::=  { opFuncEntry  6 }


	opFuncCdma2000Flag		 OBJECT-TYPE
		SYNTAX					 INTEGER{ off(0),on(1)  }
		MAX-ACCESS			 read-create
		STATUS					 current
		DESCRIPTION			 " -- "
		::=  { opFuncEntry  7 }


	opFuncDrxDelayFlag		 OBJECT-TYPE
		SYNTAX					 INTEGER{ off(0),on(1)  }
		MAX-ACCESS			 read-create
		STATUS					 current
		DESCRIPTION			 " -- "
		::=  { opFuncEntry  8 }


	opFuncDrxDelayTimer		 OBJECT-TYPE
		SYNTAX					 Unsigned32( 200 .. 65535 )
		MAX-ACCESS			 read-create
		STATUS					 current
		DESCRIPTION			 " -- "
		::=  { opFuncEntry  9 }


	opFuncRueJudgeFlag		 OBJECT-TYPE
		SYNTAX					 INTEGER{ off(0),on(1)  }
		MAX-ACCESS			 read-create
		STATUS					 current
		DESCRIPTION			 " -- "
		::=  { opFuncEntry  10 }


	opFuncDrxDelayFlagForConnect		 OBJECT-TYPE
		SYNTAX					 INTEGER{ off(0),on(1)  }
		MAX-ACCESS			 read-create
		STATUS					 current
		DESCRIPTION			 " -- "
		::=  { opFuncEntry  11 }


	opFuncDrxDelayTimerForConnect		 OBJECT-TYPE
		SYNTAX					 Unsigned32( 200 .. 65535 )
		MAX-ACCESS			 read-create
		STATUS					 current
		DESCRIPTION			 " -- "
		::=  { opFuncEntry  12 }


	hlTestSwitchTable		 OBJECT-TYPE
		SYNTAX					 SEQUENCE  OF	 HlTestSwitchEntry
		MAX-ACCESS			 not-accessible
		STATUS					 current
		DESCRIPTION			 " -- "
		::=  { optionalFunction  2 }


	hlTestSwitchEntry		 OBJECT-TYPE
		SYNTAX					 HlTestSwitchEntry
		MAX-ACCESS			 not-accessible
		STATUS					 current
		DESCRIPTION			 " -- "
		INDEX						{ hlTestSwitchLcId }
		::=  { hlTestSwitchTable  1 }


	HlTestSwitchEntry		 ::=  SEQUENCE {
		hlTestSwitchLcId					Integer32,
		hlTestSwitchRowStatus					RowStatus,
		hlTestSwitchIcicTestSwitch					INTEGER,
		hlTestSwitchUlStartPrbNoForEdgeUe					Integer32,
		hlTestSwitchDlStartPrbNoForEdgeUe					Integer32,
		hlTestSwitchUlPrbLenForEdgeUe					Integer32,
		hlTestSwitchDlPrbLenForEdgeUe					Integer32,
		hlTestSwitchSrsTestSwitch					INTEGER,
		hlTestSwitchSrsBandwidthCfg					INTEGER,
		hlTestSwitchSrsSubfrmCfg					INTEGER,
		hlTestSwitchSrsPeriodicity					INTEGER,
		hlTestSwitchSrsUpptsOneSymbol					INTEGER,
		hlTestSwitchPeriodMeasForRptStrongestCellCfg					INTEGER,
		hlTestSwitchApSrsPeriodicity					INTEGER,
		hlTestSwitchApSrsTestSwitch					INTEGER,
		hlTestSwitchTm9PrecodingSrsSwitch					INTEGER,
		hlTestSwitchSrsShortPeriodicity					INTEGER,
		hlTestSwitchUplinkMimoSwitch					INTEGER,
		hlTestSwitchVIPScheAlgorithmSwitch					INTEGER,
		hlTestSwitchLbLogProtectedSwitch					INTEGER,
		hlTestSwitchLbLogRecordType					INTEGER,
		hlTestSwitchDrxUeNumSwitch					INTEGER,
		hlTestSwitchDrxUeNumTh					Unsigned32,
		hlTestSwitchDlReceiveDataCore					INTEGER,
		hlTestSwitcErabTimeDelayRatio					Integer32,
		hlTestBadCoverageRejectQci1Setup					INTEGER,
		hlTestSwitchPdschPa					INTEGER,
		hlTestSwitchVipUePa					INTEGER,
		hlTestSwitchcellAdjCellPwrchgduration					Integer32,
		hlTestSwitchcellAdjCellReducePowerSwitch					INTEGER,
		hlTestSwitchcellAdjCellRsrpDifferTh					Integer32,
		hlTestSwitchcellAdjCellCheckStart					Integer32,
		hlTestSwitchcellAdjCellCheckNum					Integer32,
		hlTestSwitchcellUpIoTupOffsetSwitch					INTEGER,
		hlTestSwitchsourceCellPowerDelta					Integer32,
		hlTestSwitchAdjCellRecoverRsrpOffset					Integer32,
		hlTestSwitchVolteAppointFre					INTEGER,
		hlTestSwitchVolteCarrierFreq					Unsigned32,
		hlTestSwitchVolteAppointBand					INTEGER,
		hlTestBadCoverageHoDelaySwitch					INTEGER,
		hlTestSRVCCDelayTimer					Unsigned32,
		hlTestSwitchSCellRsrpThr					Integer32,
		hlTestSwitchAdjCellPowerReducedStep					Integer32,
		hlTestSwitchAdjCellPowerReducedNumThr					Integer32,
		hlTestSwitchTENDA1RSRP					Integer32,
		hlTestSwitchTENDA2RSRP					Integer32,
		hlTestSwitchA1RSRP					Integer32,
		hlTestSwitchA2RSRP					Integer32,
		hlTestSwitchVipDRXSwitch					INTEGER,
		hlTestSwitchCommonUserMRDelSwitch					INTEGER,
		hlTestSwitchUeLostTag					BITS,
		hlTestSwitchVolteUIProportion					Unsigned32,
		hlTestSwitchNormalUIProportion					Unsigned32,
		hlTestSwitchMeasOffset					Integer32,
		hlTestSwitchQciAppointFre					INTEGER,
		hlTestSwitchQciCarrierFreq					Unsigned32,
		hlTestSwitchQciAppointBand					INTEGER,
		hlTestSwitchcellUpIoTupOffsetUserType					BITS,
		hlTestSwitchQRxLevMinOffset					INTEGER,
		hlTestSwitchMrCfgPriSwitch					INTEGER,
		hlTestSwitch256QAMSwitch					INTEGER,
		hlTestSwitchcaDownlinkSwitchTLS					INTEGER,
		hlTestSwitchcaUplinkSwitchTLS					INTEGER,
		hlTestSwitchlmcMlbAlgorithmTagTLS					INTEGER,
		hlTestSwitchmroSwitchTLS					INTEGER
		}


	hlTestSwitchLcId		 OBJECT-TYPE
		SYNTAX					 Integer32( 0 .. 23 )
		MAX-ACCESS			 not-accessible
		STATUS					 current
		DESCRIPTION			 " -- "
		::=  { hlTestSwitchEntry  1 }


	hlTestSwitchRowStatus		 OBJECT-TYPE
		SYNTAX					 RowStatus
		MAX-ACCESS			 read-create
		STATUS					 current
		DESCRIPTION			 " -- "
		::=  { hlTestSwitchEntry  2 }


	hlTestSwitchIcicTestSwitch		 OBJECT-TYPE
		SYNTAX					 INTEGER{ close(0),open(1)  }
		MAX-ACCESS			 read-create
		STATUS					 current
		DESCRIPTION			 " -- "
		::=  { hlTestSwitchEntry  3 }


	hlTestSwitchUlStartPrbNoForEdgeUe		 OBJECT-TYPE
		SYNTAX					 Integer32( 0 .. 100 )
		MAX-ACCESS			 read-create
		STATUS					 current
		DESCRIPTION			 " -- "
		::=  { hlTestSwitchEntry  4 }


	hlTestSwitchDlStartPrbNoForEdgeUe		 OBJECT-TYPE
		SYNTAX					 Integer32( 0 .. 100 )
		MAX-ACCESS			 read-create
		STATUS					 current
		DESCRIPTION			 " -- "
		::=  { hlTestSwitchEntry  5 }


	hlTestSwitchUlPrbLenForEdgeUe		 OBJECT-TYPE
		SYNTAX					 Integer32( 0 .. 100 )
		MAX-ACCESS			 read-create
		STATUS					 current
		DESCRIPTION			 " -- "
		::=  { hlTestSwitchEntry  6 }


	hlTestSwitchDlPrbLenForEdgeUe		 OBJECT-TYPE
		SYNTAX					 Integer32( 0 .. 100 )
		MAX-ACCESS			 read-create
		STATUS					 current
		DESCRIPTION			 " -- "
		::=  { hlTestSwitchEntry  7 }


	hlTestSwitchSrsTestSwitch		 OBJECT-TYPE
		SYNTAX					 INTEGER{ close(0),open(1)  }
		MAX-ACCESS			 read-create
		STATUS					 current
		DESCRIPTION			 " -- "
		::=  { hlTestSwitchEntry  8 }


	hlTestSwitchSrsBandwidthCfg		 OBJECT-TYPE
		SYNTAX					 INTEGER{ bw0(0),bw1(1),bw2(2),bw3(3),bw4(4),bw5(5),bw6(6),bw7(7)  }
		MAX-ACCESS			 read-create
		STATUS					 current
		DESCRIPTION			 " -- "
		::=  { hlTestSwitchEntry  9 }


	hlTestSwitchSrsSubfrmCfg		 OBJECT-TYPE
		SYNTAX					 INTEGER{ sc0(0),sc1(1),sc2(2),sc3(3),sc4(4),sc5(5),sc6(6),sc7(7),sc8(8),sc9(9),sc10(10),sc11(11),sc12(12),sc13(13),sc14(14),sc15(15)  }
		MAX-ACCESS			 read-create
		STATUS					 current
		DESCRIPTION			 " -- "
		::=  { hlTestSwitchEntry  10 }


	hlTestSwitchSrsPeriodicity		 OBJECT-TYPE
		SYNTAX					 INTEGER{ ms2(0),ms5(1),ms10(2),ms20(3),ms40(4),ms80(5),ms160(6),ms320(7)  }
		MAX-ACCESS			 read-create
		STATUS					 current
		DESCRIPTION			 " -- "
		::=  { hlTestSwitchEntry  11 }


	hlTestSwitchSrsUpptsOneSymbol		 OBJECT-TYPE
		SYNTAX					 INTEGER{ close(0),open(1)  }
		MAX-ACCESS			 read-create
		STATUS					 current
		DESCRIPTION			 " -- "
		::=  { hlTestSwitchEntry  13 }


	hlTestSwitchPeriodMeasForRptStrongestCellCfg		 OBJECT-TYPE
		SYNTAX					 INTEGER{ close(0),open(1)  }
		MAX-ACCESS			 read-create
		STATUS					 current
		DESCRIPTION			 " -- "
		::=  { hlTestSwitchEntry  14 }


	hlTestSwitchApSrsPeriodicity		 OBJECT-TYPE
		SYNTAX					 INTEGER{ ms2(0),ms5(1),ms10(2)  }
		MAX-ACCESS			 read-create
		STATUS					 current
		DESCRIPTION			 " -- "
		::=  { hlTestSwitchEntry  17 }


	hlTestSwitchApSrsTestSwitch		 OBJECT-TYPE
		SYNTAX					 INTEGER{ close(0),open(1)  }
		MAX-ACCESS			 read-create
		STATUS					 current
		DESCRIPTION			 " -- "
		::=  { hlTestSwitchEntry  18 }


	hlTestSwitchTm9PrecodingSrsSwitch		 OBJECT-TYPE
		SYNTAX					 INTEGER{ off(0),on(1)  }
		MAX-ACCESS			 read-create
		STATUS					 current
		DESCRIPTION			 " -- "
		::=  { hlTestSwitchEntry  19 }


	hlTestSwitchSrsShortPeriodicity		 OBJECT-TYPE
		SYNTAX					 INTEGER{ ms2(0),ms5(1),ms10(2),ms20(3),ms40(4),ms80(5),ms160(6),ms320(7)  }
		MAX-ACCESS			 read-create
		STATUS					 current
		DESCRIPTION			 " -- "
		::=  { hlTestSwitchEntry  20 }


	hlTestSwitchUplinkMimoSwitch		 OBJECT-TYPE
		SYNTAX					 INTEGER{ close(0),open(1)  }
		MAX-ACCESS			 read-create
		STATUS					 current
		DESCRIPTION			 " -- "
		::=  { hlTestSwitchEntry  21 }


	hlTestSwitchVIPScheAlgorithmSwitch		 OBJECT-TYPE
		SYNTAX					 INTEGER{ close(0),absolutVIP(1),relativeVIP(2)  }
		MAX-ACCESS			 read-create
		STATUS					 current
		DESCRIPTION			 " -- "
		::=  { hlTestSwitchEntry  22 }


	hlTestSwitchLbLogProtectedSwitch		 OBJECT-TYPE
		SYNTAX					 INTEGER{ offlog(0),openlog(1)  }
		MAX-ACCESS			 read-create
		STATUS					 current
		DESCRIPTION			 " -- "
		::=  { hlTestSwitchEntry  26 }


	hlTestSwitchLbLogRecordType		 OBJECT-TYPE
		SYNTAX					 INTEGER{ once(0),recycle(1)  }
		MAX-ACCESS			 read-create
		STATUS					 current
		DESCRIPTION			 " -- "
		::=  { hlTestSwitchEntry  27 }


	hlTestSwitchDrxUeNumSwitch		 OBJECT-TYPE
		SYNTAX					 INTEGER{ off(0),on(1)  }
		MAX-ACCESS			 read-create
		STATUS					 current
		DESCRIPTION			 " -- "
		::=  { hlTestSwitchEntry  28 }


	hlTestSwitchDrxUeNumTh		 OBJECT-TYPE
		SYNTAX					 Unsigned32( 0 .. 1200 )
		MAX-ACCESS			 read-create
		STATUS					 current
		DESCRIPTION			 " -- "
		::=  { hlTestSwitchEntry  29 }


	hlTestSwitchDlReceiveDataCore		 OBJECT-TYPE
		SYNTAX					 INTEGER{ core2(0),core4(1)  }
		MAX-ACCESS			 read-create
		STATUS					 current
		DESCRIPTION			 " -- "
		::=  { hlTestSwitchEntry  30 }


	hlTestSwitcErabTimeDelayRatio		 OBJECT-TYPE
		SYNTAX					 Integer32( 1 .. 100 )
		MAX-ACCESS			 read-create
		STATUS					 current
		DESCRIPTION			 " -- "
		::=  { hlTestSwitchEntry  31 }


	hlTestBadCoverageRejectQci1Setup		 OBJECT-TYPE
		SYNTAX					 INTEGER{ off(0),on(1)  }
		MAX-ACCESS			 read-create
		STATUS					 current
		DESCRIPTION			 " -- "
		::=  { hlTestSwitchEntry  32 }


	hlTestSwitchPdschPa		 OBJECT-TYPE
		SYNTAX					 INTEGER{ n6dB(0),n4dot77dB(1),n3dB(2),n1dot77dB(3),p0dB(4),p1dB(5),p2dB(6),p3dB(7)  }
		MAX-ACCESS			 read-create
		STATUS					 current
		DESCRIPTION			 " -- "
		::=  { hlTestSwitchEntry  33 }


	hlTestSwitchVipUePa		 OBJECT-TYPE
		SYNTAX					 INTEGER{ n6dB(0),n4dot77dB(1),n3dB(2),n1dot77dB(3),p0dB(4),p1dB(5),p2dB(6),p3dB(7)  }
		MAX-ACCESS			 read-create
		STATUS					 current
		DESCRIPTION			 " -- "
		::=  { hlTestSwitchEntry  34 }


	hlTestSwitchcellAdjCellPwrchgduration		 OBJECT-TYPE
		SYNTAX					 Integer32( 1 .. 1200 )
		MAX-ACCESS			 read-create
		STATUS					 current
		DESCRIPTION			 " -- "
		::=  { hlTestSwitchEntry  37 }


	hlTestSwitchcellAdjCellReducePowerSwitch		 OBJECT-TYPE
		SYNTAX					 INTEGER{ off(0),on(1)  }
		MAX-ACCESS			 read-create
		STATUS					 current
		DESCRIPTION			 " -- "
		::=  { hlTestSwitchEntry  38 }


	hlTestSwitchcellAdjCellRsrpDifferTh		 OBJECT-TYPE
		SYNTAX					 Integer32( 0 .. 15 )
		MAX-ACCESS			 read-create
		STATUS					 current
		DESCRIPTION			 " -- "
		::=  { hlTestSwitchEntry  39 }


	hlTestSwitchcellAdjCellCheckStart		 OBJECT-TYPE
		SYNTAX					 Integer32( 0 .. 7 )
		MAX-ACCESS			 read-create
		STATUS					 current
		DESCRIPTION			 " -- "
		::=  { hlTestSwitchEntry  40 }


	hlTestSwitchcellAdjCellCheckNum		 OBJECT-TYPE
		SYNTAX					 Integer32( 1 .. 8 )
		MAX-ACCESS			 read-create
		STATUS					 current
		DESCRIPTION			 " -- "
		::=  { hlTestSwitchEntry  41 }


	hlTestSwitchcellUpIoTupOffsetSwitch		 OBJECT-TYPE
		SYNTAX					 INTEGER{ off(0),on(1)  }
		MAX-ACCESS			 read-create
		STATUS					 current
		DESCRIPTION			 " -- "
		::=  { hlTestSwitchEntry  44 }


	hlTestSwitchsourceCellPowerDelta		 OBJECT-TYPE
		SYNTAX					 Integer32( 0 .. 10 )
		MAX-ACCESS			 read-create
		STATUS					 current
		DESCRIPTION			 " -- "
		::=  { hlTestSwitchEntry  45 }


	hlTestSwitchAdjCellRecoverRsrpOffset		 OBJECT-TYPE
		SYNTAX					 Integer32( -30 .. 30 )
		MAX-ACCESS			 read-create
		STATUS					 current
		DESCRIPTION			 " -- "
		::=  { hlTestSwitchEntry  47 }


	hlTestSwitchVolteAppointFre		 OBJECT-TYPE
		SYNTAX					 INTEGER{ off(0),open(1)  }
		MAX-ACCESS			 read-create
		STATUS					 current
		DESCRIPTION			 " -- "
		::=  { hlTestSwitchEntry  48 }


	hlTestSwitchVolteCarrierFreq		 OBJECT-TYPE
		SYNTAX					 Unsigned32( 0 .. 65535 )
		MAX-ACCESS			 read-create
		STATUS					 current
		DESCRIPTION			 " -- "
		::=  { hlTestSwitchEntry  49 }


	hlTestSwitchVolteAppointBand		 OBJECT-TYPE
		SYNTAX					 INTEGER{ band1(1),band3(3),band32(32),band33(33),band34(34),band35(35),band36(36),band37(37),band38(38),band39(39),band40(40),band41(41),band61(61)  }
		MAX-ACCESS			 read-create
		STATUS					 current
		DESCRIPTION			 " -- "
		::=  { hlTestSwitchEntry  50 }


	hlTestBadCoverageHoDelaySwitch		 OBJECT-TYPE
		SYNTAX					 INTEGER{ off(0),on(1)  }
		MAX-ACCESS			 read-create
		STATUS					 current
		DESCRIPTION			 " -- "
		::=  { hlTestSwitchEntry  51 }


	hlTestSRVCCDelayTimer		 OBJECT-TYPE
		SYNTAX					 Unsigned32( 1 .. 10 )
		MAX-ACCESS			 read-create
		STATUS					 current
		DESCRIPTION			 " -- "
		::=  { hlTestSwitchEntry  52 }


	hlTestSwitchSCellRsrpThr		 OBJECT-TYPE
		SYNTAX					 Integer32( -120 .. -44 )
		MAX-ACCESS			 read-create
		STATUS					 current
		DESCRIPTION			 " -- "
		::=  { hlTestSwitchEntry  53 }


	hlTestSwitchAdjCellPowerReducedStep		 OBJECT-TYPE
		SYNTAX					 Integer32( 0 .. 9 )
		MAX-ACCESS			 read-create
		STATUS					 current
		DESCRIPTION			 " -- "
		::=  { hlTestSwitchEntry  54 }


	hlTestSwitchAdjCellPowerReducedNumThr		 OBJECT-TYPE
		SYNTAX					 Integer32( 0 .. 3 )
		MAX-ACCESS			 read-create
		STATUS					 current
		DESCRIPTION			 " -- "
		::=  { hlTestSwitchEntry  55 }


	hlTestSwitchTENDA1RSRP		 OBJECT-TYPE
		SYNTAX					 Integer32( -140 .. -44 )
		MAX-ACCESS			 read-create
		STATUS					 current
		DESCRIPTION			 " -- "
		::=  { hlTestSwitchEntry  56 }


	hlTestSwitchTENDA2RSRP		 OBJECT-TYPE
		SYNTAX					 Integer32( -140 .. -44 )
		MAX-ACCESS			 read-create
		STATUS					 current
		DESCRIPTION			 " -- "
		::=  { hlTestSwitchEntry  57 }


	hlTestSwitchA1RSRP		 OBJECT-TYPE
		SYNTAX					 Integer32( -140 .. -44 )
		MAX-ACCESS			 read-create
		STATUS					 current
		DESCRIPTION			 " -- "
		::=  { hlTestSwitchEntry  58 }


	hlTestSwitchA2RSRP		 OBJECT-TYPE
		SYNTAX					 Integer32( -140 .. -44 )
		MAX-ACCESS			 read-create
		STATUS					 current
		DESCRIPTION			 " -- "
		::=  { hlTestSwitchEntry  59 }


	hlTestSwitchVipDRXSwitch		 OBJECT-TYPE
		SYNTAX					 INTEGER{ off(0),on(1)  }
		MAX-ACCESS			 read-create
		STATUS					 current
		DESCRIPTION			 " -- "
		::=  { hlTestSwitchEntry  60 }


	hlTestSwitchCommonUserMRDelSwitch		 OBJECT-TYPE
		SYNTAX					 INTEGER{ off(0),on(1)  }
		MAX-ACCESS			 read-create
		STATUS					 current
		DESCRIPTION			 " -- "
		::=  { hlTestSwitchEntry  61 }


	hlTestSwitchUeLostTag		 OBJECT-TYPE
		SYNTAX					 BITS{ ui(0),rlc(1),ack(2),ta(3)  }
		MAX-ACCESS			 read-create
		STATUS					 current
		DESCRIPTION			 " -- "
		::=  { hlTestSwitchEntry  67 }


	hlTestSwitchVolteUIProportion		 OBJECT-TYPE
		SYNTAX					 Unsigned32( 0 .. 10 )
		MAX-ACCESS			 read-create
		STATUS					 current
		DESCRIPTION			 " -- "
		::=  { hlTestSwitchEntry  70 }


	hlTestSwitchNormalUIProportion		 OBJECT-TYPE
		SYNTAX					 Unsigned32( 0 .. 10 )
		MAX-ACCESS			 read-create
		STATUS					 current
		DESCRIPTION			 " -- "
		::=  { hlTestSwitchEntry  71 }


	hlTestSwitchMeasOffset		 OBJECT-TYPE
		SYNTAX					 Integer32( -30 .. 30 )
		MAX-ACCESS			 read-create
		STATUS					 current
		DESCRIPTION			 " -- "
		::=  { hlTestSwitchEntry  72 }


	hlTestSwitchQciAppointFre		 OBJECT-TYPE
		SYNTAX					 INTEGER{ off(0),open(1)  }
		MAX-ACCESS			 read-create
		STATUS					 current
		DESCRIPTION			 " -- "
		::=  { hlTestSwitchEntry  73 }


	hlTestSwitchQciCarrierFreq		 OBJECT-TYPE
		SYNTAX					 Unsigned32( 0 .. 65535 )
		MAX-ACCESS			 read-create
		STATUS					 current
		DESCRIPTION			 " -- "
		::=  { hlTestSwitchEntry  74 }


	hlTestSwitchQciAppointBand		 OBJECT-TYPE
		SYNTAX					 INTEGER{ band1(1),band3(3),band32(32),band33(33),band34(34),band35(35),band36(36),band37(37),band38(38),band39(39),band40(40),band41(41),band61(61)  }
		MAX-ACCESS			 read-create
		STATUS					 current
		DESCRIPTION			 " -- "
		::=  { hlTestSwitchEntry  75 }


	hlTestSwitchcellUpIoTupOffsetUserType		 OBJECT-TYPE
		SYNTAX					 BITS{ ul(0),dl(1),voice(2),video(3)  }
		MAX-ACCESS			 read-create
		STATUS					 current
		DESCRIPTION			 " -- "
		::=  { hlTestSwitchEntry  76 }


	hlTestSwitchQRxLevMinOffset		 OBJECT-TYPE
		SYNTAX					 INTEGER{ minusDbm30(0),minusDbm28(1),minusDbm26(2),minusDbm24(3),minusDbm22(4),minusDbm20(5),minusDbm18(6),minusDbm16(7),minusDbm14(8),minusDbm12(9),minusDbm10(10),minusDbm8(11),minusDbm6(12),minusDbm4(13),minusDbm2(14),dbm0(15),dbm2(16),dbm4(17),dbm6(18),dbm8(19),dbm10(20),dbm12(21),dbm14(22),dbm16(23),dbm18(24),dbm20(25),dbm22(26),dbm24(27),dbm26(28),dbm28(29),dbm30(30)  }
		MAX-ACCESS			 read-create
		STATUS					 current
		DESCRIPTION			 " -- "
		::=  { hlTestSwitchEntry  79 }


	hlTestSwitchMrCfgPriSwitch		 OBJECT-TYPE
		SYNTAX					 INTEGER{ off(0),on(1)  }
		MAX-ACCESS			 read-create
		STATUS					 current
		DESCRIPTION			 " -- "
		::=  { hlTestSwitchEntry  80 }


	hlTestSwitch256QAMSwitch		 OBJECT-TYPE
		SYNTAX					 INTEGER{ off(0),on(1)  }
		MAX-ACCESS			 read-create
		STATUS					 current
		DESCRIPTION			 " -- "
		::=  { hlTestSwitchEntry  81 }


	hlTestSwitchcaDownlinkSwitchTLS		 OBJECT-TYPE
		SYNTAX					 INTEGER{ off(0),on(1)  }
		MAX-ACCESS			 read-create
		STATUS					 current
		DESCRIPTION			 " -- "
		::=  { hlTestSwitchEntry  84 }


	hlTestSwitchcaUplinkSwitchTLS		 OBJECT-TYPE
		SYNTAX					 INTEGER{ off(0),on(1)  }
		MAX-ACCESS			 read-create
		STATUS					 current
		DESCRIPTION			 " -- "
		::=  { hlTestSwitchEntry  85 }


	hlTestSwitchlmcMlbAlgorithmTagTLS		 OBJECT-TYPE
		SYNTAX					 INTEGER{ off(0),on(1)  }
		MAX-ACCESS			 read-create
		STATUS					 current
		DESCRIPTION			 " -- "
		::=  { hlTestSwitchEntry  86 }


	hlTestSwitchmroSwitchTLS		 OBJECT-TYPE
		SYNTAX					 INTEGER{ off(0),on(1)  }
		MAX-ACCESS			 read-create
		STATUS					 current
		DESCRIPTION			 " -- "
		::=  { hlTestSwitchEntry  87 }


	schedule		 OBJECT IDENTIFIER
		::=  { cellAlgorithm  7 }


	macAlgorithmNode		 OBJECT IDENTIFIER
		::=  { schedule  1 }


	macUpAlgBaseParaTable		 OBJECT-TYPE
		SYNTAX					 SEQUENCE  OF	 MacUpAlgBaseParaEntry
		MAX-ACCESS			 not-accessible
		STATUS					 current
		DESCRIPTION			 " -- "
		::=  { macAlgorithmNode  1 }


	macUpAlgBaseParaEntry		 OBJECT-TYPE
		SYNTAX					 MacUpAlgBaseParaEntry
		MAX-ACCESS			 not-accessible
		STATUS					 current
		DESCRIPTION			 " -- "
		INDEX						{ macUpAlgorithmLcId }
		::=  { macUpAlgBaseParaTable  1 }


	MacUpAlgBaseParaEntry		 ::=  SEQUENCE {
		macUpAlgorithmLcId					Integer32,
		macUpAlgorithmRowStatus					RowStatus,
		macUpAlgorithmType					INTEGER,
		macUpAlgorithmDeltaCqiMax					Integer32,
		macUpAlgorithmUlT					Integer32,
		macUpAlgorithmUlPfScaleRate					Unsigned32,
		macUpAlgorithmUlPfScaleMcs					Unsigned32,
		macUpAlgorithmCqiModifyP					Unsigned32,
		macUpAlgorithmCqiModifyVaddMax					Integer32,
		macUpAlgorithmCqiModifyVaddMin					Integer32,
		macUpAlgorithmCqiModifySnrDefaultDec					Integer32,
		macUpAlgorithmCqiFirstBler					Integer32,
		macUpAlgorithmUlAntSelectThresSinrHigh					Integer32,
		macUpAlgorithmUlAntSelectThresSinrMedium					Integer32,
		macUpAlgorithmUlAntSelectThresSinrLow					Integer32,
		macUpAlgorithmFilterFactorForPuschSINR					Integer32,
		macUpAlgorithmIoTup					Integer32,
		macUpAlgorithmRecvPowerMaxPerPrb					Integer32,
		macUpAlgorithm16QAMPUSCHTargetSinrUpLimit					Integer32,
		macUpAlgorithmTTIbndlngSwtch					INTEGER,
		macUpAlgorithmMCSStsfyCndtnNm					Unsigned32,
		macUpAlgorithmTTIbndlngMnPrbNm					Unsigned32,
		macUpAlgorithmMCSThrshldfrEnblTTIbndlng					Unsigned32,
		macUpAlgorithmMCSThrshldfrDsblTTIbndlng					Unsigned32,
		macUpAlgorithmTTIbndlngSnrAdd					Unsigned32,
		macUpAlgorithmRiSwitch					INTEGER,
		macUpAlgorithmPmiSwitch					Integer32,
		macUpAlgorithmPucchRsrpHighThr					Integer32,
		macUpAlgorithmPucchRsrpLowThr					Integer32,
		macUpAlgorithmMcsBackforSimuPuxch					Unsigned32,
		macUpAlgorithmMcsThrforSimuPuxch					Unsigned32,
		macUpAlgorithmUlQCI1FirstBler					Unsigned32,
		macUpAlgorithmUlQCI2FirstBler					Unsigned32,
		macUpAlgorithmTargetMcs					Unsigned32,
		macUpAlgorithmMcsDiff					Unsigned32,
		macUpAlgorithmRandomLimitScale					Unsigned32,
		macUpAlgorithmRandomPrbStartScale					Unsigned32,
		macUpAlgorithmQci6NewPfScale					Unsigned32,
		macUpAlgorithmQci7NewPfScale					Unsigned32,
		macUpAlgorithmQci8NewPfScale					Unsigned32,
		macUpAlgorithmQci9NewPfScale					Unsigned32,
		macUpAlgorithmPuschInitSinrTarget					Integer32,
		macUpAlgorithmUlCqiModifyStepDelta					Integer32,
		macUpAlgorithmUlCqiModifyCrcHalfSfnDiff					Integer32,
		macUpAlgorithmSRSRxPowThr					Integer32,
		macUpAlgorithmUlAntSelectNumProtect					INTEGER,
		macUplinkHighSpeedNewPfScale					Unsigned32,
		macUplinkLowSpeedNewPfScale					Unsigned32,
		macUpAlgorithmIoTupMax					Integer32,
		macUpAlgorithmIoTupMin					Integer32,
		macUpAlgorithmRecvPowerMaxPerPrbNei					Integer32,
		macUpAlgorithmPlThrMax					Integer32,
		macUpAlgorithmPlThrMid					Integer32,
		macUpAlgorithmSrsPowerTimer					Integer32,
		macUpAlgorithmSrsPowerP					Integer32,
		macUpAlgorithmSrsPowerSinrThLower					Integer32,
		macUpAlgorithmSrsPowerSinrThUpper					Integer32,
		macUpAlgorithmSrsPowerSinrThTarget					Integer32,
		macUpAlgorithmSrsPowerSwitch					INTEGER,
		macUpAlgorithmSrsTaP					Integer32,
		macUpAlgorithmSrsTaSwitch					INTEGER,
		macUpAlgorithmPRBSwitch					INTEGER,
		macUpAlgorithm64QAMPUSCHTargetSinrUpLimit					Integer32,
		macUpAlgorithmSrsWideBandSinrFactor					Integer32,
		macUpAlgorithmIoTupOffset					Integer32,
		macUpAlgorithmRSSIMax					Integer32,
		macUpAlgorithmSINRMax					Integer32,
		macUpAlgorithmMuMiMoPairChannelCorr					Integer32,
		macUpAlgorithmUlEdgeUserMcsTh					Integer32,
		macUpAlgorithmVolteMaxSchMcsTag					INTEGER,
		macUpAlgorithmVolteMaxSchMcs					Unsigned32,
		macUpAlgorithmVolteFixCce8Tag					INTEGER,
		macUpAlgorithmVoltePuschTargetSinrShift					Unsigned32,
		macUpAlgorithmCqiMaxModifyFlag					INTEGER,
		macUpAlgorithmMCSHighLevelOptFlag					INTEGER,
		macUpAlgorithmMCSN64QAMDiff					Integer32,
		macUpAlgorithmMCS64QAMDiff					Integer32,
		macUpAlgorithmNoPhrAdaptOptFlag					INTEGER,
		macUpAlgorithmUeNumThreForPrbLimit					Integer32,
		macUpAlgorithmPrbLimitMcsThre1					Integer32,
		macUpAlgorithmPrbLimitMcsThre2					Integer32,
		macUpAlgorithmNearPointUePrbNum					Integer32,
		macUpAlgorithmMidPointUePrbNum					Integer32,
		macUpAlgorithmFarPointUePrbNum					Integer32,
		macUpAlgorithmVolteUeMuMimoSwitch					INTEGER
		}


	macUpAlgorithmLcId		 OBJECT-TYPE
		SYNTAX					 Integer32( 0 .. 23 )
		MAX-ACCESS			 not-accessible
		STATUS					 current
		DESCRIPTION			 " -- "
		::=  { macUpAlgBaseParaEntry  1 }


	macUpAlgorithmRowStatus		 OBJECT-TYPE
		SYNTAX					 RowStatus
		MAX-ACCESS			 read-create
		STATUS					 current
		DESCRIPTION			 " -- "
		::=  { macUpAlgBaseParaEntry  2 }


	macUpAlgorithmType		 OBJECT-TYPE
		SYNTAX					 INTEGER{ rr(0),maxci(1),pf(2),irr(3),newpf(4)  }
		MAX-ACCESS			 read-create
		STATUS					 current
		DESCRIPTION			 " -- "
		::=  { macUpAlgBaseParaEntry  3 }


	macUpAlgorithmDeltaCqiMax		 OBJECT-TYPE
		SYNTAX					 Integer32( 0 .. 28 )
		MAX-ACCESS			 read-create
		STATUS					 current
		DESCRIPTION			 " -- "
		::=  { macUpAlgBaseParaEntry  4 }


	macUpAlgorithmUlT		 OBJECT-TYPE
		SYNTAX					 Integer32( 0 .. 65535 )
		MAX-ACCESS			 read-create
		STATUS					 current
		DESCRIPTION			 " -- "
		::=  { macUpAlgBaseParaEntry  6 }


	macUpAlgorithmUlPfScaleRate		 OBJECT-TYPE
		SYNTAX					 Unsigned32( 0 .. 4294967295 )
		MAX-ACCESS			 read-create
		STATUS					 current
		DESCRIPTION			 " -- "
		::=  { macUpAlgBaseParaEntry  7 }


	macUpAlgorithmUlPfScaleMcs		 OBJECT-TYPE
		SYNTAX					 Unsigned32( 0 .. 4294967295 )
		MAX-ACCESS			 read-create
		STATUS					 current
		DESCRIPTION			 " -- "
		::=  { macUpAlgBaseParaEntry  8 }


	macUpAlgorithmCqiModifyP		 OBJECT-TYPE
		SYNTAX					 Unsigned32( 0 .. 100 )
		MAX-ACCESS			 read-create
		STATUS					 current
		DESCRIPTION			 " -- "
		::=  { macUpAlgBaseParaEntry  11 }


	macUpAlgorithmCqiModifyVaddMax		 OBJECT-TYPE
		SYNTAX					 Integer32( -1000 .. 1000 )
		MAX-ACCESS			 read-create
		STATUS					 current
		DESCRIPTION			 " -- "
		::=  { macUpAlgBaseParaEntry  12 }


	macUpAlgorithmCqiModifyVaddMin		 OBJECT-TYPE
		SYNTAX					 Integer32( -1000 .. 1000 )
		MAX-ACCESS			 read-create
		STATUS					 current
		DESCRIPTION			 " -- "
		::=  { macUpAlgBaseParaEntry  13 }


	macUpAlgorithmCqiModifySnrDefaultDec		 OBJECT-TYPE
		SYNTAX					 Integer32( -15 .. 15 )
		MAX-ACCESS			 read-create
		STATUS					 current
		DESCRIPTION			 " -- "
		::=  { macUpAlgBaseParaEntry  14 }


	macUpAlgorithmCqiFirstBler		 OBJECT-TYPE
		SYNTAX					 Integer32( 0 .. 100 )
		MAX-ACCESS			 read-create
		STATUS					 current
		DESCRIPTION			 " -- "
		::=  { macUpAlgBaseParaEntry  15 }


	macUpAlgorithmUlAntSelectThresSinrHigh		 OBJECT-TYPE
		SYNTAX					 Integer32( 0 .. 120 )
		MAX-ACCESS			 read-create
		STATUS					 current
		DESCRIPTION			 " -- "
		::=  { macUpAlgBaseParaEntry  19 }


	macUpAlgorithmUlAntSelectThresSinrMedium		 OBJECT-TYPE
		SYNTAX					 Integer32( 0 .. 120 )
		MAX-ACCESS			 read-create
		STATUS					 current
		DESCRIPTION			 " -- "
		::=  { macUpAlgBaseParaEntry  20 }


	macUpAlgorithmUlAntSelectThresSinrLow		 OBJECT-TYPE
		SYNTAX					 Integer32( 0 .. 120 )
		MAX-ACCESS			 read-create
		STATUS					 current
		DESCRIPTION			 " -- "
		::=  { macUpAlgBaseParaEntry  21 }


	macUpAlgorithmFilterFactorForPuschSINR		 OBJECT-TYPE
		SYNTAX					 Integer32( 0 .. 100 )
		MAX-ACCESS			 read-create
		STATUS					 current
		DESCRIPTION			 " -- "
		::=  { macUpAlgBaseParaEntry  22 }


	macUpAlgorithmIoTup		 OBJECT-TYPE
		SYNTAX					 Integer32( -20 .. 50 )
		MAX-ACCESS			 read-create
		STATUS					 current
		DESCRIPTION			 " -- "
		::=  { macUpAlgBaseParaEntry  23 }


	macUpAlgorithmRecvPowerMaxPerPrb		 OBJECT-TYPE
		SYNTAX					 Integer32( -100 .. -50 )
		MAX-ACCESS			 read-create
		STATUS					 current
		DESCRIPTION			 " -- "
		::=  { macUpAlgBaseParaEntry  24 }


	macUpAlgorithm16QAMPUSCHTargetSinrUpLimit		 OBJECT-TYPE
		SYNTAX					 Integer32( 1 .. 100 )
		MAX-ACCESS			 read-create
		STATUS					 current
		DESCRIPTION			 " -- "
		::=  { macUpAlgBaseParaEntry  25 }


	macUpAlgorithmTTIbndlngSwtch		 OBJECT-TYPE
		SYNTAX					 INTEGER{ off(0),on(1)  }
		MAX-ACCESS			 read-create
		STATUS					 current
		DESCRIPTION			 " -- "
		::=  { macUpAlgBaseParaEntry  26 }


	macUpAlgorithmMCSStsfyCndtnNm		 OBJECT-TYPE
		SYNTAX					 Unsigned32( 1 .. 20 )
		MAX-ACCESS			 read-create
		STATUS					 current
		DESCRIPTION			 " -- "
		::=  { macUpAlgBaseParaEntry  27 }


	macUpAlgorithmTTIbndlngMnPrbNm		 OBJECT-TYPE
		SYNTAX					 Unsigned32( 1 .. 3 )
		MAX-ACCESS			 read-create
		STATUS					 current
		DESCRIPTION			 " -- "
		::=  { macUpAlgBaseParaEntry  28 }


	macUpAlgorithmMCSThrshldfrEnblTTIbndlng		 OBJECT-TYPE
		SYNTAX					 Unsigned32( 0 .. 28 )
		MAX-ACCESS			 read-create
		STATUS					 current
		DESCRIPTION			 " -- "
		::=  { macUpAlgBaseParaEntry  29 }


	macUpAlgorithmMCSThrshldfrDsblTTIbndlng		 OBJECT-TYPE
		SYNTAX					 Unsigned32( 0 .. 28 )
		MAX-ACCESS			 read-create
		STATUS					 current
		DESCRIPTION			 " -- "
		::=  { macUpAlgBaseParaEntry  30 }


	macUpAlgorithmTTIbndlngSnrAdd		 OBJECT-TYPE
		SYNTAX					 Unsigned32( 0 .. 15 )
		MAX-ACCESS			 read-create
		STATUS					 current
		DESCRIPTION			 " -- "
		::=  { macUpAlgBaseParaEntry  31 }


	macUpAlgorithmRiSwitch		 OBJECT-TYPE
		SYNTAX					 INTEGER{ adaptive(0),rank1(1),rank2(2)  }
		MAX-ACCESS			 read-create
		STATUS					 current
		DESCRIPTION			 " -- "
		::=  { macUpAlgBaseParaEntry  32 }


	macUpAlgorithmPmiSwitch		 OBJECT-TYPE
		SYNTAX					 Integer32( 0 .. 23|-1 )
		MAX-ACCESS			 read-create
		STATUS					 current
		DESCRIPTION			 " -- "
		::=  { macUpAlgBaseParaEntry  33 }


	macUpAlgorithmPucchRsrpHighThr		 OBJECT-TYPE
		SYNTAX					 Integer32( -120 .. -60 )
		MAX-ACCESS			 read-create
		STATUS					 current
		DESCRIPTION			 " -- "
		::=  { macUpAlgBaseParaEntry  34 }


	macUpAlgorithmPucchRsrpLowThr		 OBJECT-TYPE
		SYNTAX					 Integer32( -130 .. -100 )
		MAX-ACCESS			 read-create
		STATUS					 current
		DESCRIPTION			 " -- "
		::=  { macUpAlgBaseParaEntry  35 }


	macUpAlgorithmMcsBackforSimuPuxch		 OBJECT-TYPE
		SYNTAX					 Unsigned32( 0 .. 10 )
		MAX-ACCESS			 read-create
		STATUS					 current
		DESCRIPTION			 " -- "
		::=  { macUpAlgBaseParaEntry  36 }


	macUpAlgorithmMcsThrforSimuPuxch		 OBJECT-TYPE
		SYNTAX					 Unsigned32( 0 .. 24 )
		MAX-ACCESS			 read-create
		STATUS					 current
		DESCRIPTION			 " -- "
		::=  { macUpAlgBaseParaEntry  37 }


	macUpAlgorithmUlQCI1FirstBler		 OBJECT-TYPE
		SYNTAX					 Unsigned32( 0 .. 100 )
		MAX-ACCESS			 read-create
		STATUS					 current
		DESCRIPTION			 " -- "
		::=  { macUpAlgBaseParaEntry  38 }


	macUpAlgorithmUlQCI2FirstBler		 OBJECT-TYPE
		SYNTAX					 Unsigned32( 0 .. 100 )
		MAX-ACCESS			 read-create
		STATUS					 current
		DESCRIPTION			 " -- "
		::=  { macUpAlgBaseParaEntry  39 }


	macUpAlgorithmTargetMcs		 OBJECT-TYPE
		SYNTAX					 Unsigned32( 0 .. 28 )
		MAX-ACCESS			 read-create
		STATUS					 current
		DESCRIPTION			 " -- "
		::=  { macUpAlgBaseParaEntry  40 }


	macUpAlgorithmMcsDiff		 OBJECT-TYPE
		SYNTAX					 Unsigned32( 0 .. 5 )
		MAX-ACCESS			 read-create
		STATUS					 current
		DESCRIPTION			 " -- "
		::=  { macUpAlgBaseParaEntry  41 }


	macUpAlgorithmRandomLimitScale		 OBJECT-TYPE
		SYNTAX					 Unsigned32( 1 .. 100 )
		MAX-ACCESS			 read-create
		STATUS					 current
		DESCRIPTION			 " -- "
		::=  { macUpAlgBaseParaEntry  42 }


	macUpAlgorithmRandomPrbStartScale		 OBJECT-TYPE
		SYNTAX					 Unsigned32( 1 .. 100 )
		MAX-ACCESS			 read-create
		STATUS					 current
		DESCRIPTION			 " -- "
		::=  { macUpAlgBaseParaEntry  43 }


	macUpAlgorithmQci6NewPfScale		 OBJECT-TYPE
		SYNTAX					 Unsigned32( 1 .. 100 )
		MAX-ACCESS			 read-create
		STATUS					 current
		DESCRIPTION			 " -- "
		::=  { macUpAlgBaseParaEntry  44 }


	macUpAlgorithmQci7NewPfScale		 OBJECT-TYPE
		SYNTAX					 Unsigned32( 1 .. 100 )
		MAX-ACCESS			 read-create
		STATUS					 current
		DESCRIPTION			 " -- "
		::=  { macUpAlgBaseParaEntry  45 }


	macUpAlgorithmQci8NewPfScale		 OBJECT-TYPE
		SYNTAX					 Unsigned32( 1 .. 100 )
		MAX-ACCESS			 read-create
		STATUS					 current
		DESCRIPTION			 " -- "
		::=  { macUpAlgBaseParaEntry  46 }


	macUpAlgorithmQci9NewPfScale		 OBJECT-TYPE
		SYNTAX					 Unsigned32( 1 .. 100 )
		MAX-ACCESS			 read-create
		STATUS					 current
		DESCRIPTION			 " -- "
		::=  { macUpAlgBaseParaEntry  47 }


	macUpAlgorithmPuschInitSinrTarget		 OBJECT-TYPE
		SYNTAX					 Integer32( -10 .. 10 )
		MAX-ACCESS			 read-create
		STATUS					 current
		DESCRIPTION			 " -- "
		::=  { macUpAlgBaseParaEntry  48 }


	macUpAlgorithmUlCqiModifyStepDelta		 OBJECT-TYPE
		SYNTAX					 Integer32( 1 .. 20 )
		MAX-ACCESS			 read-create
		STATUS					 current
		DESCRIPTION			 " -- "
		::=  { macUpAlgBaseParaEntry  51 }


	macUpAlgorithmUlCqiModifyCrcHalfSfnDiff		 OBJECT-TYPE
		SYNTAX					 Integer32( 0 .. 20 )
		MAX-ACCESS			 read-create
		STATUS					 current
		DESCRIPTION			 " -- "
		::=  { macUpAlgBaseParaEntry  52 }


	macUpAlgorithmSRSRxPowThr		 OBJECT-TYPE
		SYNTAX					 Integer32( 1 .. 30 )
		MAX-ACCESS			 read-create
		STATUS					 current
		DESCRIPTION			 " -- "
		::=  { macUpAlgBaseParaEntry  53 }


	macUpAlgorithmUlAntSelectNumProtect		 OBJECT-TYPE
		SYNTAX					 INTEGER{ num1(0),num2(1),num3(2),num4(3),num5(4),num6(5),num7(6),num8(7)  }
		MAX-ACCESS			 read-create
		STATUS					 current
		DESCRIPTION			 " -- "
		::=  { macUpAlgBaseParaEntry  54 }


	macUplinkHighSpeedNewPfScale		 OBJECT-TYPE
		SYNTAX					 Unsigned32( 1 .. 100 )
		MAX-ACCESS			 read-create
		STATUS					 current
		DESCRIPTION			 " -- "
		::=  { macUpAlgBaseParaEntry  55 }


	macUplinkLowSpeedNewPfScale		 OBJECT-TYPE
		SYNTAX					 Unsigned32( 1 .. 100 )
		MAX-ACCESS			 read-create
		STATUS					 current
		DESCRIPTION			 " -- "
		::=  { macUpAlgBaseParaEntry  56 }


	macUpAlgorithmIoTupMax		 OBJECT-TYPE
		SYNTAX					 Integer32( -20 .. 50 )
		MAX-ACCESS			 read-create
		STATUS					 current
		DESCRIPTION			 " -- "
		::=  { macUpAlgBaseParaEntry  57 }


	macUpAlgorithmIoTupMin		 OBJECT-TYPE
		SYNTAX					 Integer32( -20 .. 50 )
		MAX-ACCESS			 read-create
		STATUS					 current
		DESCRIPTION			 " -- "
		::=  { macUpAlgBaseParaEntry  58 }


	macUpAlgorithmRecvPowerMaxPerPrbNei		 OBJECT-TYPE
		SYNTAX					 Integer32( -120 .. -60 )
		MAX-ACCESS			 read-create
		STATUS					 current
		DESCRIPTION			 " -- "
		::=  { macUpAlgBaseParaEntry  59 }


	macUpAlgorithmPlThrMax		 OBJECT-TYPE
		SYNTAX					 Integer32( 60 .. 140 )
		MAX-ACCESS			 read-create
		STATUS					 current
		DESCRIPTION			 " -- "
		::=  { macUpAlgBaseParaEntry  60 }


	macUpAlgorithmPlThrMid		 OBJECT-TYPE
		SYNTAX					 Integer32( 60 .. 140 )
		MAX-ACCESS			 read-create
		STATUS					 current
		DESCRIPTION			 " -- "
		::=  { macUpAlgBaseParaEntry  61 }


	macUpAlgorithmSrsPowerTimer		 OBJECT-TYPE
		SYNTAX					 Integer32( 1 .. 10 )
		MAX-ACCESS			 read-create
		STATUS					 current
		DESCRIPTION			 " -- "
		::=  { macUpAlgBaseParaEntry  62 }


	macUpAlgorithmSrsPowerP		 OBJECT-TYPE
		SYNTAX					 Integer32( 1 .. 100 )
		MAX-ACCESS			 read-create
		STATUS					 current
		DESCRIPTION			 " -- "
		::=  { macUpAlgBaseParaEntry  63 }


	macUpAlgorithmSrsPowerSinrThLower		 OBJECT-TYPE
		SYNTAX					 Integer32( -5 .. 30 )
		MAX-ACCESS			 read-create
		STATUS					 current
		DESCRIPTION			 " -- "
		::=  { macUpAlgBaseParaEntry  64 }


	macUpAlgorithmSrsPowerSinrThUpper		 OBJECT-TYPE
		SYNTAX					 Integer32( -5 .. 30 )
		MAX-ACCESS			 read-create
		STATUS					 current
		DESCRIPTION			 " -- "
		::=  { macUpAlgBaseParaEntry  65 }


	macUpAlgorithmSrsPowerSinrThTarget		 OBJECT-TYPE
		SYNTAX					 Integer32( -5 .. 30 )
		MAX-ACCESS			 read-create
		STATUS					 current
		DESCRIPTION			 " -- "
		::=  { macUpAlgBaseParaEntry  66 }


	macUpAlgorithmSrsPowerSwitch		 OBJECT-TYPE
		SYNTAX					 INTEGER{ off(0),on(1)  }
		MAX-ACCESS			 read-create
		STATUS					 current
		DESCRIPTION			 " -- "
		::=  { macUpAlgBaseParaEntry  67 }


	macUpAlgorithmSrsTaP		 OBJECT-TYPE
		SYNTAX					 Integer32( 1 .. 100 )
		MAX-ACCESS			 read-create
		STATUS					 current
		DESCRIPTION			 " -- "
		::=  { macUpAlgBaseParaEntry  68 }


	macUpAlgorithmSrsTaSwitch		 OBJECT-TYPE
		SYNTAX					 INTEGER{ off(0),on(1)  }
		MAX-ACCESS			 read-create
		STATUS					 current
		DESCRIPTION			 " -- "
		::=  { macUpAlgBaseParaEntry  69 }


	macUpAlgorithmPRBSwitch		 OBJECT-TYPE
		SYNTAX					 INTEGER{ off(0),on(1)  }
		MAX-ACCESS			 read-create
		STATUS					 current
		DESCRIPTION			 " -- "
		::=  { macUpAlgBaseParaEntry  70 }


	macUpAlgorithm64QAMPUSCHTargetSinrUpLimit		 OBJECT-TYPE
		SYNTAX					 Integer32( 1 .. 100 )
		MAX-ACCESS			 read-create
		STATUS					 current
		DESCRIPTION			 " -- "
		::=  { macUpAlgBaseParaEntry  71 }


	macUpAlgorithmSrsWideBandSinrFactor		 OBJECT-TYPE
		SYNTAX					 Integer32( 0 .. 100 )
		MAX-ACCESS			 read-create
		STATUS					 current
		DESCRIPTION			 " -- "
		::=  { macUpAlgBaseParaEntry  72 }


	macUpAlgorithmIoTupOffset		 OBJECT-TYPE
		SYNTAX					 Integer32( -6 .. 20 )
		MAX-ACCESS			 read-create
		STATUS					 current
		DESCRIPTION			 " -- "
		::=  { macUpAlgBaseParaEntry  73 }


	macUpAlgorithmRSSIMax		 OBJECT-TYPE
		SYNTAX					 Integer32( -100 .. -30 )
		MAX-ACCESS			 read-create
		STATUS					 current
		DESCRIPTION			 " -- "
		::=  { macUpAlgBaseParaEntry  74 }


	macUpAlgorithmSINRMax		 OBJECT-TYPE
		SYNTAX					 Integer32( -100 .. 100 )
		MAX-ACCESS			 read-create
		STATUS					 current
		DESCRIPTION			 " -- "
		::=  { macUpAlgBaseParaEntry  75 }


	macUpAlgorithmMuMiMoPairChannelCorr		 OBJECT-TYPE
		SYNTAX					 Integer32( 1 .. 100 )
		MAX-ACCESS			 read-create
		STATUS					 current
		DESCRIPTION			 " -- "
		::=  { macUpAlgBaseParaEntry  76 }


	macUpAlgorithmUlEdgeUserMcsTh		 OBJECT-TYPE
		SYNTAX					 Integer32( -18 .. 28 )
		MAX-ACCESS			 read-create
		STATUS					 current
		DESCRIPTION			 " -- "
		::=  { macUpAlgBaseParaEntry  77 }


	macUpAlgorithmVolteMaxSchMcsTag		 OBJECT-TYPE
		SYNTAX					 INTEGER{ off(0),on(1)  }
		MAX-ACCESS			 read-create
		STATUS					 current
		DESCRIPTION			 " -- "
		::=  { macUpAlgBaseParaEntry  78 }


	macUpAlgorithmVolteMaxSchMcs		 OBJECT-TYPE
		SYNTAX					 Unsigned32( 0 .. 28 )
		MAX-ACCESS			 read-create
		STATUS					 current
		DESCRIPTION			 " -- "
		::=  { macUpAlgBaseParaEntry  79 }


	macUpAlgorithmVolteFixCce8Tag		 OBJECT-TYPE
		SYNTAX					 INTEGER{ off(0),on(1)  }
		MAX-ACCESS			 read-create
		STATUS					 current
		DESCRIPTION			 " -- "
		::=  { macUpAlgBaseParaEntry  80 }


	macUpAlgorithmVoltePuschTargetSinrShift		 OBJECT-TYPE
		SYNTAX					 Unsigned32( 0 .. 25 )
		MAX-ACCESS			 read-create
		STATUS					 current
		DESCRIPTION			 " -- "
		::=  { macUpAlgBaseParaEntry  81 }


	macUpAlgorithmCqiMaxModifyFlag		 OBJECT-TYPE
		SYNTAX					 INTEGER{ off(0),on(1)  }
		MAX-ACCESS			 read-create
		STATUS					 current
		DESCRIPTION			 " -- "
		::=  { macUpAlgBaseParaEntry  82 }


	macUpAlgorithmMCSHighLevelOptFlag		 OBJECT-TYPE
		SYNTAX					 INTEGER{ off(0),on(1)  }
		MAX-ACCESS			 read-create
		STATUS					 current
		DESCRIPTION			 " -- "
		::=  { macUpAlgBaseParaEntry  83 }


	macUpAlgorithmMCSN64QAMDiff		 OBJECT-TYPE
		SYNTAX					 Integer32( 1 .. 255 )
		MAX-ACCESS			 read-create
		STATUS					 current
		DESCRIPTION			 " -- "
		::=  { macUpAlgBaseParaEntry  84 }


	macUpAlgorithmMCS64QAMDiff		 OBJECT-TYPE
		SYNTAX					 Integer32( 1 .. 255 )
		MAX-ACCESS			 read-create
		STATUS					 current
		DESCRIPTION			 " -- "
		::=  { macUpAlgBaseParaEntry  85 }


	macUpAlgorithmNoPhrAdaptOptFlag		 OBJECT-TYPE
		SYNTAX					 INTEGER{ off(0),on(1)  }
		MAX-ACCESS			 read-create
		STATUS					 current
		DESCRIPTION			 " -- "
		::=  { macUpAlgBaseParaEntry  86 }


	macUpAlgorithmUeNumThreForPrbLimit		 OBJECT-TYPE
		SYNTAX					 Integer32( 0 .. 1200 )
		MAX-ACCESS			 read-create
		STATUS					 current
		DESCRIPTION			 " -- "
		::=  { macUpAlgBaseParaEntry  87 }


	macUpAlgorithmPrbLimitMcsThre1		 OBJECT-TYPE
		SYNTAX					 Integer32( 0 .. 28 )
		MAX-ACCESS			 read-create
		STATUS					 current
		DESCRIPTION			 " -- "
		::=  { macUpAlgBaseParaEntry  88 }


	macUpAlgorithmPrbLimitMcsThre2		 OBJECT-TYPE
		SYNTAX					 Integer32( 0 .. 28 )
		MAX-ACCESS			 read-create
		STATUS					 current
		DESCRIPTION			 " -- "
		::=  { macUpAlgBaseParaEntry  89 }


	macUpAlgorithmNearPointUePrbNum		 OBJECT-TYPE
		SYNTAX					 Integer32( 0 .. 100 )
		MAX-ACCESS			 read-create
		STATUS					 current
		DESCRIPTION			 " -- "
		::=  { macUpAlgBaseParaEntry  90 }


	macUpAlgorithmMidPointUePrbNum		 OBJECT-TYPE
		SYNTAX					 Integer32( 0 .. 100 )
		MAX-ACCESS			 read-create
		STATUS					 current
		DESCRIPTION			 " -- "
		::=  { macUpAlgBaseParaEntry  91 }


	macUpAlgorithmFarPointUePrbNum		 OBJECT-TYPE
		SYNTAX					 Integer32( 0 .. 100 )
		MAX-ACCESS			 read-create
		STATUS					 current
		DESCRIPTION			 " -- "
		::=  { macUpAlgBaseParaEntry  92 }


	macUpAlgorithmVolteUeMuMimoSwitch		 OBJECT-TYPE
		SYNTAX					 INTEGER{ off(0),on(1)  }
		MAX-ACCESS			 read-create
		STATUS					 current
		DESCRIPTION			 " -- "
		::=  { macUpAlgBaseParaEntry  93 }


	macDownAlgBaseParaTable		 OBJECT-TYPE
		SYNTAX					 SEQUENCE  OF	 MacDownAlgBaseParaEntry
		MAX-ACCESS			 not-accessible
		STATUS					 current
		DESCRIPTION			 " -- "
		::=  { macAlgorithmNode  2 }


	macDownAlgBaseParaEntry		 OBJECT-TYPE
		SYNTAX					 MacDownAlgBaseParaEntry
		MAX-ACCESS			 not-accessible
		STATUS					 current
		DESCRIPTION			 " -- "
		INDEX						{ macDownlinkAlgorithmLcId }
		::=  { macDownAlgBaseParaTable  1 }


	MacDownAlgBaseParaEntry		 ::=  SEQUENCE {
		macDownlinkAlgorithmLcId					Integer32,
		macDownlinkRowStatus					RowStatus,
		macDownlinkMacResType					INTEGER,
		macDownlinkAlgType					INTEGER,
		macDownlinkRetransMCScanbeChanged					INTEGER,
		macDownlinkDlPfScaleRate					Integer32,
		macDownlinkDlPfScaleMcs					Integer32,
		macDownlinkDlT					Integer32,
		macDownlinkCqiFixM					Unsigned32,
		macDownlinkCqiFixP					Unsigned32,
		macDownlinkCqiFixVaddSumMin					Integer32,
		macDownlinkCqiFixVaddSumMax					Integer32,
		macDownlinkRi1Times					Unsigned32,
		macDownlinkRi2Times					Unsigned32,
		macDownlinkCqiFirstBler					Unsigned32,
		macDownlinkDecEff11Tm3					Unsigned32,
		macDownlinkDecEff12Tm3					Unsigned32,
		macDownlinkAddEff21Tm3					Unsigned32,
		macDownlinkDecEff22Tm3					Unsigned32,
		macDownlinkBler122					Unsigned32,
		macDownlinkBler221					Unsigned32,
		macDownlinkCqi12Tm3					Unsigned32,
		macDownlinkCqi22Tm3					Unsigned32,
		macDownlinkDlAntSelectThresCqiHigh					Integer32,
		macDownlinkDlAntSelectThresCqiMedium					Integer32,
		macDownlinkDlAntSelectThresCqiLow					Integer32,
		macDownlinkEff12Tm3					Unsigned32,
		macDownlinkEff22Tm3					Unsigned32,
		macDownlinkN1					Integer32,
		macDownlinkN2					Integer32,
		macDownlinkEffTm73					Unsigned32,
		macDownlinkEffTm37					Unsigned32,
		macDownlinkp					Unsigned32,
		macDownlinkEffTm38					Unsigned32,
		macDownlinkEffTm83					Unsigned32,
		macDownlinkEff12Tm8					Unsigned32,
		macDownlinkEff21Tm8					Unsigned32,
		macDownlinklamdathreshold					Unsigned32,
		macDownlinkTm7SfbcPort5					Integer32,
		macDownlinkSrcFreqEffGap					Integer32,
		macDownlinkFsPrbMax					Integer32,
		macDownlinkSubCqiOffset					Integer32,
		macMimoFirstPeriod					Unsigned32,
		macMimoSecondPeriod					Unsigned32,
		macDownlinkCqiPeriondMin					Integer32,
		macDownlinkCqiPeriondMax					Integer32,
		macDownlinkCqi12SfbcTm4					Unsigned32,
		macDownlinkCqi22SfbcTm4					Unsigned32,
		macDownlinkEffAveFactor					Integer32,
		macMimoSdmSwitch					INTEGER,
		macMimoNewCqi12Tm3					Unsigned32,
		macDownlinkAckInactReleaseUeSwitch					INTEGER,
		macDownlinkAckInactiveNum					Unsigned32,
		macDownlinkAckActiveNum					Unsigned32,
		macDownlinkTm9MuSuMimoSwitch					INTEGER,
		macDownlinkGapOptimizationDlDataScheCqiFixM					Unsigned32,
		macDownlinkPDCCHOrderTransTimes					Unsigned32,
		macDownlinkEffTm39					Unsigned32,
		macDownlinkEffTm93					Unsigned32,
		macDownlinkEffTm9Pre					Unsigned32,
		macDownlinkEffTm9Srs					Unsigned32,
		macDownlinkCsiRsLimitMcs					Unsigned32,
		macDownlinkCsiRsDecMcs					Unsigned32,
		macDownlinkVolteInitBler					Unsigned32,
		macDownlinkQci2InitBler					Unsigned32,
		macDownlinkDlStep					Unsigned32,
		macDownlinkQci6NewPfScale					Unsigned32,
		macDownlinkQci7NewPfScale					Unsigned32,
		macDownlinkQci8NewPfScale					Unsigned32,
		macDownlinkQci9NewPfScale					Unsigned32,
		macQci1DownlinkDlStep					Unsigned32,
		macTestPmiWeightMean					INTEGER,
		macTestPmiWeightFactor					Integer32,
		macTestPmiWeightFactor2ed					Integer32,
		macTestPmiFindError					Integer32,
		macTestPmiReportErrorNum					Integer32,
		macSrbNumLimitSf1					Integer32,
		macSrbNumLimitSf3					Integer32,
		macRetxLimitFlag					INTEGER,
		macMaxBoSwitch					INTEGER,
		macDownlinkHighSpeedNewPfScale					Unsigned32,
		macDownlinkLowSpeedNewPfScale					Unsigned32,
		macDownAlgorithmVolteMaxSchMcsTag					INTEGER,
		macDownAlgorithmVolteMaxSchMcs					Unsigned32,
		macDownlink256QamSwitch					INTEGER,
		macDownlinkEffTableSwitchFlag					INTEGER,
		macDownlinkEffTableSwitchPeriod					Unsigned32,
		macDownlinkEff1TableOToN					Integer32,
		macDownlinkEff1TableNToO					Integer32,
		macDownlinkEff2TableOToN					Integer32,
		macDownlinkEff2TableNToO					Integer32
		}


	macDownlinkAlgorithmLcId		 OBJECT-TYPE
		SYNTAX					 Integer32( 0 .. 23 )
		MAX-ACCESS			 not-accessible
		STATUS					 current
		DESCRIPTION			 " -- "
		::=  { macDownAlgBaseParaEntry  1 }


	macDownlinkRowStatus		 OBJECT-TYPE
		SYNTAX					 RowStatus
		MAX-ACCESS			 read-create
		STATUS					 current
		DESCRIPTION			 " -- "
		::=  { macDownAlgBaseParaEntry  2 }


	macDownlinkMacResType		 OBJECT-TYPE
		SYNTAX					 INTEGER{ adaptive(-1),type0(0),type1(1),type2(2)  }
		MAX-ACCESS			 read-create
		STATUS					 current
		DESCRIPTION			 " -- "
		::=  { macDownAlgBaseParaEntry  5 }


	macDownlinkAlgType		 OBJECT-TYPE
		SYNTAX					 INTEGER{ rr(0),maxci(1),pf(2),irr(3),newpf(4)  }
		MAX-ACCESS			 read-create
		STATUS					 current
		DESCRIPTION			 " -- "
		::=  { macDownAlgBaseParaEntry  6 }


	macDownlinkRetransMCScanbeChanged		 OBJECT-TYPE
		SYNTAX					 INTEGER{ notSupport(0),support(1)  }
		MAX-ACCESS			 read-create
		STATUS					 current
		DESCRIPTION			 " -- "
		::=  { macDownAlgBaseParaEntry  8 }


	macDownlinkDlPfScaleRate		 OBJECT-TYPE
		SYNTAX					 Integer32( 0 .. 65535 )
		MAX-ACCESS			 read-create
		STATUS					 current
		DESCRIPTION			 " -- "
		::=  { macDownAlgBaseParaEntry  9 }


	macDownlinkDlPfScaleMcs		 OBJECT-TYPE
		SYNTAX					 Integer32( 0 .. 65535 )
		MAX-ACCESS			 read-create
		STATUS					 current
		DESCRIPTION			 " -- "
		::=  { macDownAlgBaseParaEntry  10 }


	macDownlinkDlT		 OBJECT-TYPE
		SYNTAX					 Integer32( 0 .. 65535 )
		MAX-ACCESS			 read-create
		STATUS					 current
		DESCRIPTION			 " -- "
		::=  { macDownAlgBaseParaEntry  11 }


	macDownlinkCqiFixM		 OBJECT-TYPE
		SYNTAX					 Unsigned32( 0 .. 28 )
		MAX-ACCESS			 read-create
		STATUS					 current
		DESCRIPTION			 " -- "
		::=  { macDownAlgBaseParaEntry  12 }


	macDownlinkCqiFixP		 OBJECT-TYPE
		SYNTAX					 Unsigned32( 0 .. 1024 )
		MAX-ACCESS			 read-create
		STATUS					 current
		DESCRIPTION			 " -- "
		::=  { macDownAlgBaseParaEntry  18 }


	macDownlinkCqiFixVaddSumMin		 OBJECT-TYPE
		SYNTAX					 Integer32( -100000 .. 100000 )
		MAX-ACCESS			 read-create
		STATUS					 current
		DESCRIPTION			 " -- "
		::=  { macDownAlgBaseParaEntry  20 }


	macDownlinkCqiFixVaddSumMax		 OBJECT-TYPE
		SYNTAX					 Integer32( -100000 .. 100000 )
		MAX-ACCESS			 read-create
		STATUS					 current
		DESCRIPTION			 " -- "
		::=  { macDownAlgBaseParaEntry  21 }


	macDownlinkRi1Times		 OBJECT-TYPE
		SYNTAX					 Unsigned32( 1 .. 100 )
		MAX-ACCESS			 read-create
		STATUS					 current
		DESCRIPTION			 " -- "
		::=  { macDownAlgBaseParaEntry  22 }


	macDownlinkRi2Times		 OBJECT-TYPE
		SYNTAX					 Unsigned32( 1 .. 100 )
		MAX-ACCESS			 read-create
		STATUS					 current
		DESCRIPTION			 " -- "
		::=  { macDownAlgBaseParaEntry  23 }


	macDownlinkCqiFirstBler		 OBJECT-TYPE
		SYNTAX					 Unsigned32( 1 .. 100 )
		MAX-ACCESS			 read-create
		STATUS					 current
		DESCRIPTION			 " -- "
		::=  { macDownAlgBaseParaEntry  24 }


	macDownlinkDecEff11Tm3		 OBJECT-TYPE
		SYNTAX					 Unsigned32( 0 .. 100 )
		MAX-ACCESS			 read-create
		STATUS					 current
		DESCRIPTION			 " -- "
		::=  { macDownAlgBaseParaEntry  25 }


	macDownlinkDecEff12Tm3		 OBJECT-TYPE
		SYNTAX					 Unsigned32( 1 .. 100 )
		MAX-ACCESS			 read-create
		STATUS					 current
		DESCRIPTION			 " -- "
		::=  { macDownAlgBaseParaEntry  26 }


	macDownlinkAddEff21Tm3		 OBJECT-TYPE
		SYNTAX					 Unsigned32( 1 .. 100 )
		MAX-ACCESS			 read-create
		STATUS					 current
		DESCRIPTION			 " -- "
		::=  { macDownAlgBaseParaEntry  27 }


	macDownlinkDecEff22Tm3		 OBJECT-TYPE
		SYNTAX					 Unsigned32( 0 .. 100 )
		MAX-ACCESS			 read-create
		STATUS					 current
		DESCRIPTION			 " -- "
		::=  { macDownAlgBaseParaEntry  28 }


	macDownlinkBler122		 OBJECT-TYPE
		SYNTAX					 Unsigned32( 0 .. 100 )
		MAX-ACCESS			 read-create
		STATUS					 current
		DESCRIPTION			 " -- "
		::=  { macDownAlgBaseParaEntry  29 }


	macDownlinkBler221		 OBJECT-TYPE
		SYNTAX					 Unsigned32( 0 .. 100 )
		MAX-ACCESS			 read-create
		STATUS					 current
		DESCRIPTION			 " -- "
		::=  { macDownAlgBaseParaEntry  30 }


	macDownlinkCqi12Tm3		 OBJECT-TYPE
		SYNTAX					 Unsigned32( 0 .. 15 )
		MAX-ACCESS			 read-create
		STATUS					 current
		DESCRIPTION			 " -- "
		::=  { macDownAlgBaseParaEntry  31 }


	macDownlinkCqi22Tm3		 OBJECT-TYPE
		SYNTAX					 Unsigned32( 0 .. 15 )
		MAX-ACCESS			 read-create
		STATUS					 current
		DESCRIPTION			 " -- "
		::=  { macDownAlgBaseParaEntry  32 }


	macDownlinkDlAntSelectThresCqiHigh		 OBJECT-TYPE
		SYNTAX					 Integer32( 0 .. 120 )
		MAX-ACCESS			 read-create
		STATUS					 current
		DESCRIPTION			 " -- "
		::=  { macDownAlgBaseParaEntry  36 }


	macDownlinkDlAntSelectThresCqiMedium		 OBJECT-TYPE
		SYNTAX					 Integer32( 0 .. 120 )
		MAX-ACCESS			 read-create
		STATUS					 current
		DESCRIPTION			 " -- "
		::=  { macDownAlgBaseParaEntry  37 }


	macDownlinkDlAntSelectThresCqiLow		 OBJECT-TYPE
		SYNTAX					 Integer32( 0 .. 120 )
		MAX-ACCESS			 read-create
		STATUS					 current
		DESCRIPTION			 " -- "
		::=  { macDownAlgBaseParaEntry  38 }


	macDownlinkEff12Tm3		 OBJECT-TYPE
		SYNTAX					 Unsigned32( 2 .. 15 )
		MAX-ACCESS			 read-create
		STATUS					 current
		DESCRIPTION			 " -- "
		::=  { macDownAlgBaseParaEntry  39 }


	macDownlinkEff22Tm3		 OBJECT-TYPE
		SYNTAX					 Unsigned32( 2 .. 15 )
		MAX-ACCESS			 read-create
		STATUS					 current
		DESCRIPTION			 " -- "
		::=  { macDownAlgBaseParaEntry  40 }


	macDownlinkN1		 OBJECT-TYPE
		SYNTAX					 Integer32( 1 .. 255 )
		MAX-ACCESS			 read-create
		STATUS					 current
		DESCRIPTION			 " -- "
		::=  { macDownAlgBaseParaEntry  41 }


	macDownlinkN2		 OBJECT-TYPE
		SYNTAX					 Integer32( 1 .. 255 )
		MAX-ACCESS			 read-create
		STATUS					 current
		DESCRIPTION			 " -- "
		::=  { macDownAlgBaseParaEntry  42 }


	macDownlinkEffTm73		 OBJECT-TYPE
		SYNTAX					 Unsigned32( 2 .. 15 )
		MAX-ACCESS			 read-create
		STATUS					 current
		DESCRIPTION			 " -- "
		::=  { macDownAlgBaseParaEntry  43 }


	macDownlinkEffTm37		 OBJECT-TYPE
		SYNTAX					 Unsigned32( 2 .. 15 )
		MAX-ACCESS			 read-create
		STATUS					 current
		DESCRIPTION			 " -- "
		::=  { macDownAlgBaseParaEntry  44 }


	macDownlinkp		 OBJECT-TYPE
		SYNTAX					 Unsigned32( 0 .. 1024 )
		MAX-ACCESS			 read-create
		STATUS					 current
		DESCRIPTION			 " -- "
		::=  { macDownAlgBaseParaEntry  45 }


	macDownlinkEffTm38		 OBJECT-TYPE
		SYNTAX					 Unsigned32( 2 .. 15 )
		MAX-ACCESS			 read-create
		STATUS					 current
		DESCRIPTION			 " -- "
		::=  { macDownAlgBaseParaEntry  46 }


	macDownlinkEffTm83		 OBJECT-TYPE
		SYNTAX					 Unsigned32( 2 .. 15 )
		MAX-ACCESS			 read-create
		STATUS					 current
		DESCRIPTION			 " -- "
		::=  { macDownAlgBaseParaEntry  47 }


	macDownlinkEff12Tm8		 OBJECT-TYPE
		SYNTAX					 Unsigned32( 2 .. 15 )
		MAX-ACCESS			 read-create
		STATUS					 current
		DESCRIPTION			 " -- "
		::=  { macDownAlgBaseParaEntry  48 }


	macDownlinkEff21Tm8		 OBJECT-TYPE
		SYNTAX					 Unsigned32( 2 .. 15 )
		MAX-ACCESS			 read-create
		STATUS					 current
		DESCRIPTION			 " -- "
		::=  { macDownAlgBaseParaEntry  49 }


	macDownlinklamdathreshold		 OBJECT-TYPE
		SYNTAX					 Unsigned32( 0 .. 60 )
		MAX-ACCESS			 read-create
		STATUS					 current
		DESCRIPTION			 " -- "
		::=  { macDownAlgBaseParaEntry  50 }


	macDownlinkTm7SfbcPort5		 OBJECT-TYPE
		SYNTAX					 Integer32( 0 .. 15 )
		MAX-ACCESS			 read-create
		STATUS					 current
		DESCRIPTION			 " -- "
		::=  { macDownAlgBaseParaEntry  51 }


	macDownlinkSrcFreqEffGap		 OBJECT-TYPE
		SYNTAX					 Integer32( 0 .. 10000 )
		MAX-ACCESS			 read-create
		STATUS					 current
		DESCRIPTION			 " -- "
		::=  { macDownAlgBaseParaEntry  52 }


	macDownlinkFsPrbMax		 OBJECT-TYPE
		SYNTAX					 Integer32( 4 .. 36 )
		MAX-ACCESS			 read-create
		STATUS					 current
		DESCRIPTION			 " -- "
		::=  { macDownAlgBaseParaEntry  53 }


	macDownlinkSubCqiOffset		 OBJECT-TYPE
		SYNTAX					 Integer32( 0 .. 6 )
		MAX-ACCESS			 read-create
		STATUS					 current
		DESCRIPTION			 " -- "
		::=  { macDownAlgBaseParaEntry  54 }


	macMimoFirstPeriod		 OBJECT-TYPE
		SYNTAX					 Unsigned32( 80 .. 10000 )
		MAX-ACCESS			 read-create
		STATUS					 current
		DESCRIPTION			 " -- "
		::=  { macDownAlgBaseParaEntry  55 }


	macMimoSecondPeriod		 OBJECT-TYPE
		SYNTAX					 Unsigned32( 80 .. 10000 )
		MAX-ACCESS			 read-create
		STATUS					 current
		DESCRIPTION			 " -- "
		::=  { macDownAlgBaseParaEntry  56 }


	macDownlinkCqiPeriondMin		 OBJECT-TYPE
		SYNTAX					 Integer32( -100000 .. 100000 )
		MAX-ACCESS			 read-create
		STATUS					 current
		DESCRIPTION			 " -- "
		::=  { macDownAlgBaseParaEntry  57 }


	macDownlinkCqiPeriondMax		 OBJECT-TYPE
		SYNTAX					 Integer32( -100000 .. 100000 )
		MAX-ACCESS			 read-create
		STATUS					 current
		DESCRIPTION			 " -- "
		::=  { macDownAlgBaseParaEntry  58 }


	macDownlinkCqi12SfbcTm4		 OBJECT-TYPE
		SYNTAX					 Unsigned32( 0 .. 15 )
		MAX-ACCESS			 read-create
		STATUS					 current
		DESCRIPTION			 " -- "
		::=  { macDownAlgBaseParaEntry  59 }


	macDownlinkCqi22SfbcTm4		 OBJECT-TYPE
		SYNTAX					 Unsigned32( 0 .. 15 )
		MAX-ACCESS			 read-create
		STATUS					 current
		DESCRIPTION			 " -- "
		::=  { macDownAlgBaseParaEntry  60 }


	macDownlinkEffAveFactor		 OBJECT-TYPE
		SYNTAX					 Integer32( 0 .. 1000 )
		MAX-ACCESS			 read-create
		STATUS					 current
		DESCRIPTION			 " -- "
		::=  { macDownAlgBaseParaEntry  61 }


	macMimoSdmSwitch		 OBJECT-TYPE
		SYNTAX					 INTEGER{ off(0),on(1)  }
		MAX-ACCESS			 read-create
		STATUS					 current
		DESCRIPTION			 " -- "
		::=  { macDownAlgBaseParaEntry  62 }


	macMimoNewCqi12Tm3		 OBJECT-TYPE
		SYNTAX					 Unsigned32( 0 .. 15 )
		MAX-ACCESS			 read-create
		STATUS					 current
		DESCRIPTION			 " -- "
		::=  { macDownAlgBaseParaEntry  63 }


	macDownlinkAckInactReleaseUeSwitch		 OBJECT-TYPE
		SYNTAX					 INTEGER{ off(0),on(1)  }
		MAX-ACCESS			 read-create
		STATUS					 current
		DESCRIPTION			 " -- "
		::=  { macDownAlgBaseParaEntry  64 }


	macDownlinkAckInactiveNum		 OBJECT-TYPE
		SYNTAX					 Unsigned32( 0 .. 400 )
		MAX-ACCESS			 read-create
		STATUS					 current
		DESCRIPTION			 " -- "
		::=  { macDownAlgBaseParaEntry  65 }


	macDownlinkAckActiveNum		 OBJECT-TYPE
		SYNTAX					 Unsigned32( 0 .. 100 )
		MAX-ACCESS			 read-create
		STATUS					 current
		DESCRIPTION			 " -- "
		::=  { macDownAlgBaseParaEntry  66 }


	macDownlinkTm9MuSuMimoSwitch		 OBJECT-TYPE
		SYNTAX					 INTEGER{ mumimo(0),sumimo(1),forbidtm9(2)  }
		MAX-ACCESS			 read-create
		STATUS					 current
		DESCRIPTION			 " -- "
		::=  { macDownAlgBaseParaEntry  67 }


	macDownlinkGapOptimizationDlDataScheCqiFixM		 OBJECT-TYPE
		SYNTAX					 Unsigned32( 0 .. 28 )
		MAX-ACCESS			 read-create
		STATUS					 current
		DESCRIPTION			 " -- "
		::=  { macDownAlgBaseParaEntry  68 }


	macDownlinkPDCCHOrderTransTimes		 OBJECT-TYPE
		SYNTAX					 Unsigned32( 1 .. 4 )
		MAX-ACCESS			 read-create
		STATUS					 current
		DESCRIPTION			 " -- "
		::=  { macDownAlgBaseParaEntry  69 }


	macDownlinkEffTm39		 OBJECT-TYPE
		SYNTAX					 Unsigned32( 2 .. 15 )
		MAX-ACCESS			 read-create
		STATUS					 current
		DESCRIPTION			 " -- "
		::=  { macDownAlgBaseParaEntry  70 }


	macDownlinkEffTm93		 OBJECT-TYPE
		SYNTAX					 Unsigned32( 2 .. 15 )
		MAX-ACCESS			 read-create
		STATUS					 current
		DESCRIPTION			 " -- "
		::=  { macDownAlgBaseParaEntry  71 }


	macDownlinkEffTm9Pre		 OBJECT-TYPE
		SYNTAX					 Unsigned32( 2 .. 15 )
		MAX-ACCESS			 read-create
		STATUS					 current
		DESCRIPTION			 " -- "
		::=  { macDownAlgBaseParaEntry  72 }


	macDownlinkEffTm9Srs		 OBJECT-TYPE
		SYNTAX					 Unsigned32( 2 .. 15 )
		MAX-ACCESS			 read-create
		STATUS					 current
		DESCRIPTION			 " -- "
		::=  { macDownAlgBaseParaEntry  73 }


	macDownlinkCsiRsLimitMcs		 OBJECT-TYPE
		SYNTAX					 Unsigned32( 0 .. 28 )
		MAX-ACCESS			 read-create
		STATUS					 current
		DESCRIPTION			 " -- "
		::=  { macDownAlgBaseParaEntry  75 }


	macDownlinkCsiRsDecMcs		 OBJECT-TYPE
		SYNTAX					 Unsigned32( 0 .. 28 )
		MAX-ACCESS			 read-create
		STATUS					 current
		DESCRIPTION			 " -- "
		::=  { macDownAlgBaseParaEntry  76 }


	macDownlinkVolteInitBler		 OBJECT-TYPE
		SYNTAX					 Unsigned32( 1 .. 100 )
		MAX-ACCESS			 read-create
		STATUS					 current
		DESCRIPTION			 " -- "
		::=  { macDownAlgBaseParaEntry  77 }


	macDownlinkQci2InitBler		 OBJECT-TYPE
		SYNTAX					 Unsigned32( 1 .. 100 )
		MAX-ACCESS			 read-create
		STATUS					 current
		DESCRIPTION			 " -- "
		::=  { macDownAlgBaseParaEntry  78 }


	macDownlinkDlStep		 OBJECT-TYPE
		SYNTAX					 Unsigned32( 0 .. 65535 )
		MAX-ACCESS			 read-create
		STATUS					 current
		DESCRIPTION			 " -- "
		::=  { macDownAlgBaseParaEntry  79 }


	macDownlinkQci6NewPfScale		 OBJECT-TYPE
		SYNTAX					 Unsigned32( 1 .. 100 )
		MAX-ACCESS			 read-create
		STATUS					 current
		DESCRIPTION			 " -- "
		::=  { macDownAlgBaseParaEntry  80 }


	macDownlinkQci7NewPfScale		 OBJECT-TYPE
		SYNTAX					 Unsigned32( 1 .. 100 )
		MAX-ACCESS			 read-create
		STATUS					 current
		DESCRIPTION			 " -- "
		::=  { macDownAlgBaseParaEntry  81 }


	macDownlinkQci8NewPfScale		 OBJECT-TYPE
		SYNTAX					 Unsigned32( 1 .. 100 )
		MAX-ACCESS			 read-create
		STATUS					 current
		DESCRIPTION			 " -- "
		::=  { macDownAlgBaseParaEntry  82 }


	macDownlinkQci9NewPfScale		 OBJECT-TYPE
		SYNTAX					 Unsigned32( 1 .. 100 )
		MAX-ACCESS			 read-create
		STATUS					 current
		DESCRIPTION			 " -- "
		::=  { macDownAlgBaseParaEntry  83 }


	macQci1DownlinkDlStep		 OBJECT-TYPE
		SYNTAX					 Unsigned32( 0 .. 65535 )
		MAX-ACCESS			 read-create
		STATUS					 current
		DESCRIPTION			 " -- "
		::=  { macDownAlgBaseParaEntry  84 }


	macTestPmiWeightMean		 OBJECT-TYPE
		SYNTAX					 INTEGER{ off(0),on(1)  }
		MAX-ACCESS			 read-create
		STATUS					 current
		DESCRIPTION			 " -- "
		::=  { macDownAlgBaseParaEntry  85 }


	macTestPmiWeightFactor		 OBJECT-TYPE
		SYNTAX					 Integer32( 0 .. 255 )
		MAX-ACCESS			 read-create
		STATUS					 current
		DESCRIPTION			 " -- "
		::=  { macDownAlgBaseParaEntry  86 }


	macTestPmiWeightFactor2ed		 OBJECT-TYPE
		SYNTAX					 Integer32( 0 .. 255 )
		MAX-ACCESS			 read-create
		STATUS					 current
		DESCRIPTION			 " -- "
		::=  { macDownAlgBaseParaEntry  87 }


	macTestPmiFindError		 OBJECT-TYPE
		SYNTAX					 Integer32( 1 .. 64 )
		MAX-ACCESS			 read-create
		STATUS					 current
		DESCRIPTION			 " -- "
		::=  { macDownAlgBaseParaEntry  88 }


	macTestPmiReportErrorNum		 OBJECT-TYPE
		SYNTAX					 Integer32( 1 .. 64 )
		MAX-ACCESS			 read-create
		STATUS					 current
		DESCRIPTION			 " -- "
		::=  { macDownAlgBaseParaEntry  89 }


	macSrbNumLimitSf1		 OBJECT-TYPE
		SYNTAX					 Integer32( 0 .. 50 )
		MAX-ACCESS			 read-create
		STATUS					 current
		DESCRIPTION			 " -- "
		::=  { macDownAlgBaseParaEntry  90 }


	macSrbNumLimitSf3		 OBJECT-TYPE
		SYNTAX					 Integer32( 0 .. 50 )
		MAX-ACCESS			 read-create
		STATUS					 current
		DESCRIPTION			 " -- "
		::=  { macDownAlgBaseParaEntry  91 }


	macRetxLimitFlag		 OBJECT-TYPE
		SYNTAX					 INTEGER{ off(0),on(1)  }
		MAX-ACCESS			 read-create
		STATUS					 current
		DESCRIPTION			 " -- "
		::=  { macDownAlgBaseParaEntry  92 }


	macMaxBoSwitch		 OBJECT-TYPE
		SYNTAX					 INTEGER{ off(0),sf16(1),sf1368(2),sf38(3)  }
		MAX-ACCESS			 read-create
		STATUS					 current
		DESCRIPTION			 " -- "
		::=  { macDownAlgBaseParaEntry  93 }


	macDownlinkHighSpeedNewPfScale		 OBJECT-TYPE
		SYNTAX					 Unsigned32( 1 .. 100 )
		MAX-ACCESS			 read-create
		STATUS					 current
		DESCRIPTION			 " -- "
		::=  { macDownAlgBaseParaEntry  94 }


	macDownlinkLowSpeedNewPfScale		 OBJECT-TYPE
		SYNTAX					 Unsigned32( 1 .. 100 )
		MAX-ACCESS			 read-create
		STATUS					 current
		DESCRIPTION			 " -- "
		::=  { macDownAlgBaseParaEntry  95 }


	macDownAlgorithmVolteMaxSchMcsTag		 OBJECT-TYPE
		SYNTAX					 INTEGER{ off(0),on(1)  }
		MAX-ACCESS			 read-create
		STATUS					 current
		DESCRIPTION			 " -- "
		::=  { macDownAlgBaseParaEntry  96 }


	macDownAlgorithmVolteMaxSchMcs		 OBJECT-TYPE
		SYNTAX					 Unsigned32( 0 .. 28 )
		MAX-ACCESS			 read-create
		STATUS					 current
		DESCRIPTION			 " -- "
		::=  { macDownAlgBaseParaEntry  97 }


	macDownlink256QamSwitch		 OBJECT-TYPE
		SYNTAX					 INTEGER{ off(0),on(1)  }
		MAX-ACCESS			 read-create
		STATUS					 current
		DESCRIPTION			 " -- "
		::=  { macDownAlgBaseParaEntry  100 }


	macDownlinkEffTableSwitchFlag		 OBJECT-TYPE
		SYNTAX					 INTEGER{ off(0),on(1)  }
		MAX-ACCESS			 read-create
		STATUS					 current
		DESCRIPTION			 " -- "
		::=  { macDownAlgBaseParaEntry  101 }


	macDownlinkEffTableSwitchPeriod		 OBJECT-TYPE
		SYNTAX					 Unsigned32( 80 .. 10000 )
		MAX-ACCESS			 read-create
		STATUS					 current
		DESCRIPTION			 " -- "
		::=  { macDownAlgBaseParaEntry  102 }


	macDownlinkEff1TableOToN		 OBJECT-TYPE
		SYNTAX					 Integer32( 0 .. 15 )
		MAX-ACCESS			 read-create
		STATUS					 current
		DESCRIPTION			 " -- "
		::=  { macDownAlgBaseParaEntry  103 }


	macDownlinkEff1TableNToO		 OBJECT-TYPE
		SYNTAX					 Integer32( 0 .. 15 )
		MAX-ACCESS			 read-create
		STATUS					 current
		DESCRIPTION			 " -- "
		::=  { macDownAlgBaseParaEntry  104 }


	macDownlinkEff2TableOToN		 OBJECT-TYPE
		SYNTAX					 Integer32( 0 .. 15 )
		MAX-ACCESS			 read-create
		STATUS					 current
		DESCRIPTION			 " -- "
		::=  { macDownAlgBaseParaEntry  105 }


	macDownlinkEff2TableNToO		 OBJECT-TYPE
		SYNTAX					 Integer32( 0 .. 15 )
		MAX-ACCESS			 read-create
		STATUS					 current
		DESCRIPTION			 " -- "
		::=  { macDownAlgBaseParaEntry  106 }


	macDownMuMiMoAlgBaseParaTable		 OBJECT-TYPE
		SYNTAX					 SEQUENCE  OF	 MacDownMuMiMoAlgBaseParaEntry
		MAX-ACCESS			 not-accessible
		STATUS					 current
		DESCRIPTION			 " -- "
		::=  { macAlgorithmNode  3 }


	macDownMuMiMoAlgBaseParaEntry		 OBJECT-TYPE
		SYNTAX					 MacDownMuMiMoAlgBaseParaEntry
		MAX-ACCESS			 not-accessible
		STATUS					 current
		DESCRIPTION			 " -- "
		INDEX						{ macDownlinkMuMiMoAlgorithmLcId }
		::=  { macDownMuMiMoAlgBaseParaTable  1 }


	MacDownMuMiMoAlgBaseParaEntry		 ::=  SEQUENCE {
		macDownlinkMuMiMoAlgorithmLcId					Integer32,
		macDownlinkMuMiMoRowStatus					RowStatus,
		macDownlinkMuMiMoUePairEffThr					Integer32,
		macDownlinkMuMiMoUePairEffDiffThr					Integer32,
		macDonwlinkMuMiMoUePairAoADiffThr					Integer32,
		macDownlinkMuMiMoEffAdjustDlMuMimo					Integer32,
		macDownlinkMuMiMoPowerDeductFactor					Integer32,
		macDownlinkMuMiMoResPreestamateFactor					Integer32,
		macDownlinkMuMiMoMcsBackoff0					Integer32,
		macDownlinkMuMiMoMcsBackoff1					Integer32,
		macDownlinkMuMiMoMcsBackoff2					Integer32,
		macDownlinkMuMiMoMcsBackoff3					Integer32,
		macDownlinkMuMiMoMcsBackoff4					Integer32,
		macDownlinkMuMiMoMcsBackoff5					Integer32,
		macDownlinkMuMiMoMcsBackoff6					Integer32,
		macDownlinkMuMiMoMcsBackoff7					Integer32,
		macDownlinkMuMiMoMcsBackoff8					Integer32,
		macDownlinkMuMiMoMcsBackoff9					Integer32,
		macDownlinkMuMiMoMcsBackoff10					Integer32,
		macDownlinkMuMiMoMcsBackoff11					Integer32,
		macDownlinkMuMiMoMcsBackoff12					Integer32,
		macDownlinkMuMiMoMcsBackoff13					Integer32,
		macDownlinkMuMiMoMcsBackoff14					Integer32,
		macDownlinkMuMiMoMcsBackoff15					Integer32,
		macDownlinkMuMiMoMcsBackoff16					Integer32,
		macDownlinkMuMiMoMcsBackoff17					Integer32,
		macDownlinkMuMiMoMcsBackoff18					Integer32,
		macDownlinkMuMiMoMcsBackoff19					Integer32,
		macDownlinkMuMiMoMcsBackoff20					Integer32,
		macDownlinkMuMiMoMcsBackoff21					Integer32,
		macDownlinkMuMiMoMcsBackoff22					Integer32,
		macDownlinkMuMiMoMcsBackoff23					Integer32,
		macDownlinkMuMiMoMcsBackoff24					Integer32,
		macDownlinkMuMiMoMcsBackoff25					Integer32,
		macDownlinkMuMiMoMcsBackoff26					Integer32,
		macDownlinkMuMiMoMcsBackoff27					Integer32
		}


	macDownlinkMuMiMoAlgorithmLcId		 OBJECT-TYPE
		SYNTAX					 Integer32( 0 .. 23 )
		MAX-ACCESS			 not-accessible
		STATUS					 current
		DESCRIPTION			 " -- "
		::=  { macDownMuMiMoAlgBaseParaEntry  1 }


	macDownlinkMuMiMoRowStatus		 OBJECT-TYPE
		SYNTAX					 RowStatus
		MAX-ACCESS			 read-create
		STATUS					 current
		DESCRIPTION			 " -- "
		::=  { macDownMuMiMoAlgBaseParaEntry  2 }


	macDownlinkMuMiMoUePairEffThr		 OBJECT-TYPE
		SYNTAX					 Integer32( 1523 .. 55547 )
		MAX-ACCESS			 read-create
		STATUS					 current
		DESCRIPTION			 " -- "
		::=  { macDownMuMiMoAlgBaseParaEntry  3 }


	macDownlinkMuMiMoUePairEffDiffThr		 OBJECT-TYPE
		SYNTAX					 Integer32( 1523 .. 55547 )
		MAX-ACCESS			 read-create
		STATUS					 current
		DESCRIPTION			 " -- "
		::=  { macDownMuMiMoAlgBaseParaEntry  4 }


	macDonwlinkMuMiMoUePairAoADiffThr		 OBJECT-TYPE
		SYNTAX					 Integer32( 0 .. 180 )
		MAX-ACCESS			 read-create
		STATUS					 current
		DESCRIPTION			 " -- "
		::=  { macDownMuMiMoAlgBaseParaEntry  5 }


	macDownlinkMuMiMoEffAdjustDlMuMimo		 OBJECT-TYPE
		SYNTAX					 Integer32( 0 .. 60 )
		MAX-ACCESS			 read-create
		STATUS					 current
		DESCRIPTION			 " -- "
		::=  { macDownMuMiMoAlgBaseParaEntry  6 }


	macDownlinkMuMiMoPowerDeductFactor		 OBJECT-TYPE
		SYNTAX					 Integer32( 0 .. 60 )
		MAX-ACCESS			 read-create
		STATUS					 current
		DESCRIPTION			 " -- "
		::=  { macDownMuMiMoAlgBaseParaEntry  7 }


	macDownlinkMuMiMoResPreestamateFactor		 OBJECT-TYPE
		SYNTAX					 Integer32( 12 .. 20 )
		MAX-ACCESS			 read-create
		STATUS					 current
		DESCRIPTION			 " -- "
		::=  { macDownMuMiMoAlgBaseParaEntry  8 }


	macDownlinkMuMiMoMcsBackoff0		 OBJECT-TYPE
		SYNTAX					 Integer32( 0 .. 6 )
		MAX-ACCESS			 read-create
		STATUS					 current
		DESCRIPTION			 " -- "
		::=  { macDownMuMiMoAlgBaseParaEntry  9 }


	macDownlinkMuMiMoMcsBackoff1		 OBJECT-TYPE
		SYNTAX					 Integer32( 0 .. 6 )
		MAX-ACCESS			 read-create
		STATUS					 current
		DESCRIPTION			 " -- "
		::=  { macDownMuMiMoAlgBaseParaEntry  10 }


	macDownlinkMuMiMoMcsBackoff2		 OBJECT-TYPE
		SYNTAX					 Integer32( 0 .. 6 )
		MAX-ACCESS			 read-create
		STATUS					 current
		DESCRIPTION			 " -- "
		::=  { macDownMuMiMoAlgBaseParaEntry  11 }


	macDownlinkMuMiMoMcsBackoff3		 OBJECT-TYPE
		SYNTAX					 Integer32( 0 .. 6 )
		MAX-ACCESS			 read-create
		STATUS					 current
		DESCRIPTION			 " -- "
		::=  { macDownMuMiMoAlgBaseParaEntry  12 }


	macDownlinkMuMiMoMcsBackoff4		 OBJECT-TYPE
		SYNTAX					 Integer32( 0 .. 6 )
		MAX-ACCESS			 read-create
		STATUS					 current
		DESCRIPTION			 " -- "
		::=  { macDownMuMiMoAlgBaseParaEntry  13 }


	macDownlinkMuMiMoMcsBackoff5		 OBJECT-TYPE
		SYNTAX					 Integer32( 0 .. 6 )
		MAX-ACCESS			 read-create
		STATUS					 current
		DESCRIPTION			 " -- "
		::=  { macDownMuMiMoAlgBaseParaEntry  14 }


	macDownlinkMuMiMoMcsBackoff6		 OBJECT-TYPE
		SYNTAX					 Integer32( 0 .. 6 )
		MAX-ACCESS			 read-create
		STATUS					 current
		DESCRIPTION			 " -- "
		::=  { macDownMuMiMoAlgBaseParaEntry  15 }


	macDownlinkMuMiMoMcsBackoff7		 OBJECT-TYPE
		SYNTAX					 Integer32( 0 .. 6 )
		MAX-ACCESS			 read-create
		STATUS					 current
		DESCRIPTION			 " -- "
		::=  { macDownMuMiMoAlgBaseParaEntry  16 }


	macDownlinkMuMiMoMcsBackoff8		 OBJECT-TYPE
		SYNTAX					 Integer32( 0 .. 6 )
		MAX-ACCESS			 read-create
		STATUS					 current
		DESCRIPTION			 " -- "
		::=  { macDownMuMiMoAlgBaseParaEntry  17 }


	macDownlinkMuMiMoMcsBackoff9		 OBJECT-TYPE
		SYNTAX					 Integer32( 0 .. 6 )
		MAX-ACCESS			 read-create
		STATUS					 current
		DESCRIPTION			 " -- "
		::=  { macDownMuMiMoAlgBaseParaEntry  18 }


	macDownlinkMuMiMoMcsBackoff10		 OBJECT-TYPE
		SYNTAX					 Integer32( 0 .. 6 )
		MAX-ACCESS			 read-create
		STATUS					 current
		DESCRIPTION			 " -- "
		::=  { macDownMuMiMoAlgBaseParaEntry  19 }


	macDownlinkMuMiMoMcsBackoff11		 OBJECT-TYPE
		SYNTAX					 Integer32( 0 .. 6 )
		MAX-ACCESS			 read-create
		STATUS					 current
		DESCRIPTION			 " -- "
		::=  { macDownMuMiMoAlgBaseParaEntry  20 }


	macDownlinkMuMiMoMcsBackoff12		 OBJECT-TYPE
		SYNTAX					 Integer32( 0 .. 6 )
		MAX-ACCESS			 read-create
		STATUS					 current
		DESCRIPTION			 " -- "
		::=  { macDownMuMiMoAlgBaseParaEntry  21 }


	macDownlinkMuMiMoMcsBackoff13		 OBJECT-TYPE
		SYNTAX					 Integer32( 0 .. 6 )
		MAX-ACCESS			 read-create
		STATUS					 current
		DESCRIPTION			 " -- "
		::=  { macDownMuMiMoAlgBaseParaEntry  22 }


	macDownlinkMuMiMoMcsBackoff14		 OBJECT-TYPE
		SYNTAX					 Integer32( 0 .. 6 )
		MAX-ACCESS			 read-create
		STATUS					 current
		DESCRIPTION			 " -- "
		::=  { macDownMuMiMoAlgBaseParaEntry  23 }


	macDownlinkMuMiMoMcsBackoff15		 OBJECT-TYPE
		SYNTAX					 Integer32( 0 .. 6 )
		MAX-ACCESS			 read-create
		STATUS					 current
		DESCRIPTION			 " -- "
		::=  { macDownMuMiMoAlgBaseParaEntry  24 }


	macDownlinkMuMiMoMcsBackoff16		 OBJECT-TYPE
		SYNTAX					 Integer32( 0 .. 6 )
		MAX-ACCESS			 read-create
		STATUS					 current
		DESCRIPTION			 " -- "
		::=  { macDownMuMiMoAlgBaseParaEntry  25 }


	macDownlinkMuMiMoMcsBackoff17		 OBJECT-TYPE
		SYNTAX					 Integer32( 0 .. 6 )
		MAX-ACCESS			 read-create
		STATUS					 current
		DESCRIPTION			 " -- "
		::=  { macDownMuMiMoAlgBaseParaEntry  26 }


	macDownlinkMuMiMoMcsBackoff18		 OBJECT-TYPE
		SYNTAX					 Integer32( 0 .. 6 )
		MAX-ACCESS			 read-create
		STATUS					 current
		DESCRIPTION			 " -- "
		::=  { macDownMuMiMoAlgBaseParaEntry  27 }


	macDownlinkMuMiMoMcsBackoff19		 OBJECT-TYPE
		SYNTAX					 Integer32( 0 .. 6 )
		MAX-ACCESS			 read-create
		STATUS					 current
		DESCRIPTION			 " -- "
		::=  { macDownMuMiMoAlgBaseParaEntry  28 }


	macDownlinkMuMiMoMcsBackoff20		 OBJECT-TYPE
		SYNTAX					 Integer32( 0 .. 6 )
		MAX-ACCESS			 read-create
		STATUS					 current
		DESCRIPTION			 " -- "
		::=  { macDownMuMiMoAlgBaseParaEntry  29 }


	macDownlinkMuMiMoMcsBackoff21		 OBJECT-TYPE
		SYNTAX					 Integer32( 0 .. 6 )
		MAX-ACCESS			 read-create
		STATUS					 current
		DESCRIPTION			 " -- "
		::=  { macDownMuMiMoAlgBaseParaEntry  30 }


	macDownlinkMuMiMoMcsBackoff22		 OBJECT-TYPE
		SYNTAX					 Integer32( 0 .. 6 )
		MAX-ACCESS			 read-create
		STATUS					 current
		DESCRIPTION			 " -- "
		::=  { macDownMuMiMoAlgBaseParaEntry  31 }


	macDownlinkMuMiMoMcsBackoff23		 OBJECT-TYPE
		SYNTAX					 Integer32( 0 .. 6 )
		MAX-ACCESS			 read-create
		STATUS					 current
		DESCRIPTION			 " -- "
		::=  { macDownMuMiMoAlgBaseParaEntry  32 }


	macDownlinkMuMiMoMcsBackoff24		 OBJECT-TYPE
		SYNTAX					 Integer32( 0 .. 6 )
		MAX-ACCESS			 read-create
		STATUS					 current
		DESCRIPTION			 " -- "
		::=  { macDownMuMiMoAlgBaseParaEntry  33 }


	macDownlinkMuMiMoMcsBackoff25		 OBJECT-TYPE
		SYNTAX					 Integer32( 0 .. 6 )
		MAX-ACCESS			 read-create
		STATUS					 current
		DESCRIPTION			 " -- "
		::=  { macDownMuMiMoAlgBaseParaEntry  34 }


	macDownlinkMuMiMoMcsBackoff26		 OBJECT-TYPE
		SYNTAX					 Integer32( 0 .. 6 )
		MAX-ACCESS			 read-create
		STATUS					 current
		DESCRIPTION			 " -- "
		::=  { macDownMuMiMoAlgBaseParaEntry  35 }


	macDownlinkMuMiMoMcsBackoff27		 OBJECT-TYPE
		SYNTAX					 Integer32( 0 .. 6 )
		MAX-ACCESS			 read-create
		STATUS					 current
		DESCRIPTION			 " -- "
		::=  { macDownMuMiMoAlgBaseParaEntry  36 }


	macUpMuMiMoAlgBaseParaTable		 OBJECT-TYPE
		SYNTAX					 SEQUENCE  OF	 MacUpMuMiMoAlgBaseParaEntry
		MAX-ACCESS			 not-accessible
		STATUS					 current
		DESCRIPTION			 " -- "
		::=  { macAlgorithmNode  4 }


	macUpMuMiMoAlgBaseParaEntry		 OBJECT-TYPE
		SYNTAX					 MacUpMuMiMoAlgBaseParaEntry
		MAX-ACCESS			 not-accessible
		STATUS					 current
		DESCRIPTION			 " -- "
		INDEX						{ macUpMuMiMoAlgorithmLcId }
		::=  { macUpMuMiMoAlgBaseParaTable  1 }


	MacUpMuMiMoAlgBaseParaEntry		 ::=  SEQUENCE {
		macUpMuMiMoAlgorithmLcId					Integer32,
		macUpMuMiMoRowStatus					RowStatus,
		macUpMuMiMoPairDeltaDOAThr					Integer32,
		macUpMuMiMoPairSNRThr					Integer32,
		macUpMuMiMoPairDeltaRecPwrThr					Integer32,
		macUpMuMiMoMuMimoBackSnr					Integer32,
		macUpMuMiMoMcsBackOff0					Integer32,
		macUpMuMiMoMcsBackOff1					Integer32,
		macUpMuMiMoMcsBackOff2					Integer32,
		macUpMuMiMoMcsBackOff3					Integer32,
		macUpMuMiMoMcsBackOff4					Integer32,
		macUpMuMiMoMcsBackOff5					Integer32,
		macUpMuMiMoMcsBackOff6					Integer32,
		macUpMuMiMoMcsBackOff7					Integer32,
		macUpMuMiMoMcsBackOff8					Integer32,
		macUpMuMiMoMcsBackOff9					Integer32,
		macUpMuMiMoMcsBackOff10					Integer32,
		macUpMuMiMoMcsBackOff11					Integer32,
		macUpMuMiMoMcsBackOff12					Integer32,
		macUpMuMiMoMcsBackOff13					Integer32,
		macUpMuMiMoMcsBackOff14					Integer32,
		macUpMuMiMoMcsBackOff15					Integer32,
		macUpMuMiMoMcsBackOff16					Integer32,
		macUpMuMiMoMcsBackOff17					Integer32,
		macUpMuMiMoMcsBackOff18					Integer32,
		macUpMuMiMoMcsBackOff19					Integer32,
		macUpMuMiMoMcsBackOff20					Integer32,
		macUpMuMiMoMcsBackOff21					Integer32,
		macUpMuMiMoMcsBackOff22					Integer32,
		macUpMuMiMoMcsBackOff23					Integer32,
		macUpMuMiMoMcsBackOff24					Integer32,
		macUpMuMiMoMcsBackOff25					Integer32,
		macUpMuMiMoMcsBackOff26					Integer32,
		macUpMuMiMoMcsBackOff27					Integer32,
		macUpMuMiMoMcsBackOff28					Integer32,
		macUpMuMimoPairPrbThr					Integer32
		}


	macUpMuMiMoAlgorithmLcId		 OBJECT-TYPE
		SYNTAX					 Integer32( 0 .. 23 )
		MAX-ACCESS			 not-accessible
		STATUS					 current
		DESCRIPTION			 " -- "
		::=  { macUpMuMiMoAlgBaseParaEntry  1 }


	macUpMuMiMoRowStatus		 OBJECT-TYPE
		SYNTAX					 RowStatus
		MAX-ACCESS			 read-create
		STATUS					 current
		DESCRIPTION			 " -- "
		::=  { macUpMuMiMoAlgBaseParaEntry  2 }


	macUpMuMiMoPairDeltaDOAThr		 OBJECT-TYPE
		SYNTAX					 Integer32( 0 .. 180 )
		MAX-ACCESS			 read-create
		STATUS					 current
		DESCRIPTION			 " -- "
		::=  { macUpMuMiMoAlgBaseParaEntry  3 }


	macUpMuMiMoPairSNRThr		 OBJECT-TYPE
		SYNTAX					 Integer32( 0 .. 500 )
		MAX-ACCESS			 read-create
		STATUS					 current
		DESCRIPTION			 " -- "
		::=  { macUpMuMiMoAlgBaseParaEntry  4 }


	macUpMuMiMoPairDeltaRecPwrThr		 OBJECT-TYPE
		SYNTAX					 Integer32( 0 .. 500 )
		MAX-ACCESS			 read-create
		STATUS					 current
		DESCRIPTION			 " -- "
		::=  { macUpMuMiMoAlgBaseParaEntry  5 }


	macUpMuMiMoMuMimoBackSnr		 OBJECT-TYPE
		SYNTAX					 Integer32( 0 .. 300 )
		MAX-ACCESS			 read-create
		STATUS					 current
		DESCRIPTION			 " -- "
		::=  { macUpMuMiMoAlgBaseParaEntry  6 }


	macUpMuMiMoMcsBackOff0		 OBJECT-TYPE
		SYNTAX					 Integer32( 0 .. 10 )
		MAX-ACCESS			 read-create
		STATUS					 current
		DESCRIPTION			 " -- "
		::=  { macUpMuMiMoAlgBaseParaEntry  7 }


	macUpMuMiMoMcsBackOff1		 OBJECT-TYPE
		SYNTAX					 Integer32( 0 .. 10 )
		MAX-ACCESS			 read-create
		STATUS					 current
		DESCRIPTION			 " -- "
		::=  { macUpMuMiMoAlgBaseParaEntry  8 }


	macUpMuMiMoMcsBackOff2		 OBJECT-TYPE
		SYNTAX					 Integer32( 0 .. 10 )
		MAX-ACCESS			 read-create
		STATUS					 current
		DESCRIPTION			 " -- "
		::=  { macUpMuMiMoAlgBaseParaEntry  9 }


	macUpMuMiMoMcsBackOff3		 OBJECT-TYPE
		SYNTAX					 Integer32( 0 .. 10 )
		MAX-ACCESS			 read-create
		STATUS					 current
		DESCRIPTION			 " -- "
		::=  { macUpMuMiMoAlgBaseParaEntry  10 }


	macUpMuMiMoMcsBackOff4		 OBJECT-TYPE
		SYNTAX					 Integer32( 0 .. 10 )
		MAX-ACCESS			 read-create
		STATUS					 current
		DESCRIPTION			 " -- "
		::=  { macUpMuMiMoAlgBaseParaEntry  11 }


	macUpMuMiMoMcsBackOff5		 OBJECT-TYPE
		SYNTAX					 Integer32( 0 .. 10 )
		MAX-ACCESS			 read-create
		STATUS					 current
		DESCRIPTION			 " -- "
		::=  { macUpMuMiMoAlgBaseParaEntry  12 }


	macUpMuMiMoMcsBackOff6		 OBJECT-TYPE
		SYNTAX					 Integer32( 0 .. 10 )
		MAX-ACCESS			 read-create
		STATUS					 current
		DESCRIPTION			 " -- "
		::=  { macUpMuMiMoAlgBaseParaEntry  13 }


	macUpMuMiMoMcsBackOff7		 OBJECT-TYPE
		SYNTAX					 Integer32( 0 .. 10 )
		MAX-ACCESS			 read-create
		STATUS					 current
		DESCRIPTION			 " -- "
		::=  { macUpMuMiMoAlgBaseParaEntry  14 }


	macUpMuMiMoMcsBackOff8		 OBJECT-TYPE
		SYNTAX					 Integer32( 0 .. 10 )
		MAX-ACCESS			 read-create
		STATUS					 current
		DESCRIPTION			 " -- "
		::=  { macUpMuMiMoAlgBaseParaEntry  15 }


	macUpMuMiMoMcsBackOff9		 OBJECT-TYPE
		SYNTAX					 Integer32( 0 .. 10 )
		MAX-ACCESS			 read-create
		STATUS					 current
		DESCRIPTION			 " -- "
		::=  { macUpMuMiMoAlgBaseParaEntry  16 }


	macUpMuMiMoMcsBackOff10		 OBJECT-TYPE
		SYNTAX					 Integer32( 0 .. 10 )
		MAX-ACCESS			 read-create
		STATUS					 current
		DESCRIPTION			 " -- "
		::=  { macUpMuMiMoAlgBaseParaEntry  17 }


	macUpMuMiMoMcsBackOff11		 OBJECT-TYPE
		SYNTAX					 Integer32( 0 .. 10 )
		MAX-ACCESS			 read-create
		STATUS					 current
		DESCRIPTION			 " -- "
		::=  { macUpMuMiMoAlgBaseParaEntry  18 }


	macUpMuMiMoMcsBackOff12		 OBJECT-TYPE
		SYNTAX					 Integer32( 0 .. 10 )
		MAX-ACCESS			 read-create
		STATUS					 current
		DESCRIPTION			 " -- "
		::=  { macUpMuMiMoAlgBaseParaEntry  19 }


	macUpMuMiMoMcsBackOff13		 OBJECT-TYPE
		SYNTAX					 Integer32( 0 .. 10 )
		MAX-ACCESS			 read-create
		STATUS					 current
		DESCRIPTION			 " -- "
		::=  { macUpMuMiMoAlgBaseParaEntry  20 }


	macUpMuMiMoMcsBackOff14		 OBJECT-TYPE
		SYNTAX					 Integer32( 0 .. 10 )
		MAX-ACCESS			 read-create
		STATUS					 current
		DESCRIPTION			 " -- "
		::=  { macUpMuMiMoAlgBaseParaEntry  21 }


	macUpMuMiMoMcsBackOff15		 OBJECT-TYPE
		SYNTAX					 Integer32( 0 .. 10 )
		MAX-ACCESS			 read-create
		STATUS					 current
		DESCRIPTION			 " -- "
		::=  { macUpMuMiMoAlgBaseParaEntry  22 }


	macUpMuMiMoMcsBackOff16		 OBJECT-TYPE
		SYNTAX					 Integer32( 0 .. 10 )
		MAX-ACCESS			 read-create
		STATUS					 current
		DESCRIPTION			 " -- "
		::=  { macUpMuMiMoAlgBaseParaEntry  23 }


	macUpMuMiMoMcsBackOff17		 OBJECT-TYPE
		SYNTAX					 Integer32( 0 .. 10 )
		MAX-ACCESS			 read-create
		STATUS					 current
		DESCRIPTION			 " -- "
		::=  { macUpMuMiMoAlgBaseParaEntry  24 }


	macUpMuMiMoMcsBackOff18		 OBJECT-TYPE
		SYNTAX					 Integer32( 0 .. 10 )
		MAX-ACCESS			 read-create
		STATUS					 current
		DESCRIPTION			 " -- "
		::=  { macUpMuMiMoAlgBaseParaEntry  25 }


	macUpMuMiMoMcsBackOff19		 OBJECT-TYPE
		SYNTAX					 Integer32( 0 .. 10 )
		MAX-ACCESS			 read-create
		STATUS					 current
		DESCRIPTION			 " -- "
		::=  { macUpMuMiMoAlgBaseParaEntry  26 }


	macUpMuMiMoMcsBackOff20		 OBJECT-TYPE
		SYNTAX					 Integer32( 0 .. 10 )
		MAX-ACCESS			 read-create
		STATUS					 current
		DESCRIPTION			 " -- "
		::=  { macUpMuMiMoAlgBaseParaEntry  27 }


	macUpMuMiMoMcsBackOff21		 OBJECT-TYPE
		SYNTAX					 Integer32( 0 .. 10 )
		MAX-ACCESS			 read-create
		STATUS					 current
		DESCRIPTION			 " -- "
		::=  { macUpMuMiMoAlgBaseParaEntry  28 }


	macUpMuMiMoMcsBackOff22		 OBJECT-TYPE
		SYNTAX					 Integer32( 0 .. 10 )
		MAX-ACCESS			 read-create
		STATUS					 current
		DESCRIPTION			 " -- "
		::=  { macUpMuMiMoAlgBaseParaEntry  29 }


	macUpMuMiMoMcsBackOff23		 OBJECT-TYPE
		SYNTAX					 Integer32( 0 .. 10 )
		MAX-ACCESS			 read-create
		STATUS					 current
		DESCRIPTION			 " -- "
		::=  { macUpMuMiMoAlgBaseParaEntry  30 }


	macUpMuMiMoMcsBackOff24		 OBJECT-TYPE
		SYNTAX					 Integer32( 0 .. 10 )
		MAX-ACCESS			 read-create
		STATUS					 current
		DESCRIPTION			 " -- "
		::=  { macUpMuMiMoAlgBaseParaEntry  31 }


	macUpMuMiMoMcsBackOff25		 OBJECT-TYPE
		SYNTAX					 Integer32( 0 .. 10 )
		MAX-ACCESS			 read-create
		STATUS					 current
		DESCRIPTION			 " -- "
		::=  { macUpMuMiMoAlgBaseParaEntry  32 }


	macUpMuMiMoMcsBackOff26		 OBJECT-TYPE
		SYNTAX					 Integer32( 0 .. 10 )
		MAX-ACCESS			 read-create
		STATUS					 current
		DESCRIPTION			 " -- "
		::=  { macUpMuMiMoAlgBaseParaEntry  33 }


	macUpMuMiMoMcsBackOff27		 OBJECT-TYPE
		SYNTAX					 Integer32( 0 .. 10 )
		MAX-ACCESS			 read-create
		STATUS					 current
		DESCRIPTION			 " -- "
		::=  { macUpMuMiMoAlgBaseParaEntry  34 }


	macUpMuMiMoMcsBackOff28		 OBJECT-TYPE
		SYNTAX					 Integer32( 0 .. 10 )
		MAX-ACCESS			 read-create
		STATUS					 current
		DESCRIPTION			 " -- "
		::=  { macUpMuMiMoAlgBaseParaEntry  35 }


	macUpMuMimoPairPrbThr		 OBJECT-TYPE
		SYNTAX					 Integer32( 1 .. 100 )
		MAX-ACCESS			 read-create
		STATUS					 current
		DESCRIPTION			 " -- "
		::=  { macUpMuMiMoAlgBaseParaEntry  36 }


	videoActiveTable		 OBJECT-TYPE
		SYNTAX					 SEQUENCE  OF	 VideoActiveEntry
		MAX-ACCESS			 not-accessible
		STATUS					 current
		DESCRIPTION			 " -- "
		::=  { macAlgorithmNode  5 }


	videoActiveEntry		 OBJECT-TYPE
		SYNTAX					 VideoActiveEntry
		MAX-ACCESS			 not-accessible
		STATUS					 current
		DESCRIPTION			 " -- "
		INDEX						{ videoActiveLcId }
		::=  { videoActiveTable  1 }


	VideoActiveEntry		 ::=  SEQUENCE {
		videoActiveLcId					Integer32,
		videoActiveRowStatus					RowStatus,
		videoScheduleMode					Integer32,
		videoInitScheduleTime					Integer32,
		videoDlMAXPRBUsed					Integer32,
		videoDlOverMAXPRBUsed					Integer32,
		videoMinBRSwitch					INTEGER,
		videoMinBR					INTEGER,
		videoDlBucketSizeDuration					INTEGER,
		videoUlBoSwitch					INTEGER,
		videoUlPreschePriority					Integer32,
		videoUlBOSize					Integer32,
		videoUlPrescheTimeLimit					INTEGER
		}


	videoActiveLcId		 OBJECT-TYPE
		SYNTAX					 Integer32( 0 .. 23 )
		MAX-ACCESS			 not-accessible
		STATUS					 current
		DESCRIPTION			 " -- "
		::=  { videoActiveEntry  1 }


	videoActiveRowStatus		 OBJECT-TYPE
		SYNTAX					 RowStatus
		MAX-ACCESS			 read-create
		STATUS					 current
		DESCRIPTION			 " -- "
		::=  { videoActiveEntry  2 }


	videoScheduleMode		 OBJECT-TYPE
		SYNTAX					 Integer32( 0 .. 1 )
		MAX-ACCESS			 read-create
		STATUS					 current
		DESCRIPTION			 " -- "
		::=  { videoActiveEntry  3 }


	videoInitScheduleTime		 OBJECT-TYPE
		SYNTAX					 Integer32( 1 .. 100 )
		MAX-ACCESS			 read-create
		STATUS					 current
		DESCRIPTION			 " -- "
		::=  { videoActiveEntry  4 }


	videoDlMAXPRBUsed		 OBJECT-TYPE
		SYNTAX					 Integer32( 1 .. 100 )
		MAX-ACCESS			 read-create
		STATUS					 current
		DESCRIPTION			 " -- "
		::=  { videoActiveEntry  5 }


	videoDlOverMAXPRBUsed		 OBJECT-TYPE
		SYNTAX					 Integer32( 1 .. 100 )
		MAX-ACCESS			 read-create
		STATUS					 current
		DESCRIPTION			 " -- "
		::=  { videoActiveEntry  6 }


	videoMinBRSwitch		 OBJECT-TYPE
		SYNTAX					 INTEGER{ off(0),on(1)  }
		MAX-ACCESS			 read-create
		STATUS					 current
		DESCRIPTION			 " -- "
		::=  { videoActiveEntry  7 }


	videoMinBR		 OBJECT-TYPE
		SYNTAX					 INTEGER{ kB0(0),kB8(1),kB16(2),kB32(3),kB64(4),kB128(5),kB256(6),infinity(7),kB640(8),kB512(9),kB768(10),kB896(11),kB1024(12),kB1152(13),kB1280(14),kB1408(15),kB1536(16),kB1664(17),kB1792(18),kB1920(19),kB2048(20),kB2176(21),kB2304(22),kB2432(23),kB2560(24),kB5120(25)  }
		MAX-ACCESS			 read-create
		STATUS					 current
		DESCRIPTION			 " -- "
		::=  { videoActiveEntry  8 }


	videoDlBucketSizeDuration		 OBJECT-TYPE
		SYNTAX					 INTEGER{ bsdMs5(0),bsdMs50(1),bsdMs100(2),bsdMs250(3)  }
		MAX-ACCESS			 read-create
		STATUS					 current
		DESCRIPTION			 " -- "
		::=  { videoActiveEntry  9 }


	videoUlBoSwitch		 OBJECT-TYPE
		SYNTAX					 INTEGER{ off(0),on(1)  }
		MAX-ACCESS			 read-create
		STATUS					 current
		DESCRIPTION			 " -- "
		::=  { videoActiveEntry  10 }


	videoUlPreschePriority		 OBJECT-TYPE
		SYNTAX					 Integer32( 0 .. 1 )
		MAX-ACCESS			 read-create
		STATUS					 current
		DESCRIPTION			 " -- "
		::=  { videoActiveEntry  11 }


	videoUlBOSize		 OBJECT-TYPE
		SYNTAX					 Integer32( 0 .. 63 )
		MAX-ACCESS			 read-create
		STATUS					 current
		DESCRIPTION			 " -- "
		::=  { videoActiveEntry  12 }


	videoUlPrescheTimeLimit		 OBJECT-TYPE
		SYNTAX					 INTEGER{ ms100(0),ms200(1),ms500(2),s1(3),s2(4),s5(5),s10(6),infinity(7),ms10(8),ms20(9),ms40(10),ms50(11),ms80(12)  }
		MAX-ACCESS			 read-create
		STATUS					 current
		DESCRIPTION			 " -- "
		::=  { videoActiveEntry  13 }


	pdcpVideoParamTable		 OBJECT-TYPE
		SYNTAX					 SEQUENCE  OF	 PdcpVideoParamEntry
		MAX-ACCESS			 not-accessible
		STATUS					 current
		DESCRIPTION			 " -- "
		::=  { macAlgorithmNode  6 }


	pdcpVideoParamEntry		 OBJECT-TYPE
		SYNTAX					 PdcpVideoParamEntry
		MAX-ACCESS			 not-accessible
		STATUS					 current
		DESCRIPTION			 " -- "
		INDEX						{ pdcpVideoParamLcId }
		::=  { pdcpVideoParamTable  1 }


	PdcpVideoParamEntry		 ::=  SEQUENCE {
		pdcpVideoParamLcId					Integer32,
		pdcpVideoParamRowStatus					RowStatus,
		pdcpVideoJudgeSche					Integer32,
		pdcpVideoCpuMaxThreshold					Integer32,
		pdcpVideoPkgPeriodNum					Integer32,
		pdcpVideoPkgPeriodT					INTEGER,
		pdcpVideoLargePkgNumTH					Integer32,
		pdcpVideoLargePkgTH					Integer32,
		pdcpVideoUtcpkgMinSize					Integer32,
		pdcpVideoUtcpkgMaxSize					Integer32,
		pdcpVideoRBMaxNum					Integer32,
		pdcpVideoQQVideoActive					INTEGER,
		pdcpVideoIQiYiVideoActive					INTEGER,
		pdcpVideoYouKuVideoActive					INTEGER,
		pdcpVideoLeTVVideoActive					INTEGER,
		pdcpVideoMiGuVideoActive					INTEGER,
		pdcpVideoKuaiShouVideoActive					INTEGER,
		pdcpVideoMgTVVideoActive					INTEGER,
		pdcpVideoReserver1VideoActive					INTEGER,
		pdcpVideoReserver2VideoActive					INTEGER,
		pdcpVideoReserver3VideoActive					INTEGER,
		pdcpVideoReserver4VideoActive					INTEGER,
		pdcpVideoReserver5VideoActive					INTEGER,
		pdcpVideoReserver6VideoActive					INTEGER,
		pdcpVideoReserver7VideoActive					INTEGER,
		pdcpVideoReserver8VideoActive					INTEGER,
		pdcpVideoReserver9VideoActive					INTEGER,
		pdcpVideoReserver10VideoActive					INTEGER,
		pdcpVideoReserver11VideoActive					INTEGER,
		pdcpVideoReserver12VideoActive					INTEGER,
		pdcpVideoReserver13VideoActive					INTEGER,
		pdcpVideoReserver14VideoActive					INTEGER,
		pdcpVideoReserver15VideoActive					INTEGER,
		pdcpVideoReserver16VideoActive					INTEGER,
		pdcpVideoReserver17VideoActive					INTEGER,
		pdcpVideoReserver18VideoActive					INTEGER,
		pdcpVideoReserver19VideoActive					INTEGER,
		pdcpVideoReserver20VideoActive					INTEGER
		}


	pdcpVideoParamLcId		 OBJECT-TYPE
		SYNTAX					 Integer32( 0 .. 23 )
		MAX-ACCESS			 not-accessible
		STATUS					 current
		DESCRIPTION			 " -- "
		::=  { pdcpVideoParamEntry  1 }


	pdcpVideoParamRowStatus		 OBJECT-TYPE
		SYNTAX					 RowStatus
		MAX-ACCESS			 read-create
		STATUS					 current
		DESCRIPTION			 " -- "
		::=  { pdcpVideoParamEntry  2 }


	pdcpVideoJudgeSche		 OBJECT-TYPE
		SYNTAX					 Integer32( 0 .. 1 )
		MAX-ACCESS			 read-create
		STATUS					 current
		DESCRIPTION			 " -- "
		::=  { pdcpVideoParamEntry  3 }


	pdcpVideoCpuMaxThreshold		 OBJECT-TYPE
		SYNTAX					 Integer32( 0 .. 100 )
		MAX-ACCESS			 read-create
		STATUS					 current
		DESCRIPTION			 " -- "
		::=  { pdcpVideoParamEntry  4 }


	pdcpVideoPkgPeriodNum		 OBJECT-TYPE
		SYNTAX					 Integer32( 1 .. 100 )
		MAX-ACCESS			 read-create
		STATUS					 current
		DESCRIPTION			 " -- "
		::=  { pdcpVideoParamEntry  5 }


	pdcpVideoPkgPeriodT		 OBJECT-TYPE
		SYNTAX					 INTEGER{ ms100(0),ms200(1),ms500(2),ms1000(3),ms2000(4),ms5000(5)  }
		MAX-ACCESS			 read-create
		STATUS					 current
		DESCRIPTION			 " -- "
		::=  { pdcpVideoParamEntry  6 }


	pdcpVideoLargePkgNumTH		 OBJECT-TYPE
		SYNTAX					 Integer32( 1 .. 1000 )
		MAX-ACCESS			 read-create
		STATUS					 current
		DESCRIPTION			 " -- "
		::=  { pdcpVideoParamEntry  7 }


	pdcpVideoLargePkgTH		 OBJECT-TYPE
		SYNTAX					 Integer32( 800 .. 1500 )
		MAX-ACCESS			 read-create
		STATUS					 current
		DESCRIPTION			 " -- "
		::=  { pdcpVideoParamEntry  8 }


	pdcpVideoUtcpkgMinSize		 OBJECT-TYPE
		SYNTAX					 Integer32( 1 .. 1500 )
		MAX-ACCESS			 read-create
		STATUS					 current
		DESCRIPTION			 " -- "
		::=  { pdcpVideoParamEntry  9 }


	pdcpVideoUtcpkgMaxSize		 OBJECT-TYPE
		SYNTAX					 Integer32( 1 .. 1500 )
		MAX-ACCESS			 read-create
		STATUS					 current
		DESCRIPTION			 " -- "
		::=  { pdcpVideoParamEntry  10 }


	pdcpVideoRBMaxNum		 OBJECT-TYPE
		SYNTAX					 Integer32( 0 .. 50 )
		MAX-ACCESS			 read-create
		STATUS					 current
		DESCRIPTION			 " -- "
		::=  { pdcpVideoParamEntry  11 }


	pdcpVideoQQVideoActive		 OBJECT-TYPE
		SYNTAX					 INTEGER{ false(0),ture(1)  }
		MAX-ACCESS			 read-create
		STATUS					 current
		DESCRIPTION			 " -- "
		::=  { pdcpVideoParamEntry  12 }


	pdcpVideoIQiYiVideoActive		 OBJECT-TYPE
		SYNTAX					 INTEGER{ false(0),ture(1)  }
		MAX-ACCESS			 read-create
		STATUS					 current
		DESCRIPTION			 " -- "
		::=  { pdcpVideoParamEntry  13 }


	pdcpVideoYouKuVideoActive		 OBJECT-TYPE
		SYNTAX					 INTEGER{ false(0),ture(1)  }
		MAX-ACCESS			 read-create
		STATUS					 current
		DESCRIPTION			 " -- "
		::=  { pdcpVideoParamEntry  14 }


	pdcpVideoLeTVVideoActive		 OBJECT-TYPE
		SYNTAX					 INTEGER{ false(0),ture(1)  }
		MAX-ACCESS			 read-create
		STATUS					 current
		DESCRIPTION			 " -- "
		::=  { pdcpVideoParamEntry  15 }


	pdcpVideoMiGuVideoActive		 OBJECT-TYPE
		SYNTAX					 INTEGER{ false(0),ture(1)  }
		MAX-ACCESS			 read-create
		STATUS					 current
		DESCRIPTION			 " -- "
		::=  { pdcpVideoParamEntry  16 }


	pdcpVideoKuaiShouVideoActive		 OBJECT-TYPE
		SYNTAX					 INTEGER{ false(0),ture(1)  }
		MAX-ACCESS			 read-create
		STATUS					 current
		DESCRIPTION			 " -- "
		::=  { pdcpVideoParamEntry  17 }


	pdcpVideoMgTVVideoActive		 OBJECT-TYPE
		SYNTAX					 INTEGER{ false(0),ture(1)  }
		MAX-ACCESS			 read-create
		STATUS					 current
		DESCRIPTION			 " -- "
		::=  { pdcpVideoParamEntry  18 }


	pdcpVideoReserver1VideoActive		 OBJECT-TYPE
		SYNTAX					 INTEGER{ false(0),ture(1)  }
		MAX-ACCESS			 read-create
		STATUS					 current
		DESCRIPTION			 " -- "
		::=  { pdcpVideoParamEntry  19 }


	pdcpVideoReserver2VideoActive		 OBJECT-TYPE
		SYNTAX					 INTEGER{ false(0),ture(1)  }
		MAX-ACCESS			 read-create
		STATUS					 current
		DESCRIPTION			 " -- "
		::=  { pdcpVideoParamEntry  20 }


	pdcpVideoReserver3VideoActive		 OBJECT-TYPE
		SYNTAX					 INTEGER{ false(0),ture(1)  }
		MAX-ACCESS			 read-create
		STATUS					 current
		DESCRIPTION			 " -- "
		::=  { pdcpVideoParamEntry  21 }


	pdcpVideoReserver4VideoActive		 OBJECT-TYPE
		SYNTAX					 INTEGER{ false(0),ture(1)  }
		MAX-ACCESS			 read-create
		STATUS					 current
		DESCRIPTION			 " -- "
		::=  { pdcpVideoParamEntry  22 }


	pdcpVideoReserver5VideoActive		 OBJECT-TYPE
		SYNTAX					 INTEGER{ false(0),ture(1)  }
		MAX-ACCESS			 read-create
		STATUS					 current
		DESCRIPTION			 " -- "
		::=  { pdcpVideoParamEntry  23 }


	pdcpVideoReserver6VideoActive		 OBJECT-TYPE
		SYNTAX					 INTEGER{ false(0),ture(1)  }
		MAX-ACCESS			 read-create
		STATUS					 current
		DESCRIPTION			 " -- "
		::=  { pdcpVideoParamEntry  24 }


	pdcpVideoReserver7VideoActive		 OBJECT-TYPE
		SYNTAX					 INTEGER{ false(0),ture(1)  }
		MAX-ACCESS			 read-create
		STATUS					 current
		DESCRIPTION			 " -- "
		::=  { pdcpVideoParamEntry  25 }


	pdcpVideoReserver8VideoActive		 OBJECT-TYPE
		SYNTAX					 INTEGER{ false(0),ture(1)  }
		MAX-ACCESS			 read-create
		STATUS					 current
		DESCRIPTION			 " -- "
		::=  { pdcpVideoParamEntry  26 }


	pdcpVideoReserver9VideoActive		 OBJECT-TYPE
		SYNTAX					 INTEGER{ false(0),ture(1)  }
		MAX-ACCESS			 read-create
		STATUS					 current
		DESCRIPTION			 " -- "
		::=  { pdcpVideoParamEntry  27 }


	pdcpVideoReserver10VideoActive		 OBJECT-TYPE
		SYNTAX					 INTEGER{ false(0),ture(1)  }
		MAX-ACCESS			 read-create
		STATUS					 current
		DESCRIPTION			 " -- "
		::=  { pdcpVideoParamEntry  28 }


	pdcpVideoReserver11VideoActive		 OBJECT-TYPE
		SYNTAX					 INTEGER{ false(0),ture(1)  }
		MAX-ACCESS			 read-create
		STATUS					 current
		DESCRIPTION			 " -- "
		::=  { pdcpVideoParamEntry  29 }


	pdcpVideoReserver12VideoActive		 OBJECT-TYPE
		SYNTAX					 INTEGER{ false(0),ture(1)  }
		MAX-ACCESS			 read-create
		STATUS					 current
		DESCRIPTION			 " -- "
		::=  { pdcpVideoParamEntry  30 }


	pdcpVideoReserver13VideoActive		 OBJECT-TYPE
		SYNTAX					 INTEGER{ false(0),ture(1)  }
		MAX-ACCESS			 read-create
		STATUS					 current
		DESCRIPTION			 " -- "
		::=  { pdcpVideoParamEntry  31 }


	pdcpVideoReserver14VideoActive		 OBJECT-TYPE
		SYNTAX					 INTEGER{ false(0),ture(1)  }
		MAX-ACCESS			 read-create
		STATUS					 current
		DESCRIPTION			 " -- "
		::=  { pdcpVideoParamEntry  32 }


	pdcpVideoReserver15VideoActive		 OBJECT-TYPE
		SYNTAX					 INTEGER{ false(0),ture(1)  }
		MAX-ACCESS			 read-create
		STATUS					 current
		DESCRIPTION			 " -- "
		::=  { pdcpVideoParamEntry  33 }


	pdcpVideoReserver16VideoActive		 OBJECT-TYPE
		SYNTAX					 INTEGER{ false(0),ture(1)  }
		MAX-ACCESS			 read-create
		STATUS					 current
		DESCRIPTION			 " -- "
		::=  { pdcpVideoParamEntry  34 }


	pdcpVideoReserver17VideoActive		 OBJECT-TYPE
		SYNTAX					 INTEGER{ false(0),ture(1)  }
		MAX-ACCESS			 read-create
		STATUS					 current
		DESCRIPTION			 " -- "
		::=  { pdcpVideoParamEntry  35 }


	pdcpVideoReserver18VideoActive		 OBJECT-TYPE
		SYNTAX					 INTEGER{ false(0),ture(1)  }
		MAX-ACCESS			 read-create
		STATUS					 current
		DESCRIPTION			 " -- "
		::=  { pdcpVideoParamEntry  36 }


	pdcpVideoReserver19VideoActive		 OBJECT-TYPE
		SYNTAX					 INTEGER{ false(0),ture(1)  }
		MAX-ACCESS			 read-create
		STATUS					 current
		DESCRIPTION			 " -- "
		::=  { pdcpVideoParamEntry  37 }


	pdcpVideoReserver20VideoActive		 OBJECT-TYPE
		SYNTAX					 INTEGER{ false(0),ture(1)  }
		MAX-ACCESS			 read-create
		STATUS					 current
		DESCRIPTION			 " -- "
		::=  { pdcpVideoParamEntry  38 }


	pdcpVideoKeyWordsTable		 OBJECT-TYPE
		SYNTAX					 SEQUENCE  OF	 PdcpVideoKeyWordsEntry
		MAX-ACCESS			 not-accessible
		STATUS					 current
		DESCRIPTION			 " -- "
		::=  { macAlgorithmNode  7 }


	pdcpVideoKeyWordsEntry		 OBJECT-TYPE
		SYNTAX					 PdcpVideoKeyWordsEntry
		MAX-ACCESS			 not-accessible
		STATUS					 current
		DESCRIPTION			 " -- "
		INDEX						{ pdcpVideoKeyWordsLcId,pdcpVideoKeyWordsCfgId }
		::=  { pdcpVideoKeyWordsTable  1 }


	PdcpVideoKeyWordsEntry		 ::=  SEQUENCE {
		pdcpVideoKeyWordsLcId					Integer32,
		pdcpVideoKeyWordsCfgId					Integer32,
		pdcpVideoKeyWordsRowStatus					RowStatus,
		pdcpVideoKeyWordsVendor					INTEGER,
		pdcpVideoKeyWords					DisplayString,
		pdcpVideoKeyWordsOffset					Integer32,
		pdcpVideoKeyWordsLength					Integer32
		}


	pdcpVideoKeyWordsLcId		 OBJECT-TYPE
		SYNTAX					 Integer32( 0 .. 23 )
		MAX-ACCESS			 not-accessible
		STATUS					 current
		DESCRIPTION			 " -- "
		::=  { pdcpVideoKeyWordsEntry  1 }


	pdcpVideoKeyWordsCfgId		 OBJECT-TYPE
		SYNTAX					 Integer32( 0 .. 63 )
		MAX-ACCESS			 not-accessible
		STATUS					 current
		DESCRIPTION			 " -- "
		::=  { pdcpVideoKeyWordsEntry  2 }


	pdcpVideoKeyWordsRowStatus		 OBJECT-TYPE
		SYNTAX					 RowStatus
		MAX-ACCESS			 read-create
		STATUS					 current
		DESCRIPTION			 " -- "
		::=  { pdcpVideoKeyWordsEntry  3 }


	pdcpVideoKeyWordsVendor		 OBJECT-TYPE
		SYNTAX					 INTEGER{ vendor0(0),vendor1(1),vendor2(2),vendor3(3),vendor4(4),vendor5(5),vendor6(6),vendor7(7),vendor8(8),vendor9(9),vendor10(10),vendor11(11),vendor12(12),vendor13(13),vendor14(14),vendor15(15),vendor16(16),vendor17(17),vendor18(18),vendor19(19),vendor20(20),vendor21(21),vendor22(22),vendor23(23),vendor24(24),vendor25(25),vendor26(26)  }
		MAX-ACCESS			 read-create
		STATUS					 current
		DESCRIPTION			 " -- "
		::=  { pdcpVideoKeyWordsEntry  4 }


	pdcpVideoKeyWords		 OBJECT-TYPE
		SYNTAX					 DisplayString( SIZE ( 1 .. 10 ) )
		MAX-ACCESS			 read-create
		STATUS					 current
		DESCRIPTION			 " -- "
		::=  { pdcpVideoKeyWordsEntry  5 }


	pdcpVideoKeyWordsOffset		 OBJECT-TYPE
		SYNTAX					 Integer32( 0 .. 255 )
		MAX-ACCESS			 read-create
		STATUS					 current
		DESCRIPTION			 " -- "
		::=  { pdcpVideoKeyWordsEntry  6 }


	pdcpVideoKeyWordsLength		 OBJECT-TYPE
		SYNTAX					 Integer32( 0 .. 10 )
		MAX-ACCESS			 read-create
		STATUS					 current
		DESCRIPTION			 " -- "
		::=  { pdcpVideoKeyWordsEntry  7 }


	macSwitchNode		 OBJECT IDENTIFIER
		::=  { schedule  2 }


	macSwitchInfoTable		 OBJECT-TYPE
		SYNTAX					 SEQUENCE  OF	 MacSwitchInfoEntry
		MAX-ACCESS			 not-accessible
		STATUS					 current
		DESCRIPTION			 " -- "
		::=  { macSwitchNode  1 }


	macSwitchInfoEntry		 OBJECT-TYPE
		SYNTAX					 MacSwitchInfoEntry
		MAX-ACCESS			 not-accessible
		STATUS					 current
		DESCRIPTION			 " -- "
		INDEX						{ macSwitchInfoLcId }
		::=  { macSwitchInfoTable  1 }


	MacSwitchInfoEntry		 ::=  SEQUENCE {
		macSwitchInfoLcId					Integer32,
		macSwitchInfoRowStatus					RowStatus,
		macSwitchInfoUeInactiveSwitch					INTEGER,
		macSwitchInfoUeInactivePeriod					Integer32,
		macSwitchInfoDlHoppingFlag					INTEGER,
		macSwitchInfoDlHopGap					INTEGER,
		macSwitchInfoUlHoppingFlag					INTEGER,
		macSwitchInfoUlHoppingType					INTEGER,
		macSwitchInfoUlMuMIMOSwitch					INTEGER,
		macSwitchInfoUlFreqSelectScheduleSwitch					INTEGER,
		macSwitchInfoTm8MuSuMimoSwitch					INTEGER,
		macSwitchInfoCellCombinedUlSwitch					INTEGER,
		macSwitchInfoCellCombinedDlSwitch					INTEGER,
		macSwitchInfoDlFsSwitch					INTEGER,
		macSwitchInfoCclrSwitch					INTEGER,
		macSwitchInfoCclrPercent					Integer32,
		macSwitchInfoNewRbPriorityScheTime					Integer32,
		macSwitchInfoCellCombineAntOffset					Integer32,
		macSwitchInfoSignalConMsg2BISwitch					INTEGER,
		macSwitchInfoSignalConTimerPeriod					Integer32,
		macSwitchInfoSignalConThr					Integer32,
		macSwitchInfoSignalConBIValue					Integer32,
		macSwitchInfoReserveTimeForMsg4					Integer32,
		macSwitchInfoRlcUeInactiveSwitch					INTEGER,
		macSwitchInfoCaUeNumLimit					Integer32,
		macSwitchInfoVoIPUeInactiveProhibitSwitch					INTEGER,
		macSwitchInfoVoIPUeInactivePeriod					Integer32,
		macSwitchInfoTrafficeInactiveTimer					Integer32,
		macSwitchInfoHighSpeedUeInactivePeriod					Integer32,
		macSwitchInfoextendRrcReestablishSwitch					INTEGER,
		macSwitchInfoReserveTimeForContentReslut					Integer32,
		macSwitchInfoUlCceReserveFlag					INTEGER,
		macSwitchInfoUlCceRatio					Integer32,
		macSwitchInfoMcsDiffFlag					INTEGER,
		macSwitchInfoMcsDiffValue					Unsigned32,
		macSwitchInfoL2UpAdaptSwitch					Unsigned32,
		macSwitchInfoUeInactivePeriodOffset					Integer32,
		macSwitchInfoDlEdgeUserMcsTh					Integer32,
		macSwitchInfoCceOffset					Integer32,
		macSwitchInfoCceOffsetRatioCfi1					Integer32,
		macSwitchInfoCceOffsetRatioCfi2					Integer32
		}


	macSwitchInfoLcId		 OBJECT-TYPE
		SYNTAX					 Integer32( 0 .. 23 )
		MAX-ACCESS			 not-accessible
		STATUS					 current
		DESCRIPTION			 " -- "
		::=  { macSwitchInfoEntry  1 }


	macSwitchInfoRowStatus		 OBJECT-TYPE
		SYNTAX					 RowStatus
		MAX-ACCESS			 read-create
		STATUS					 current
		DESCRIPTION			 " -- "
		::=  { macSwitchInfoEntry  2 }


	macSwitchInfoUeInactiveSwitch		 OBJECT-TYPE
		SYNTAX					 INTEGER{ off(0),on(1)  }
		MAX-ACCESS			 read-create
		STATUS					 current
		DESCRIPTION			 " -- "
		::=  { macSwitchInfoEntry  3 }


	macSwitchInfoUeInactivePeriod		 OBJECT-TYPE
		SYNTAX					 Integer32( 0 .. 65535 )
		MAX-ACCESS			 read-create
		STATUS					 current
		DESCRIPTION			 " -- "
		::=  { macSwitchInfoEntry  4 }


	macSwitchInfoDlHoppingFlag		 OBJECT-TYPE
		SYNTAX					 INTEGER{ off(0),on(1)  }
		MAX-ACCESS			 read-create
		STATUS					 current
		DESCRIPTION			 " -- "
		::=  { macSwitchInfoEntry  5 }


	macSwitchInfoDlHopGap		 OBJECT-TYPE
		SYNTAX					 INTEGER{ adaptive(-1),gap1(0),gap2(1)  }
		MAX-ACCESS			 read-create
		STATUS					 current
		DESCRIPTION			 " -- "
		::=  { macSwitchInfoEntry  6 }


	macSwitchInfoUlHoppingFlag		 OBJECT-TYPE
		SYNTAX					 INTEGER{ off(0),on(1)  }
		MAX-ACCESS			 read-create
		STATUS					 current
		DESCRIPTION			 " -- "
		::=  { macSwitchInfoEntry  9 }


	macSwitchInfoUlHoppingType		 OBJECT-TYPE
		SYNTAX					 INTEGER{ adaptive(-1),hopbit0(0),hopbit1(1),hopbit2(2),hopbit11(3)  }
		MAX-ACCESS			 read-create
		STATUS					 current
		DESCRIPTION			 " -- "
		::=  { macSwitchInfoEntry  10 }


	macSwitchInfoUlMuMIMOSwitch		 OBJECT-TYPE
		SYNTAX					 INTEGER{ off(0),on(1)  }
		MAX-ACCESS			 read-create
		STATUS					 current
		DESCRIPTION			 " -- "
		::=  { macSwitchInfoEntry  11 }


	macSwitchInfoUlFreqSelectScheduleSwitch		 OBJECT-TYPE
		SYNTAX					 INTEGER{ off(0),on(1)  }
		MAX-ACCESS			 read-create
		STATUS					 current
		DESCRIPTION			 " -- "
		::=  { macSwitchInfoEntry  12 }


	macSwitchInfoTm8MuSuMimoSwitch		 OBJECT-TYPE
		SYNTAX					 INTEGER{ mumimo(0),sumimo(1),forbidtm8(2),sumuadapter(3)  }
		MAX-ACCESS			 read-create
		STATUS					 current
		DESCRIPTION			 " -- "
		::=  { macSwitchInfoEntry  13 }


	macSwitchInfoCellCombinedUlSwitch		 OBJECT-TYPE
		SYNTAX					 INTEGER{ off(0),on(1)  }
		MAX-ACCESS			 read-create
		STATUS					 current
		DESCRIPTION			 " -- "
		::=  { macSwitchInfoEntry  14 }


	macSwitchInfoCellCombinedDlSwitch		 OBJECT-TYPE
		SYNTAX					 INTEGER{ off(0),on(1)  }
		MAX-ACCESS			 read-create
		STATUS					 current
		DESCRIPTION			 " -- "
		::=  { macSwitchInfoEntry  15 }


	macSwitchInfoDlFsSwitch		 OBJECT-TYPE
		SYNTAX					 INTEGER{ off(0),srson(1),cqion(2)  }
		MAX-ACCESS			 read-create
		STATUS					 current
		DESCRIPTION			 " -- "
		::=  { macSwitchInfoEntry  16 }


	macSwitchInfoCclrSwitch		 OBJECT-TYPE
		SYNTAX					 INTEGER{ off(0),on(1)  }
		MAX-ACCESS			 read-create
		STATUS					 current
		DESCRIPTION			 " -- "
		::=  { macSwitchInfoEntry  17 }


	macSwitchInfoCclrPercent		 OBJECT-TYPE
		SYNTAX					 Integer32( 10 .. 100 )
		MAX-ACCESS			 read-create
		STATUS					 current
		DESCRIPTION			 " -- "
		::=  { macSwitchInfoEntry  18 }


	macSwitchInfoNewRbPriorityScheTime		 OBJECT-TYPE
		SYNTAX					 Integer32( 0 .. 120 )
		MAX-ACCESS			 read-create
		STATUS					 current
		DESCRIPTION			 " -- "
		::=  { macSwitchInfoEntry  19 }


	macSwitchInfoCellCombineAntOffset		 OBJECT-TYPE
		SYNTAX					 Integer32( 0 .. 9 )
		MAX-ACCESS			 read-create
		STATUS					 current
		DESCRIPTION			 " -- "
		::=  { macSwitchInfoEntry  20 }


	macSwitchInfoSignalConMsg2BISwitch		 OBJECT-TYPE
		SYNTAX					 INTEGER{ off(0),on(1)  }
		MAX-ACCESS			 read-create
		STATUS					 current
		DESCRIPTION			 " -- "
		::=  { macSwitchInfoEntry  21 }


	macSwitchInfoSignalConTimerPeriod		 OBJECT-TYPE
		SYNTAX					 Integer32( 1 .. 1000 )
		MAX-ACCESS			 read-create
		STATUS					 current
		DESCRIPTION			 " -- "
		::=  { macSwitchInfoEntry  22 }


	macSwitchInfoSignalConThr		 OBJECT-TYPE
		SYNTAX					 Integer32( 0 .. 3000 )
		MAX-ACCESS			 read-create
		STATUS					 current
		DESCRIPTION			 " -- "
		::=  { macSwitchInfoEntry  23 }


	macSwitchInfoSignalConBIValue		 OBJECT-TYPE
		SYNTAX					 Integer32( 0 .. 15 )
		MAX-ACCESS			 read-create
		STATUS					 current
		DESCRIPTION			 " -- "
		::=  { macSwitchInfoEntry  24 }


	macSwitchInfoReserveTimeForMsg4		 OBJECT-TYPE
		SYNTAX					 Integer32( 0 .. 64 )
		MAX-ACCESS			 read-create
		STATUS					 current
		DESCRIPTION			 " -- "
		::=  { macSwitchInfoEntry  25 }


	macSwitchInfoRlcUeInactiveSwitch		 OBJECT-TYPE
		SYNTAX					 INTEGER{ off(0),on(1)  }
		MAX-ACCESS			 read-create
		STATUS					 current
		DESCRIPTION			 " -- "
		::=  { macSwitchInfoEntry  26 }


	macSwitchInfoCaUeNumLimit		 OBJECT-TYPE
		SYNTAX					 Integer32( 0 .. 15 )
		MAX-ACCESS			 read-create
		STATUS					 current
		DESCRIPTION			 " -- "
		::=  { macSwitchInfoEntry  27 }


	macSwitchInfoVoIPUeInactiveProhibitSwitch		 OBJECT-TYPE
		SYNTAX					 INTEGER{ off(0),on(1)  }
		MAX-ACCESS			 read-create
		STATUS					 current
		DESCRIPTION			 " -- "
		::=  { macSwitchInfoEntry  28 }


	macSwitchInfoVoIPUeInactivePeriod		 OBJECT-TYPE
		SYNTAX					 Integer32( 0 .. 65535 )
		MAX-ACCESS			 read-create
		STATUS					 current
		DESCRIPTION			 " -- "
		::=  { macSwitchInfoEntry  29 }


	macSwitchInfoTrafficeInactiveTimer		 OBJECT-TYPE
		SYNTAX					 Integer32( 0 .. 65535 )
		MAX-ACCESS			 read-create
		STATUS					 current
		DESCRIPTION			 " -- "
		::=  { macSwitchInfoEntry  30 }


	macSwitchInfoHighSpeedUeInactivePeriod		 OBJECT-TYPE
		SYNTAX					 Integer32( 0 .. 65535 )
		MAX-ACCESS			 read-create
		STATUS					 current
		DESCRIPTION			 " -- "
		::=  { macSwitchInfoEntry  31 }


	macSwitchInfoextendRrcReestablishSwitch		 OBJECT-TYPE
		SYNTAX					 INTEGER{ off(0),on(1)  }
		MAX-ACCESS			 read-create
		STATUS					 current
		DESCRIPTION			 " -- "
		::=  { macSwitchInfoEntry  32 }


	macSwitchInfoReserveTimeForContentReslut		 OBJECT-TYPE
		SYNTAX					 Integer32( 0 .. 64 )
		MAX-ACCESS			 read-create
		STATUS					 current
		DESCRIPTION			 " -- "
		::=  { macSwitchInfoEntry  33 }


	macSwitchInfoUlCceReserveFlag		 OBJECT-TYPE
		SYNTAX					 INTEGER{ off(0),on(1)  }
		MAX-ACCESS			 read-create
		STATUS					 current
		DESCRIPTION			 " -- "
		::=  { macSwitchInfoEntry  34 }


	macSwitchInfoUlCceRatio		 OBJECT-TYPE
		SYNTAX					 Integer32( 0 .. 100 )
		MAX-ACCESS			 read-create
		STATUS					 current
		DESCRIPTION			 " -- "
		::=  { macSwitchInfoEntry  35 }


	macSwitchInfoMcsDiffFlag		 OBJECT-TYPE
		SYNTAX					 INTEGER{ off(0),on(1)  }
		MAX-ACCESS			 read-create
		STATUS					 current
		DESCRIPTION			 " -- "
		::=  { macSwitchInfoEntry  36 }


	macSwitchInfoMcsDiffValue		 OBJECT-TYPE
		SYNTAX					 Unsigned32( 0 .. 18 )
		MAX-ACCESS			 read-create
		STATUS					 current
		DESCRIPTION			 " -- "
		::=  { macSwitchInfoEntry  37 }


	macSwitchInfoL2UpAdaptSwitch		 OBJECT-TYPE
		SYNTAX					 Unsigned32( 0 .. 2 )
		MAX-ACCESS			 read-create
		STATUS					 current
		DESCRIPTION			 " -- "
		::=  { macSwitchInfoEntry  38 }


	macSwitchInfoUeInactivePeriodOffset		 OBJECT-TYPE
		SYNTAX					 Integer32( 0 .. 65535 )
		MAX-ACCESS			 read-create
		STATUS					 current
		DESCRIPTION			 " -- "
		::=  { macSwitchInfoEntry  39 }


	macSwitchInfoDlEdgeUserMcsTh		 OBJECT-TYPE
		SYNTAX					 Integer32( -18 .. 28 )
		MAX-ACCESS			 read-create
		STATUS					 current
		DESCRIPTION			 " -- "
		::=  { macSwitchInfoEntry  43 }


	macSwitchInfoCceOffset		 OBJECT-TYPE
		SYNTAX					 Integer32( 0 .. 32 )
		MAX-ACCESS			 read-create
		STATUS					 current
		DESCRIPTION			 " -- "
		::=  { macSwitchInfoEntry  44 }


	macSwitchInfoCceOffsetRatioCfi1		 OBJECT-TYPE
		SYNTAX					 Integer32( 0 .. 10 )
		MAX-ACCESS			 read-create
		STATUS					 current
		DESCRIPTION			 " -- "
		::=  { macSwitchInfoEntry  45 }


	macSwitchInfoCceOffsetRatioCfi2		 OBJECT-TYPE
		SYNTAX					 Integer32( 0 .. 10 )
		MAX-ACCESS			 read-create
		STATUS					 current
		DESCRIPTION			 " -- "
		::=  { macSwitchInfoEntry  46 }


	macTestSwitchInfoTable		 OBJECT-TYPE
		SYNTAX					 SEQUENCE  OF	 MacTestSwitchInfoEntry
		MAX-ACCESS			 not-accessible
		STATUS					 current
		DESCRIPTION			 " -- "
		::=  { macSwitchNode  2 }


	macTestSwitchInfoEntry		 OBJECT-TYPE
		SYNTAX					 MacTestSwitchInfoEntry
		MAX-ACCESS			 not-accessible
		STATUS					 current
		DESCRIPTION			 " -- "
		INDEX						{ macTestSwitchInfoLcId }
		::=  { macTestSwitchInfoTable  1 }


	MacTestSwitchInfoEntry		 ::=  SEQUENCE {
		macTestSwitchInfoLcId					Integer32,
		macTestSwitchInfoRowStatus					RowStatus,
		macTestSwitchInfoDlAmcSwitch					INTEGER,
		macTestSwitchInfoUlAmcSwitch					INTEGER,
		macTestSwitchInfoDlMcs					Integer32,
		macTestSwitchInfoUlMcs					Integer32,
		macTestSwitchInfoDlHarqSwitch					INTEGER,
		macTestSwitchInfoUlHarqSwitch					INTEGER,
		macTestSwitchInfoDlCqiFixSwitch					INTEGER,
		macTestSwitchInfoUlCqiFixSwitch					INTEGER,
		macTestSwitchInfoDlMimoSwitch					INTEGER,
		macTestSwitchInfoUlPrbNumMin					Unsigned32,
		macTestSwitchInfoDlScrambleSwitch					INTEGER,
		macTestSwitchInfoScramblePeriod					Integer32,
		macTestSwitchInfoRandomScrambleSwitch					INTEGER,
		macTestSwitchInfoScrambleStartPrbPosition					Integer32,
		macTestSwitchInfoPdschScrambleProp					Integer32,
		macTestSwitchInfoPdcchScrambleProp					Integer32,
		macTestSwitchInfoCchRamScrambleSwitch					INTEGER,
		macTestSwitchInfoCchScramblePrbStartPos					Integer32,
		macTestSwitchInfoCchScramblePeriod					Integer32,
		macTestSwitchInfoPrbLimitSwitch					INTEGER,
		macTestSwitchInfoSibPrbAddSwitch					Integer32,
		macTestSwitchInfoDediCceSwitch					INTEGER,
		macTestSwitchInfoDediCceNum					INTEGER,
		macTestSwitchInfoPcfichSwitch					INTEGER,
		macTestSwitchInfoCchCfiNum					Integer32,
		macTestSwitchInfoMeasSwitch					INTEGER,
		macTestSwitchInfoDlCodeWordSwapSwitch					INTEGER,
		macTestSwitchInfoTaScheSwitch					INTEGER,
		macTestSwitchInfoTaCheckSwitch					INTEGER,
		macTestSwitchInfoDlFlowCtrlSwitch					INTEGER,
		macTestSwitchInfoMacBfWbFlag					INTEGER,
		macTestSwitchInfoMacBfLamdaFromTableFlag					INTEGER,
		macTestSwitchInfoUlNonAdaptiveReTxSwitch					INTEGER,
		macTestSwitchInfoUlFlowCtrlSwitch					INTEGER,
		macTestSwitchInfoUlUciOnlySwitch					INTEGER,
		macTestSwitchInfoUlDelAckPrbSwitch					INTEGER,
		macTestSwitchInfoUlLimitSrbMcsSwitch					INTEGER,
		macTestSwitchInfoUlMaxScheUeNum					Integer32,
		macTestSwitchInfoDlMaxScheUeNum					Integer32,
		macTestSwitchInfoAccessStubSwitch					INTEGER,
		macTestSwitchInfoRNTPMsgSwitch					INTEGER,
		macTestSwitchInfoScrambleMimo					INTEGER,
		macTestSwitchInfoScraWithRealUeSwitch					INTEGER,
		macTestSwitchInfolimitUlPrb					Integer32,
		macTestSwitchInfolimitDlPrb					Integer32,
		macTestSwitchInfoMcslimitSwitch					INTEGER,
		macTestSwitchInfolimitUlMcs					Integer32,
		macTestSwitchInfolimitDlMcs					Integer32,
		macTestSwitchInfoScrambleDeltaPower					Integer32,
		macTestSwitchInfoScramblePowerMargin					Integer32,
		macTestSwitchInfoCommUePdcchCceNum					INTEGER,
		macTestSwitchInfoPowerProtectSwitch					INTEGER,
		macTestSwitchInfoSpsFirstTBSize					Integer32,
		macTestSwitchInfoSpsActiveHoldFlag					INTEGER,
		macTestSwitchLogTypeTrigger					INTEGER,
		macTestSwitchLogRecordType					INTEGER,
		macTestSwitchInfoDlCchCfiNum					Integer32,
		macTestSwitchInfoVIPScheduleSwitch					INTEGER,
		macTestSwitchInfoMaxARPLevelForVIPSchedule					Integer32,
		macTestSwitchInfoMinARPLevelForVIPSchedule					Integer32,
		macTestSwitchInfoPdschPwrProtectSwitch					INTEGER,
		macTestSwitchInfoHoPdcchPowerIncrease					Integer32,
		macTestSwitchInfoMsg2HoPdcchPowerIncrease					Integer32,
		macTestSwitchInfoMACIcicEdgeUserCriterion					INTEGER,
		macTestSwitchInfoHoMsg2ICIC					INTEGER,
		macTestSwitchInfoHoPdschPromotion					Integer32,
		macTestSwitchInfoHoMsg2Promotion					INTEGER,
		macTestSwitchInfoHoMsg2PRBThreshold					Integer32,
		macTestSwitchInfoDlPdbScheFlag					INTEGER,
		macTestSwitchInfoUlPdbScheFlag					INTEGER,
		macTestSwitchInfoDlSfbcResType					INTEGER,
		macTestSwitchInfoUlPrbSelectLimit					INTEGER,
		macTestSwitchInfoSrsType1Switch					INTEGER,
		macTestSwitchInfoUlMimoSwitch					INTEGER,
		macTestSwitchInfoSchePrbControlSwitch					INTEGER,
		macTestSwitchInfoSchePrbControlSub					Integer32,
		macTestSwitchInfoSchePrbStart					Integer32,
		macTestSwitchInfoSchePrbNum					Integer32,
		macTestSwitchInfoMbsfnCfiNum					Integer32,
		macTestSwitchInfoSpsFirstTBSizeSwitch					INTEGER,
		macTestSwitchInfoGapScheOptimizationSwitch					INTEGER,
		macTestSwitchInfoDlOneStreamBfUsePort8					INTEGER,
		macTestSwitchInfoPagingSwitch					INTEGER,
		macTestSwitchInfoNeighCellPagingSwitch					INTEGER,
		macTestSwitchInfoSelPriScheSwitch					INTEGER,
		macTestSwitchInfoMbsfnSchTm9Flag					INTEGER,
		macTestSwitchInfoMaxMsg3Mcs					Integer32,
		macTestSwitchInfoMaxMsg4Mcs					Integer32,
		macTestSwitchInfoUlMaxSrbMcs					Integer32,
		macTestSwitchInfoDlMaxSrbMcs					Integer32,
		macTestSwitchInfoTm9CBSelfAdaptSwitch					INTEGER,
		macTestSwitchInfoComEnhancedAllTxSwitch					INTEGER,
		macTestSwitchInfoUpAdaptAdvanceSwitch					INTEGER,
		macTestSwitchInfoUpTfrcRandomSwitch					INTEGER,
		macTestSwitchInfoDlTfrcRandomSwitch					INTEGER,
		macTestSwitchInfoCqiMaxTime					INTEGER,
		macTestSwitchInfoBsrBoSwitch					INTEGER,
		macTestSwitchInfoUlSrsSfnMcsDec					Integer32,
		macTestSwitchInfoPucch1bcsPeakFlag					Integer32,
		macTestSwitchInfoVoipUlPrbNumMin					Integer32,
		macTestSwitchInfoUl2PrbMcsDec					Integer32,
		macTestSwitchInfoInitULPrbNumMax					Integer32,
		macTestSwitchInfoInitULPreScheFlag					INTEGER,
		macTestSwitchInfoInitULCQIModifFlag					INTEGER,
		macTestSwitchInfoInitDLCQIModifFlag					INTEGER,
		macTestSwitchInfoInitULMaxPrbNumFlag					INTEGER,
		macTestSwitchInfoLogUeIndex					Integer32,
		macTestSwitchInfoAlarmIndex					Unsigned32,
		macTestSwitchInfoLogIndex					Unsigned32,
		macTestSwitchInfoUpQueEstimateMaxPrb					Unsigned32,
		macTestSwitchInfoDownQueEstimateMaxPrb					Unsigned32,
		macTestSwitchInfoUpTfrcMaxPrbInPrachSubfram					Integer32,
		macTestSwitchInfoUpDownSubFramLimitDownUeNum					Integer32,
		macTestSwitchCsiRsPriority					INTEGER,
		macTestSwitchTaDelta					Integer32,
		macTestSwitchInfoVoIPOneWayDelay					Integer32,
		macTestSwitchInfoVoIPOneWayThreshold					Integer32,
		macTestSwitchInfoResiBLERThreshold					Integer32,
		macTestSwitchUpScheOptMcsSwitch					INTEGER,
		macTestSwitchUpScheOptMcsThred					Integer32,
		macTestSwitchUpScheOptMcsStaticsNum					Integer32,
		macTestSwitchQci1ScwSwitch					INTEGER,
		macTestSwitchQci2ScwSwitch					INTEGER,
		macTestSwitchQci1Qci2ScwSwitch					INTEGER,
		macTestSwitchDlAtuUlAckFirstBler					Integer32,
		macTestSwitchUlRetxPrbSwitch					INTEGER,
		macTestSwitchSrbDlScheNumSub0					Integer32,
		macTestSwitchSrbDlScheNumSub1					Integer32,
		macTestSwitchSrbDlScheNumSub3					Integer32,
		macTestSwitchSrbDlScheNumSub4					Integer32,
		macTestSwitchUlResConfSwitch					INTEGER,
		macTestSwitchInfoUpDownSubFLDownUeNumbpoi					Integer32,
		macTestSwitchInfoDlCchCfiNumbpoi					Integer32,
		macTestSwitchInfoUlMaxScheUeNumbpoi					Integer32,
		macTestSwitchInfoDlMaxScheUeNumbpoi					Integer32,
		macTestSwitchInfoCqiTm8RiTMSwitch					INTEGER,
		macTestSwitchVolteAnsweredLimitMcsSwitch					INTEGER,
		macTestSwitchVolteAnsweredPeriod					Unsigned32,
		macTestSwitchInfoUlVoipRetxFlag					INTEGER
		}


	macTestSwitchInfoLcId		 OBJECT-TYPE
		SYNTAX					 Integer32( 0 .. 23 )
		MAX-ACCESS			 not-accessible
		STATUS					 current
		DESCRIPTION			 " -- "
		::=  { macTestSwitchInfoEntry  1 }


	macTestSwitchInfoRowStatus		 OBJECT-TYPE
		SYNTAX					 RowStatus
		MAX-ACCESS			 read-create
		STATUS					 current
		DESCRIPTION			 " -- "
		::=  { macTestSwitchInfoEntry  2 }


	macTestSwitchInfoDlAmcSwitch		 OBJECT-TYPE
		SYNTAX					 INTEGER{ off(0),on(1)  }
		MAX-ACCESS			 read-create
		STATUS					 current
		DESCRIPTION			 " -- "
		::=  { macTestSwitchInfoEntry  3 }


	macTestSwitchInfoUlAmcSwitch		 OBJECT-TYPE
		SYNTAX					 INTEGER{ off(0),on(1)  }
		MAX-ACCESS			 read-create
		STATUS					 current
		DESCRIPTION			 " -- "
		::=  { macTestSwitchInfoEntry  4 }


	macTestSwitchInfoDlMcs		 OBJECT-TYPE
		SYNTAX					 Integer32( 0 .. 28 )
		MAX-ACCESS			 read-create
		STATUS					 current
		DESCRIPTION			 " -- "
		::=  { macTestSwitchInfoEntry  5 }


	macTestSwitchInfoUlMcs		 OBJECT-TYPE
		SYNTAX					 Integer32( 0 .. 28 )
		MAX-ACCESS			 read-create
		STATUS					 current
		DESCRIPTION			 " -- "
		::=  { macTestSwitchInfoEntry  6 }


	macTestSwitchInfoDlHarqSwitch		 OBJECT-TYPE
		SYNTAX					 INTEGER{ off(0),on(1)  }
		MAX-ACCESS			 read-create
		STATUS					 current
		DESCRIPTION			 " -- "
		::=  { macTestSwitchInfoEntry  7 }


	macTestSwitchInfoUlHarqSwitch		 OBJECT-TYPE
		SYNTAX					 INTEGER{ off(0),on(1)  }
		MAX-ACCESS			 read-create
		STATUS					 current
		DESCRIPTION			 " -- "
		::=  { macTestSwitchInfoEntry  8 }


	macTestSwitchInfoDlCqiFixSwitch		 OBJECT-TYPE
		SYNTAX					 INTEGER{ off(0),on(1)  }
		MAX-ACCESS			 read-create
		STATUS					 current
		DESCRIPTION			 " -- "
		::=  { macTestSwitchInfoEntry  9 }


	macTestSwitchInfoUlCqiFixSwitch		 OBJECT-TYPE
		SYNTAX					 INTEGER{ off(0),on(1)  }
		MAX-ACCESS			 read-create
		STATUS					 current
		DESCRIPTION			 " -- "
		::=  { macTestSwitchInfoEntry  10 }


	macTestSwitchInfoDlMimoSwitch		 OBJECT-TYPE
		SYNTAX					 INTEGER{ interMode(-2),off(-1),sfbc(0),oneLayerSdm(1),largeCddSdm(2),zeroCddSdm(3),tm7oneStreamBf(4),tm8oneStreamBf(5),twoStreamBf(6),tm9oneStreamBf(7),tm9twoStreamBf(8)  }
		MAX-ACCESS			 read-create
		STATUS					 current
		DESCRIPTION			 " -- "
		::=  { macTestSwitchInfoEntry  11 }


	macTestSwitchInfoUlPrbNumMin		 OBJECT-TYPE
		SYNTAX					 Unsigned32( 1 .. 100 )
		MAX-ACCESS			 read-create
		STATUS					 current
		DESCRIPTION			 " -- "
		::=  { macTestSwitchInfoEntry  12 }


	macTestSwitchInfoDlScrambleSwitch		 OBJECT-TYPE
		SYNTAX					 INTEGER{ off(0),on(1)  }
		MAX-ACCESS			 read-create
		STATUS					 current
		DESCRIPTION			 " -- "
		::=  { macTestSwitchInfoEntry  13 }


	macTestSwitchInfoScramblePeriod		 OBJECT-TYPE
		SYNTAX					 Integer32( 1 .. 65535 )
		MAX-ACCESS			 read-create
		STATUS					 current
		DESCRIPTION			 " -- "
		::=  { macTestSwitchInfoEntry  14 }


	macTestSwitchInfoRandomScrambleSwitch		 OBJECT-TYPE
		SYNTAX					 INTEGER{ off(0),on(1)  }
		MAX-ACCESS			 read-create
		STATUS					 current
		DESCRIPTION			 " -- "
		::=  { macTestSwitchInfoEntry  15 }


	macTestSwitchInfoScrambleStartPrbPosition		 OBJECT-TYPE
		SYNTAX					 Integer32( 0 .. 99 )
		MAX-ACCESS			 read-create
		STATUS					 current
		DESCRIPTION			 " -- "
		::=  { macTestSwitchInfoEntry  16 }


	macTestSwitchInfoPdschScrambleProp		 OBJECT-TYPE
		SYNTAX					 Integer32( 0 .. 100 )
		MAX-ACCESS			 read-create
		STATUS					 current
		DESCRIPTION			 " -- "
		::=  { macTestSwitchInfoEntry  17 }


	macTestSwitchInfoPdcchScrambleProp		 OBJECT-TYPE
		SYNTAX					 Integer32( 0 .. 100 )
		MAX-ACCESS			 read-create
		STATUS					 current
		DESCRIPTION			 " -- "
		::=  { macTestSwitchInfoEntry  18 }


	macTestSwitchInfoCchRamScrambleSwitch		 OBJECT-TYPE
		SYNTAX					 INTEGER{ off(0),on(1)  }
		MAX-ACCESS			 read-create
		STATUS					 current
		DESCRIPTION			 " -- "
		::=  { macTestSwitchInfoEntry  19 }


	macTestSwitchInfoCchScramblePrbStartPos		 OBJECT-TYPE
		SYNTAX					 Integer32( 0 .. 87 )
		MAX-ACCESS			 read-create
		STATUS					 current
		DESCRIPTION			 " -- "
		::=  { macTestSwitchInfoEntry  20 }


	macTestSwitchInfoCchScramblePeriod		 OBJECT-TYPE
		SYNTAX					 Integer32( 1 .. 65535 )
		MAX-ACCESS			 read-create
		STATUS					 current
		DESCRIPTION			 " -- "
		::=  { macTestSwitchInfoEntry  21 }


	macTestSwitchInfoPrbLimitSwitch		 OBJECT-TYPE
		SYNTAX					 INTEGER{ off(0),on(1)  }
		MAX-ACCESS			 read-create
		STATUS					 current
		DESCRIPTION			 " -- "
		::=  { macTestSwitchInfoEntry  22 }


	macTestSwitchInfoSibPrbAddSwitch		 OBJECT-TYPE
		SYNTAX					 Integer32( 0 .. 16 )
		MAX-ACCESS			 read-create
		STATUS					 current
		DESCRIPTION			 " -- "
		::=  { macTestSwitchInfoEntry  23 }


	macTestSwitchInfoDediCceSwitch		 OBJECT-TYPE
		SYNTAX					 INTEGER{ off(0),on(1)  }
		MAX-ACCESS			 read-create
		STATUS					 current
		DESCRIPTION			 " -- "
		::=  { macTestSwitchInfoEntry  24 }


	macTestSwitchInfoDediCceNum		 OBJECT-TYPE
		SYNTAX					 INTEGER{ val1(1),val2(2),val4(4),val8(8)  }
		MAX-ACCESS			 read-create
		STATUS					 current
		DESCRIPTION			 " -- "
		::=  { macTestSwitchInfoEntry  25 }


	macTestSwitchInfoPcfichSwitch		 OBJECT-TYPE
		SYNTAX					 INTEGER{ off(0),on(1)  }
		MAX-ACCESS			 read-create
		STATUS					 current
		DESCRIPTION			 " -- "
		::=  { macTestSwitchInfoEntry  28 }


	macTestSwitchInfoCchCfiNum		 OBJECT-TYPE
		SYNTAX					 Integer32( 1 .. 3 )
		MAX-ACCESS			 read-create
		STATUS					 current
		DESCRIPTION			 " -- "
		::=  { macTestSwitchInfoEntry  29 }


	macTestSwitchInfoMeasSwitch		 OBJECT-TYPE
		SYNTAX					 INTEGER{ off(0),on(1)  }
		MAX-ACCESS			 read-create
		STATUS					 current
		DESCRIPTION			 " -- "
		::=  { macTestSwitchInfoEntry  30 }


	macTestSwitchInfoDlCodeWordSwapSwitch		 OBJECT-TYPE
		SYNTAX					 INTEGER{ off(0),on(1)  }
		MAX-ACCESS			 read-create
		STATUS					 current
		DESCRIPTION			 " -- "
		::=  { macTestSwitchInfoEntry  32 }


	macTestSwitchInfoTaScheSwitch		 OBJECT-TYPE
		SYNTAX					 INTEGER{ off(0),ms500(1),ms750(2),ms1280(3),ms1920(4),ms2560(5),ms5120(6),ms10240(7)  }
		MAX-ACCESS			 read-create
		STATUS					 current
		DESCRIPTION			 " -- "
		::=  { macTestSwitchInfoEntry  34 }


	macTestSwitchInfoTaCheckSwitch		 OBJECT-TYPE
		SYNTAX					 INTEGER{ off(0),on(1)  }
		MAX-ACCESS			 read-create
		STATUS					 current
		DESCRIPTION			 " -- "
		::=  { macTestSwitchInfoEntry  35 }


	macTestSwitchInfoDlFlowCtrlSwitch		 OBJECT-TYPE
		SYNTAX					 INTEGER{ off(0),on(1)  }
		MAX-ACCESS			 read-create
		STATUS					 current
		DESCRIPTION			 " -- "
		::=  { macTestSwitchInfoEntry  36 }


	macTestSwitchInfoMacBfWbFlag		 OBJECT-TYPE
		SYNTAX					 INTEGER{ false(0),true(1)  }
		MAX-ACCESS			 read-create
		STATUS					 current
		DESCRIPTION			 " -- "
		::=  { macTestSwitchInfoEntry  37 }


	macTestSwitchInfoMacBfLamdaFromTableFlag		 OBJECT-TYPE
		SYNTAX					 INTEGER{ false(0),true(1)  }
		MAX-ACCESS			 read-create
		STATUS					 current
		DESCRIPTION			 " -- "
		::=  { macTestSwitchInfoEntry  38 }


	macTestSwitchInfoUlNonAdaptiveReTxSwitch		 OBJECT-TYPE
		SYNTAX					 INTEGER{ off(0),on(1)  }
		MAX-ACCESS			 read-create
		STATUS					 current
		DESCRIPTION			 " -- "
		::=  { macTestSwitchInfoEntry  39 }


	macTestSwitchInfoUlFlowCtrlSwitch		 OBJECT-TYPE
		SYNTAX					 INTEGER{ off(0),on(1)  }
		MAX-ACCESS			 read-create
		STATUS					 current
		DESCRIPTION			 " -- "
		::=  { macTestSwitchInfoEntry  41 }


	macTestSwitchInfoUlUciOnlySwitch		 OBJECT-TYPE
		SYNTAX					 INTEGER{ off(0),on(1)  }
		MAX-ACCESS			 read-create
		STATUS					 current
		DESCRIPTION			 " -- "
		::=  { macTestSwitchInfoEntry  42 }


	macTestSwitchInfoUlDelAckPrbSwitch		 OBJECT-TYPE
		SYNTAX					 INTEGER{ off(0),on(1)  }
		MAX-ACCESS			 read-create
		STATUS					 current
		DESCRIPTION			 " -- "
		::=  { macTestSwitchInfoEntry  43 }


	macTestSwitchInfoUlLimitSrbMcsSwitch		 OBJECT-TYPE
		SYNTAX					 INTEGER{ off(0),on(1)  }
		MAX-ACCESS			 read-create
		STATUS					 current
		DESCRIPTION			 " -- "
		::=  { macTestSwitchInfoEntry  44 }


	macTestSwitchInfoUlMaxScheUeNum		 OBJECT-TYPE
		SYNTAX					 Integer32( 0 .. 30 )
		MAX-ACCESS			 read-create
		STATUS					 current
		DESCRIPTION			 " -- "
		::=  { macTestSwitchInfoEntry  45 }


	macTestSwitchInfoDlMaxScheUeNum		 OBJECT-TYPE
		SYNTAX					 Integer32( 0 .. 20 )
		MAX-ACCESS			 read-create
		STATUS					 current
		DESCRIPTION			 " -- "
		::=  { macTestSwitchInfoEntry  46 }


	macTestSwitchInfoAccessStubSwitch		 OBJECT-TYPE
		SYNTAX					 INTEGER{ off(0),on(1)  }
		MAX-ACCESS			 read-create
		STATUS					 current
		DESCRIPTION			 " -- "
		::=  { macTestSwitchInfoEntry  47 }


	macTestSwitchInfoRNTPMsgSwitch		 OBJECT-TYPE
		SYNTAX					 INTEGER{ off(0),on(1)  }
		MAX-ACCESS			 read-create
		STATUS					 current
		DESCRIPTION			 " -- "
		::=  { macTestSwitchInfoEntry  48 }


	macTestSwitchInfoScrambleMimo		 OBJECT-TYPE
		SYNTAX					 INTEGER{ sfbc(0),tm7oneStreamBf(4)  }
		MAX-ACCESS			 read-create
		STATUS					 current
		DESCRIPTION			 " -- "
		::=  { macTestSwitchInfoEntry  49 }


	macTestSwitchInfoScraWithRealUeSwitch		 OBJECT-TYPE
		SYNTAX					 INTEGER{ off(0),on(1)  }
		MAX-ACCESS			 read-create
		STATUS					 current
		DESCRIPTION			 " -- "
		::=  { macTestSwitchInfoEntry  50 }


	macTestSwitchInfolimitUlPrb		 OBJECT-TYPE
		SYNTAX					 Integer32( 0 .. 100 )
		MAX-ACCESS			 read-create
		STATUS					 current
		DESCRIPTION			 " -- "
		::=  { macTestSwitchInfoEntry  51 }


	macTestSwitchInfolimitDlPrb		 OBJECT-TYPE
		SYNTAX					 Integer32( 0 .. 100 )
		MAX-ACCESS			 read-create
		STATUS					 current
		DESCRIPTION			 " -- "
		::=  { macTestSwitchInfoEntry  52 }


	macTestSwitchInfoMcslimitSwitch		 OBJECT-TYPE
		SYNTAX					 INTEGER{ off(0),on(1)  }
		MAX-ACCESS			 read-create
		STATUS					 current
		DESCRIPTION			 " -- "
		::=  { macTestSwitchInfoEntry  53 }


	macTestSwitchInfolimitUlMcs		 OBJECT-TYPE
		SYNTAX					 Integer32( 0 .. 28 )
		MAX-ACCESS			 read-create
		STATUS					 current
		DESCRIPTION			 " -- "
		::=  { macTestSwitchInfoEntry  54 }


	macTestSwitchInfolimitDlMcs		 OBJECT-TYPE
		SYNTAX					 Integer32( 0 .. 28 )
		MAX-ACCESS			 read-create
		STATUS					 current
		DESCRIPTION			 " -- "
		::=  { macTestSwitchInfoEntry  55 }


	macTestSwitchInfoScrambleDeltaPower		 OBJECT-TYPE
		SYNTAX					 Integer32( -60 .. 70 )
		MAX-ACCESS			 read-create
		STATUS					 current
		DESCRIPTION			 " -- "
		::=  { macTestSwitchInfoEntry  56 }


	macTestSwitchInfoScramblePowerMargin		 OBJECT-TYPE
		SYNTAX					 Integer32( 0 .. 50 )
		MAX-ACCESS			 read-create
		STATUS					 current
		DESCRIPTION			 " -- "
		::=  { macTestSwitchInfoEntry  57 }


	macTestSwitchInfoCommUePdcchCceNum		 OBJECT-TYPE
		SYNTAX					 INTEGER{ val4(4),val8(8)  }
		MAX-ACCESS			 read-create
		STATUS					 current
		DESCRIPTION			 " -- "
		::=  { macTestSwitchInfoEntry  58 }


	macTestSwitchInfoPowerProtectSwitch		 OBJECT-TYPE
		SYNTAX					 INTEGER{ off(0),on(1)  }
		MAX-ACCESS			 read-create
		STATUS					 current
		DESCRIPTION			 " -- "
		::=  { macTestSwitchInfoEntry  59 }


	macTestSwitchInfoSpsFirstTBSize		 OBJECT-TYPE
		SYNTAX					 Integer32( 0 .. 4000 )
		MAX-ACCESS			 read-create
		STATUS					 current
		DESCRIPTION			 " -- "
		::=  { macTestSwitchInfoEntry  60 }


	macTestSwitchInfoSpsActiveHoldFlag		 OBJECT-TYPE
		SYNTAX					 INTEGER{ off(0),on(1)  }
		MAX-ACCESS			 read-create
		STATUS					 current
		DESCRIPTION			 " -- "
		::=  { macTestSwitchInfoEntry  61 }


	macTestSwitchLogTypeTrigger		 OBJECT-TYPE
		SYNTAX					 INTEGER{ offlog(-3),accesslog(-2),pinglog(-1),ulconfig(51),dlconfig(52),reestabish(53),uplinkschedule(0),uplinkscheexception(1),uplinkresourceassignment(2),uplinkuplinkresourceassignmenterror(3),uplinkdata(4),uplinkdatacrc(5),downlinkschedule(6),downlinkscheduleprocess(7),downlinkresourceassignment(8),downlinkresourceassignmenterror(9),downlinkdata(10),downlinkdataexception(11),harqstate(12),harqfeedbackvalue(13),accessmsg1msg2(14),accessprocessexception(15),mimoexchange(16),drxprocess(17),tfrcexception(18),registerunregister(19),dlsps(20),cchpower(21),error(22),ulharqstate(23),celllicence(24),ta(25),ulinfofrompl(26),dlspecialelement(27),dma(28),cqimodify(29),srb(30),drc(32),ca(33),ttibundling(34),fs(35),dci(36),uci(37),ulsps(38),keyulsps(39),rlcdata(40),dcicch(45),sendcch(46),srcqiack(47),pdcpdata(70),pdcpdatasec(71),pdcpdataho(72),pdcprohc(73)  }
		MAX-ACCESS			 read-create
		STATUS					 current
		DESCRIPTION			 " -- "
		::=  { macTestSwitchInfoEntry  62 }


	macTestSwitchLogRecordType		 OBJECT-TYPE
		SYNTAX					 INTEGER{ once(0),recycle(1)  }
		MAX-ACCESS			 read-create
		STATUS					 current
		DESCRIPTION			 " -- "
		::=  { macTestSwitchInfoEntry  63 }


	macTestSwitchInfoDlCchCfiNum		 OBJECT-TYPE
		SYNTAX					 Integer32( 1 .. 3 )
		MAX-ACCESS			 read-create
		STATUS					 current
		DESCRIPTION			 " -- "
		::=  { macTestSwitchInfoEntry  64 }


	macTestSwitchInfoVIPScheduleSwitch		 OBJECT-TYPE
		SYNTAX					 INTEGER{ off(0),on(1)  }
		MAX-ACCESS			 read-create
		STATUS					 current
		DESCRIPTION			 " -- "
		::=  { macTestSwitchInfoEntry  65 }


	macTestSwitchInfoMaxARPLevelForVIPSchedule		 OBJECT-TYPE
		SYNTAX					 Integer32( 1 .. 15 )
		MAX-ACCESS			 read-create
		STATUS					 current
		DESCRIPTION			 " -- "
		::=  { macTestSwitchInfoEntry  66 }


	macTestSwitchInfoMinARPLevelForVIPSchedule		 OBJECT-TYPE
		SYNTAX					 Integer32( 1 .. 15 )
		MAX-ACCESS			 read-create
		STATUS					 current
		DESCRIPTION			 " -- "
		::=  { macTestSwitchInfoEntry  67 }


	macTestSwitchInfoPdschPwrProtectSwitch		 OBJECT-TYPE
		SYNTAX					 INTEGER{ off(0),on(1)  }
		MAX-ACCESS			 read-create
		STATUS					 current
		DESCRIPTION			 " -- "
		::=  { macTestSwitchInfoEntry  68 }


	macTestSwitchInfoHoPdcchPowerIncrease		 OBJECT-TYPE
		SYNTAX					 Integer32( 0 .. 6 )
		MAX-ACCESS			 read-create
		STATUS					 current
		DESCRIPTION			 " -- "
		::=  { macTestSwitchInfoEntry  69 }


	macTestSwitchInfoMsg2HoPdcchPowerIncrease		 OBJECT-TYPE
		SYNTAX					 Integer32( 0 .. 6 )
		MAX-ACCESS			 read-create
		STATUS					 current
		DESCRIPTION			 " -- "
		::=  { macTestSwitchInfoEntry  70 }


	macTestSwitchInfoMACIcicEdgeUserCriterion		 OBJECT-TYPE
		SYNTAX					 INTEGER{ off(0),on(1)  }
		MAX-ACCESS			 read-create
		STATUS					 current
		DESCRIPTION			 " -- "
		::=  { macTestSwitchInfoEntry  71 }


	macTestSwitchInfoHoMsg2ICIC		 OBJECT-TYPE
		SYNTAX					 INTEGER{ off(0),on(1)  }
		MAX-ACCESS			 read-create
		STATUS					 current
		DESCRIPTION			 " -- "
		::=  { macTestSwitchInfoEntry  72 }


	macTestSwitchInfoHoPdschPromotion		 OBJECT-TYPE
		SYNTAX					 Integer32( 0 .. 6 )
		MAX-ACCESS			 read-create
		STATUS					 current
		DESCRIPTION			 " -- "
		::=  { macTestSwitchInfoEntry  73 }


	macTestSwitchInfoHoMsg2Promotion		 OBJECT-TYPE
		SYNTAX					 INTEGER{ o(0),oDot5(1),one(2),oneDot5(3),two(4),twoDot5(5),three(6),threeDot5(7),four(8),fourDot5(9),five(10),fiveDot5(11),six(12)  }
		MAX-ACCESS			 read-create
		STATUS					 current
		DESCRIPTION			 " -- "
		::=  { macTestSwitchInfoEntry  74 }


	macTestSwitchInfoHoMsg2PRBThreshold		 OBJECT-TYPE
		SYNTAX					 Integer32( 6 .. 21 )
		MAX-ACCESS			 read-create
		STATUS					 current
		DESCRIPTION			 " -- "
		::=  { macTestSwitchInfoEntry  75 }


	macTestSwitchInfoDlPdbScheFlag		 OBJECT-TYPE
		SYNTAX					 INTEGER{ off(0),on(1)  }
		MAX-ACCESS			 read-create
		STATUS					 current
		DESCRIPTION			 " -- "
		::=  { macTestSwitchInfoEntry  76 }


	macTestSwitchInfoUlPdbScheFlag		 OBJECT-TYPE
		SYNTAX					 INTEGER{ off(0),on(1)  }
		MAX-ACCESS			 read-create
		STATUS					 current
		DESCRIPTION			 " -- "
		::=  { macTestSwitchInfoEntry  77 }


	macTestSwitchInfoDlSfbcResType		 OBJECT-TYPE
		SYNTAX					 INTEGER{ type0ortype1(0),type2(1)  }
		MAX-ACCESS			 read-create
		STATUS					 current
		DESCRIPTION			 " -- "
		::=  { macTestSwitchInfoEntry  78 }


	macTestSwitchInfoUlPrbSelectLimit		 OBJECT-TYPE
		SYNTAX					 INTEGER{ off(0),limitfirst50(1),limitlast50(2)  }
		MAX-ACCESS			 read-create
		STATUS					 current
		DESCRIPTION			 " -- "
		::=  { macTestSwitchInfoEntry  79 }


	macTestSwitchInfoSrsType1Switch		 OBJECT-TYPE
		SYNTAX					 INTEGER{ off(0),on(1)  }
		MAX-ACCESS			 read-create
		STATUS					 current
		DESCRIPTION			 " -- "
		::=  { macTestSwitchInfoEntry  80 }


	macTestSwitchInfoUlMimoSwitch		 OBJECT-TYPE
		SYNTAX					 INTEGER{ interMode(-1),singleAntennaPort(0),closeLoopRank1(1),closeLoopRank2(2)  }
		MAX-ACCESS			 read-create
		STATUS					 current
		DESCRIPTION			 " -- "
		::=  { macTestSwitchInfoEntry  81 }


	macTestSwitchInfoSchePrbControlSwitch		 OBJECT-TYPE
		SYNTAX					 INTEGER{ off(0),on(1)  }
		MAX-ACCESS			 read-create
		STATUS					 current
		DESCRIPTION			 " -- "
		::=  { macTestSwitchInfoEntry  82 }


	macTestSwitchInfoSchePrbControlSub		 OBJECT-TYPE
		SYNTAX					 Integer32( 0 .. 9 )
		MAX-ACCESS			 read-create
		STATUS					 current
		DESCRIPTION			 " -- "
		::=  { macTestSwitchInfoEntry  83 }


	macTestSwitchInfoSchePrbStart		 OBJECT-TYPE
		SYNTAX					 Integer32( 0 .. 99 )
		MAX-ACCESS			 read-create
		STATUS					 current
		DESCRIPTION			 " -- "
		::=  { macTestSwitchInfoEntry  84 }


	macTestSwitchInfoSchePrbNum		 OBJECT-TYPE
		SYNTAX					 Integer32( 1 .. 100 )
		MAX-ACCESS			 read-create
		STATUS					 current
		DESCRIPTION			 " -- "
		::=  { macTestSwitchInfoEntry  85 }


	macTestSwitchInfoMbsfnCfiNum		 OBJECT-TYPE
		SYNTAX					 Integer32( 0 .. 2 )
		MAX-ACCESS			 read-create
		STATUS					 current
		DESCRIPTION			 " -- "
		::=  { macTestSwitchInfoEntry  86 }


	macTestSwitchInfoSpsFirstTBSizeSwitch		 OBJECT-TYPE
		SYNTAX					 INTEGER{ off(0),on(1)  }
		MAX-ACCESS			 read-create
		STATUS					 current
		DESCRIPTION			 " -- "
		::=  { macTestSwitchInfoEntry  90 }


	macTestSwitchInfoGapScheOptimizationSwitch		 OBJECT-TYPE
		SYNTAX					 INTEGER{ off(0),on(1)  }
		MAX-ACCESS			 read-create
		STATUS					 current
		DESCRIPTION			 " -- "
		::=  { macTestSwitchInfoEntry  91 }


	macTestSwitchInfoDlOneStreamBfUsePort8		 OBJECT-TYPE
		SYNTAX					 INTEGER{ port7(0),port8(1)  }
		MAX-ACCESS			 read-create
		STATUS					 current
		DESCRIPTION			 " -- "
		::=  { macTestSwitchInfoEntry  92 }


	macTestSwitchInfoPagingSwitch		 OBJECT-TYPE
		SYNTAX					 INTEGER{ off(0),on(1)  }
		MAX-ACCESS			 read-create
		STATUS					 current
		DESCRIPTION			 " -- "
		::=  { macTestSwitchInfoEntry  93 }


	macTestSwitchInfoNeighCellPagingSwitch		 OBJECT-TYPE
		SYNTAX					 INTEGER{ off(0),on(1)  }
		MAX-ACCESS			 read-create
		STATUS					 current
		DESCRIPTION			 " -- "
		::=  { macTestSwitchInfoEntry  94 }


	macTestSwitchInfoSelPriScheSwitch		 OBJECT-TYPE
		SYNTAX					 INTEGER{ off(0),on(1)  }
		MAX-ACCESS			 read-create
		STATUS					 current
		DESCRIPTION			 " -- "
		::=  { macTestSwitchInfoEntry  95 }


	macTestSwitchInfoMbsfnSchTm9Flag		 OBJECT-TYPE
		SYNTAX					 INTEGER{ off(0),on(1)  }
		MAX-ACCESS			 read-create
		STATUS					 current
		DESCRIPTION			 " -- "
		::=  { macTestSwitchInfoEntry  96 }


	macTestSwitchInfoMaxMsg3Mcs		 OBJECT-TYPE
		SYNTAX					 Integer32( 0 .. 15 )
		MAX-ACCESS			 read-create
		STATUS					 current
		DESCRIPTION			 " -- "
		::=  { macTestSwitchInfoEntry  97 }


	macTestSwitchInfoMaxMsg4Mcs		 OBJECT-TYPE
		SYNTAX					 Integer32( 0 .. 9 )
		MAX-ACCESS			 read-create
		STATUS					 current
		DESCRIPTION			 " -- "
		::=  { macTestSwitchInfoEntry  98 }


	macTestSwitchInfoUlMaxSrbMcs		 OBJECT-TYPE
		SYNTAX					 Integer32( 0 .. 28 )
		MAX-ACCESS			 read-create
		STATUS					 current
		DESCRIPTION			 " -- "
		::=  { macTestSwitchInfoEntry  99 }


	macTestSwitchInfoDlMaxSrbMcs		 OBJECT-TYPE
		SYNTAX					 Integer32( 0 .. 28 )
		MAX-ACCESS			 read-create
		STATUS					 current
		DESCRIPTION			 " -- "
		::=  { macTestSwitchInfoEntry  100 }


	macTestSwitchInfoTm9CBSelfAdaptSwitch		 OBJECT-TYPE
		SYNTAX					 INTEGER{ off(0),on(1)  }
		MAX-ACCESS			 read-create
		STATUS					 current
		DESCRIPTION			 " -- "
		::=  { macTestSwitchInfoEntry  101 }


	macTestSwitchInfoComEnhancedAllTxSwitch		 OBJECT-TYPE
		SYNTAX					 INTEGER{ off(0),on(1)  }
		MAX-ACCESS			 read-create
		STATUS					 current
		DESCRIPTION			 " -- "
		::=  { macTestSwitchInfoEntry  103 }


	macTestSwitchInfoUpAdaptAdvanceSwitch		 OBJECT-TYPE
		SYNTAX					 INTEGER{ off(0),on(1)  }
		MAX-ACCESS			 read-create
		STATUS					 current
		DESCRIPTION			 " -- "
		::=  { macTestSwitchInfoEntry  104 }


	macTestSwitchInfoUpTfrcRandomSwitch		 OBJECT-TYPE
		SYNTAX					 INTEGER{ off(0),on(1)  }
		MAX-ACCESS			 read-create
		STATUS					 current
		DESCRIPTION			 " -- "
		::=  { macTestSwitchInfoEntry  105 }


	macTestSwitchInfoDlTfrcRandomSwitch		 OBJECT-TYPE
		SYNTAX					 INTEGER{ off(0),on(1)  }
		MAX-ACCESS			 read-create
		STATUS					 current
		DESCRIPTION			 " -- "
		::=  { macTestSwitchInfoEntry  106 }


	macTestSwitchInfoCqiMaxTime		 OBJECT-TYPE
		SYNTAX					 INTEGER{ ms200(0),ms400(1),ms600(2),ms800(3),s1(4),s2(5),s4(6),s6(7),s8(8),s10(9),infinity(10)  }
		MAX-ACCESS			 read-create
		STATUS					 current
		DESCRIPTION			 " -- "
		::=  { macTestSwitchInfoEntry  107 }


	macTestSwitchInfoBsrBoSwitch		 OBJECT-TYPE
		SYNTAX					 INTEGER{ off(0),on(1)  }
		MAX-ACCESS			 read-create
		STATUS					 current
		DESCRIPTION			 " -- "
		::=  { macTestSwitchInfoEntry  108 }


	macTestSwitchInfoUlSrsSfnMcsDec		 OBJECT-TYPE
		SYNTAX					 Integer32( 0 .. 28 )
		MAX-ACCESS			 read-create
		STATUS					 current
		DESCRIPTION			 " -- "
		::=  { macTestSwitchInfoEntry  109 }


	macTestSwitchInfoPucch1bcsPeakFlag		 OBJECT-TYPE
		SYNTAX					 Integer32( 0 .. 3 )
		MAX-ACCESS			 read-create
		STATUS					 current
		DESCRIPTION			 " -- "
		::=  { macTestSwitchInfoEntry  110 }


	macTestSwitchInfoVoipUlPrbNumMin		 OBJECT-TYPE
		SYNTAX					 Integer32( 1 .. 6 )
		MAX-ACCESS			 read-create
		STATUS					 current
		DESCRIPTION			 " -- "
		::=  { macTestSwitchInfoEntry  111 }


	macTestSwitchInfoUl2PrbMcsDec		 OBJECT-TYPE
		SYNTAX					 Integer32( 0 .. 6 )
		MAX-ACCESS			 read-create
		STATUS					 current
		DESCRIPTION			 " -- "
		::=  { macTestSwitchInfoEntry  112 }


	macTestSwitchInfoInitULPrbNumMax		 OBJECT-TYPE
		SYNTAX					 Integer32( 1 .. 100 )
		MAX-ACCESS			 read-create
		STATUS					 current
		DESCRIPTION			 " -- "
		::=  { macTestSwitchInfoEntry  113 }


	macTestSwitchInfoInitULPreScheFlag		 OBJECT-TYPE
		SYNTAX					 INTEGER{ off(0),on(1)  }
		MAX-ACCESS			 read-create
		STATUS					 current
		DESCRIPTION			 " -- "
		::=  { macTestSwitchInfoEntry  114 }


	macTestSwitchInfoInitULCQIModifFlag		 OBJECT-TYPE
		SYNTAX					 INTEGER{ off(0),on(1)  }
		MAX-ACCESS			 read-create
		STATUS					 current
		DESCRIPTION			 " -- "
		::=  { macTestSwitchInfoEntry  115 }


	macTestSwitchInfoInitDLCQIModifFlag		 OBJECT-TYPE
		SYNTAX					 INTEGER{ off(0),on(1)  }
		MAX-ACCESS			 read-create
		STATUS					 current
		DESCRIPTION			 " -- "
		::=  { macTestSwitchInfoEntry  116 }


	macTestSwitchInfoInitULMaxPrbNumFlag		 OBJECT-TYPE
		SYNTAX					 INTEGER{ off(0),on(1)  }
		MAX-ACCESS			 read-create
		STATUS					 current
		DESCRIPTION			 " -- "
		::=  { macTestSwitchInfoEntry  117 }


	macTestSwitchInfoLogUeIndex		 OBJECT-TYPE
		SYNTAX					 Integer32( 0 .. 65535 )
		MAX-ACCESS			 read-create
		STATUS					 current
		DESCRIPTION			 " -- "
		::=  { macTestSwitchInfoEntry  118 }


	macTestSwitchInfoAlarmIndex		 OBJECT-TYPE
		SYNTAX					 Unsigned32( 0 .. 65535 )
		MAX-ACCESS			 read-create
		STATUS					 current
		DESCRIPTION			 " -- "
		::=  { macTestSwitchInfoEntry  119 }


	macTestSwitchInfoLogIndex		 OBJECT-TYPE
		SYNTAX					 Unsigned32( 0 .. 65535 )
		MAX-ACCESS			 read-create
		STATUS					 current
		DESCRIPTION			 " -- "
		::=  { macTestSwitchInfoEntry  120 }


	macTestSwitchInfoUpQueEstimateMaxPrb		 OBJECT-TYPE
		SYNTAX					 Unsigned32( 0 .. 600 )
		MAX-ACCESS			 read-create
		STATUS					 current
		DESCRIPTION			 " -- "
		::=  { macTestSwitchInfoEntry  121 }


	macTestSwitchInfoDownQueEstimateMaxPrb		 OBJECT-TYPE
		SYNTAX					 Unsigned32( 0 .. 600 )
		MAX-ACCESS			 read-create
		STATUS					 current
		DESCRIPTION			 " -- "
		::=  { macTestSwitchInfoEntry  122 }


	macTestSwitchInfoUpTfrcMaxPrbInPrachSubfram		 OBJECT-TYPE
		SYNTAX					 Integer32( 0 .. 100 )
		MAX-ACCESS			 read-create
		STATUS					 current
		DESCRIPTION			 " -- "
		::=  { macTestSwitchInfoEntry  123 }


	macTestSwitchInfoUpDownSubFramLimitDownUeNum		 OBJECT-TYPE
		SYNTAX					 Integer32( 0 .. 50 )
		MAX-ACCESS			 read-create
		STATUS					 current
		DESCRIPTION			 " -- "
		::=  { macTestSwitchInfoEntry  124 }


	macTestSwitchCsiRsPriority		 OBJECT-TYPE
		SYNTAX					 INTEGER{ off(0),on(1)  }
		MAX-ACCESS			 read-create
		STATUS					 current
		DESCRIPTION			 " -- "
		::=  { macTestSwitchInfoEntry  125 }


	macTestSwitchTaDelta		 OBJECT-TYPE
		SYNTAX					 Integer32( -100 .. 100 )
		MAX-ACCESS			 read-create
		STATUS					 current
		DESCRIPTION			 " -- "
		::=  { macTestSwitchInfoEntry  126 }


	macTestSwitchInfoVoIPOneWayDelay		 OBJECT-TYPE
		SYNTAX					 Integer32( 1 .. 60 )
		MAX-ACCESS			 read-create
		STATUS					 current
		DESCRIPTION			 " -- "
		::=  { macTestSwitchInfoEntry  127 }


	macTestSwitchInfoVoIPOneWayThreshold		 OBJECT-TYPE
		SYNTAX					 Integer32( 1 .. 50 )
		MAX-ACCESS			 read-create
		STATUS					 current
		DESCRIPTION			 " -- "
		::=  { macTestSwitchInfoEntry  128 }


	macTestSwitchInfoResiBLERThreshold		 OBJECT-TYPE
		SYNTAX					 Integer32( 1 .. 100 )
		MAX-ACCESS			 read-create
		STATUS					 current
		DESCRIPTION			 " -- "
		::=  { macTestSwitchInfoEntry  129 }


	macTestSwitchUpScheOptMcsSwitch		 OBJECT-TYPE
		SYNTAX					 INTEGER{ off(0),on(1)  }
		MAX-ACCESS			 read-create
		STATUS					 current
		DESCRIPTION			 " -- "
		::=  { macTestSwitchInfoEntry  130 }


	macTestSwitchUpScheOptMcsThred		 OBJECT-TYPE
		SYNTAX					 Integer32( 0 .. 20 )
		MAX-ACCESS			 read-create
		STATUS					 current
		DESCRIPTION			 " -- "
		::=  { macTestSwitchInfoEntry  131 }


	macTestSwitchUpScheOptMcsStaticsNum		 OBJECT-TYPE
		SYNTAX					 Integer32( 0 .. 100 )
		MAX-ACCESS			 read-create
		STATUS					 current
		DESCRIPTION			 " -- "
		::=  { macTestSwitchInfoEntry  132 }


	macTestSwitchQci1ScwSwitch		 OBJECT-TYPE
		SYNTAX					 INTEGER{ off(0),on(1)  }
		MAX-ACCESS			 read-create
		STATUS					 current
		DESCRIPTION			 " -- "
		::=  { macTestSwitchInfoEntry  133 }


	macTestSwitchQci2ScwSwitch		 OBJECT-TYPE
		SYNTAX					 INTEGER{ off(0),on(1)  }
		MAX-ACCESS			 read-create
		STATUS					 current
		DESCRIPTION			 " -- "
		::=  { macTestSwitchInfoEntry  134 }


	macTestSwitchQci1Qci2ScwSwitch		 OBJECT-TYPE
		SYNTAX					 INTEGER{ off(0),on(1)  }
		MAX-ACCESS			 read-create
		STATUS					 current
		DESCRIPTION			 " -- "
		::=  { macTestSwitchInfoEntry  135 }


	macTestSwitchDlAtuUlAckFirstBler		 OBJECT-TYPE
		SYNTAX					 Integer32( 0 .. 100 )
		MAX-ACCESS			 read-create
		STATUS					 current
		DESCRIPTION			 " -- "
		::=  { macTestSwitchInfoEntry  136 }


	macTestSwitchUlRetxPrbSwitch		 OBJECT-TYPE
		SYNTAX					 INTEGER{ off(0),on(1)  }
		MAX-ACCESS			 read-create
		STATUS					 current
		DESCRIPTION			 " -- "
		::=  { macTestSwitchInfoEntry  137 }


	macTestSwitchSrbDlScheNumSub0		 OBJECT-TYPE
		SYNTAX					 Integer32( 0 .. 20 )
		MAX-ACCESS			 read-create
		STATUS					 current
		DESCRIPTION			 " -- "
		::=  { macTestSwitchInfoEntry  138 }


	macTestSwitchSrbDlScheNumSub1		 OBJECT-TYPE
		SYNTAX					 Integer32( 0 .. 20 )
		MAX-ACCESS			 read-create
		STATUS					 current
		DESCRIPTION			 " -- "
		::=  { macTestSwitchInfoEntry  139 }


	macTestSwitchSrbDlScheNumSub3		 OBJECT-TYPE
		SYNTAX					 Integer32( 0 .. 20 )
		MAX-ACCESS			 read-create
		STATUS					 current
		DESCRIPTION			 " -- "
		::=  { macTestSwitchInfoEntry  140 }


	macTestSwitchSrbDlScheNumSub4		 OBJECT-TYPE
		SYNTAX					 Integer32( 0 .. 20 )
		MAX-ACCESS			 read-create
		STATUS					 current
		DESCRIPTION			 " -- "
		::=  { macTestSwitchInfoEntry  141 }


	macTestSwitchUlResConfSwitch		 OBJECT-TYPE
		SYNTAX					 INTEGER{ off(0),on(1)  }
		MAX-ACCESS			 read-create
		STATUS					 current
		DESCRIPTION			 " -- "
		::=  { macTestSwitchInfoEntry  142 }


	macTestSwitchInfoUpDownSubFLDownUeNumbpoi		 OBJECT-TYPE
		SYNTAX					 Integer32( 0 .. 30 )
		MAX-ACCESS			 read-create
		STATUS					 current
		DESCRIPTION			 " -- "
		::=  { macTestSwitchInfoEntry  143 }


	macTestSwitchInfoDlCchCfiNumbpoi		 OBJECT-TYPE
		SYNTAX					 Integer32( 1 .. 3 )
		MAX-ACCESS			 read-create
		STATUS					 current
		DESCRIPTION			 " -- "
		::=  { macTestSwitchInfoEntry  144 }


	macTestSwitchInfoUlMaxScheUeNumbpoi		 OBJECT-TYPE
		SYNTAX					 Integer32( 0 .. 30 )
		MAX-ACCESS			 read-create
		STATUS					 current
		DESCRIPTION			 " -- "
		::=  { macTestSwitchInfoEntry  145 }


	macTestSwitchInfoDlMaxScheUeNumbpoi		 OBJECT-TYPE
		SYNTAX					 Integer32( 0 .. 30 )
		MAX-ACCESS			 read-create
		STATUS					 current
		DESCRIPTION			 " -- "
		::=  { macTestSwitchInfoEntry  146 }


	macTestSwitchInfoCqiTm8RiTMSwitch		 OBJECT-TYPE
		SYNTAX					 INTEGER{ off(0),on(1)  }
		MAX-ACCESS			 read-create
		STATUS					 current
		DESCRIPTION			 " -- "
		::=  { macTestSwitchInfoEntry  152 }


	macTestSwitchVolteAnsweredLimitMcsSwitch		 OBJECT-TYPE
		SYNTAX					 INTEGER{ off(0),on(1)  }
		MAX-ACCESS			 read-create
		STATUS					 current
		DESCRIPTION			 " -- "
		::=  { macTestSwitchInfoEntry  154 }


	macTestSwitchVolteAnsweredPeriod		 OBJECT-TYPE
		SYNTAX					 Unsigned32( 1 .. 20 )
		MAX-ACCESS			 read-create
		STATUS					 current
		DESCRIPTION			 " -- "
		::=  { macTestSwitchInfoEntry  155 }


	macTestSwitchInfoUlVoipRetxFlag		 OBJECT-TYPE
		SYNTAX					 INTEGER{ off(0),auto(1),noAuto(2)  }
		MAX-ACCESS			 read-create
		STATUS					 current
		DESCRIPTION			 " -- "
		::=  { macTestSwitchInfoEntry  156 }


	macSwitchTestInfoTable		 OBJECT-TYPE
		SYNTAX					 SEQUENCE  OF	 MacSwitchTestInfoEntry
		MAX-ACCESS			 not-accessible
		STATUS					 current
		DESCRIPTION			 " -- "
		::=  { macSwitchNode  3 }


	macSwitchTestInfoEntry		 OBJECT-TYPE
		SYNTAX					 MacSwitchTestInfoEntry
		MAX-ACCESS			 not-accessible
		STATUS					 current
		DESCRIPTION			 " -- "
		INDEX						{ macSwitchTestInfoLcId }
		::=  { macSwitchTestInfoTable  1 }


	MacSwitchTestInfoEntry		 ::=  SEQUENCE {
		macSwitchTestInfoLcId					Integer32,
		macSwitchTestInfoRowStatus					RowStatus,
		macSwitchTestInfoDlBoSwitch					INTEGER,
		macSwitchTestInfoUlBoSwitch					INTEGER,
		macSwitchTestInfoRbIndex					Unsigned32,
		macSwitchTestInfoStartPos					Unsigned32,
		macSwitchTestInfoUeNum					Unsigned32,
		macSwitchTestInfoDlBoSize					Unsigned32,
		macSwitchTestInfoUlBoSize					Unsigned32,
		macSwitchTestInfoPdcpFreq					Unsigned32,
		macSwitchTestInfoPdcpPktNum					Unsigned32,
		macSwitchTestInfoPdcpPktLen					Unsigned32,
		macSwitchTestInfoPdcpDynamicPktLenSwitch					INTEGER,
		macSwitchTestInfoPdcpDynamicMinPktLen					Unsigned32,
		macSwitchTestInfoUlPrescheBatConsumpRef					INTEGER,
		macSwitchTestInfoUlPrescheTimeLimit					INTEGER,
		macSwitchTestInfoUlPreschePrbLimit					Unsigned32,
		macSwitchTestInfoActiveRrcPeriod					INTEGER,
		macTestSwitchInfoVoLTECdlStatPeriod					Integer32,
		macSwitchTestInfoRTPLossThreshold					Unsigned32,
		macSwitchTestInfoRohcFBNackThreshold					Unsigned32,
		macSwitchTestInfoAutoTransLog					INTEGER,
		macSwitchTestInfoPdcpAmOptimizeThr					Unsigned32,
		macSwitchTestInfoVipCntLmt					Unsigned32,
		macSwitchTestInfoTAReviseThre					Unsigned32,
		macSwitchTestInfoTAReviseLmt					Unsigned32,
		macSwitchTestInfoTCPDelayOpt					Unsigned32,
		macSwitchTestInfoRohcOptSwitch					INTEGER,
		macSwitchTestInfoL2Reserve					Unsigned32,
		macSwitchTestInfoRohcThreshold					Unsigned32,
		macSwitchTestInfoIpPacketThr					Unsigned32,
		macSwitchTestInfoUlPrescheAllPrbLimit					Unsigned32,
		macSwitchTestInfoUlPrescheTbSizeLimit					Unsigned32,
		macSwitchTestInfoUlPrescheInterval					Unsigned32,
		macSwitchTestInfoRlcMaxTransmitTimes					Unsigned32,
		macSwitchTestInfoTaPdcchOrderTimes					Unsigned32,
		macSwitchTestInfoTaPdcchOrderTimerLen					INTEGER,
		macStopLogByType					Unsigned32,
		macSwitchTestInfoUlPreschePrbNumMin					Unsigned32,
		macSwitchTestInfoTCPActiveAckSwitch					INTEGER,
		macSwitchTestInfoTCPActiveAckNumber					Unsigned32,
		macSwitchTestInfoTm8MuSuMimoSwitchTLS					INTEGER,
		macSwitchTestInfoUlMuMIMOSwitchTLS					INTEGER,
		macSwitchTestInfoDlFsSwitchTLS					INTEGER,
		macSwitchTestInfoDl8BitsQamTls					INTEGER,
		macSwitchTestInfoTm9MsmTLS					INTEGER,
		macSwitchTestInfoRiaSwitchTLS					INTEGER
		}


	macSwitchTestInfoLcId		 OBJECT-TYPE
		SYNTAX					 Integer32( 0 .. 23 )
		MAX-ACCESS			 not-accessible
		STATUS					 current
		DESCRIPTION			 " -- "
		::=  { macSwitchTestInfoEntry  1 }


	macSwitchTestInfoRowStatus		 OBJECT-TYPE
		SYNTAX					 RowStatus
		MAX-ACCESS			 read-create
		STATUS					 current
		DESCRIPTION			 " -- "
		::=  { macSwitchTestInfoEntry  2 }


	macSwitchTestInfoDlBoSwitch		 OBJECT-TYPE
		SYNTAX					 INTEGER{ off(0),on(1),dataon(2)  }
		MAX-ACCESS			 read-create
		STATUS					 current
		DESCRIPTION			 " -- "
		::=  { macSwitchTestInfoEntry  3 }


	macSwitchTestInfoUlBoSwitch		 OBJECT-TYPE
		SYNTAX					 INTEGER{ off(0),presche(1),bo(2),dltriggerpre(3),preboth(4)  }
		MAX-ACCESS			 read-create
		STATUS					 current
		DESCRIPTION			 " -- "
		::=  { macSwitchTestInfoEntry  4 }


	macSwitchTestInfoRbIndex		 OBJECT-TYPE
		SYNTAX					 Unsigned32( 3 .. 8 )
		MAX-ACCESS			 read-create
		STATUS					 current
		DESCRIPTION			 " -- "
		::=  { macSwitchTestInfoEntry  5 }


	macSwitchTestInfoStartPos		 OBJECT-TYPE
		SYNTAX					 Unsigned32( 0 .. 1199 )
		MAX-ACCESS			 read-create
		STATUS					 current
		DESCRIPTION			 " -- "
		::=  { macSwitchTestInfoEntry  6 }


	macSwitchTestInfoUeNum		 OBJECT-TYPE
		SYNTAX					 Unsigned32( 0 .. 1199 )
		MAX-ACCESS			 read-create
		STATUS					 current
		DESCRIPTION			 " -- "
		::=  { macSwitchTestInfoEntry  7 }


	macSwitchTestInfoDlBoSize		 OBJECT-TYPE
		SYNTAX					 Unsigned32( 0 .. 200000 )
		MAX-ACCESS			 read-create
		STATUS					 current
		DESCRIPTION			 " -- "
		::=  { macSwitchTestInfoEntry  8 }


	macSwitchTestInfoUlBoSize		 OBJECT-TYPE
		SYNTAX					 Unsigned32( 0 .. 63 )
		MAX-ACCESS			 read-create
		STATUS					 current
		DESCRIPTION			 " -- "
		::=  { macSwitchTestInfoEntry  9 }


	macSwitchTestInfoPdcpFreq		 OBJECT-TYPE
		SYNTAX					 Unsigned32( 0 .. 200 )
		MAX-ACCESS			 read-create
		STATUS					 current
		DESCRIPTION			 " -- "
		::=  { macSwitchTestInfoEntry  10 }


	macSwitchTestInfoPdcpPktNum		 OBJECT-TYPE
		SYNTAX					 Unsigned32( 1 .. 40 )
		MAX-ACCESS			 read-create
		STATUS					 current
		DESCRIPTION			 " -- "
		::=  { macSwitchTestInfoEntry  11 }


	macSwitchTestInfoPdcpPktLen		 OBJECT-TYPE
		SYNTAX					 Unsigned32( 1 .. 2000 )
		MAX-ACCESS			 read-create
		STATUS					 current
		DESCRIPTION			 " -- "
		::=  { macSwitchTestInfoEntry  12 }


	macSwitchTestInfoPdcpDynamicPktLenSwitch		 OBJECT-TYPE
		SYNTAX					 INTEGER{ off(0),on(1)  }
		MAX-ACCESS			 read-create
		STATUS					 current
		DESCRIPTION			 " -- "
		::=  { macSwitchTestInfoEntry  13 }


	macSwitchTestInfoPdcpDynamicMinPktLen		 OBJECT-TYPE
		SYNTAX					 Unsigned32( 1 .. 2000 )
		MAX-ACCESS			 read-create
		STATUS					 current
		DESCRIPTION			 " -- "
		::=  { macSwitchTestInfoEntry  14 }


	macSwitchTestInfoUlPrescheBatConsumpRef		 OBJECT-TYPE
		SYNTAX					 INTEGER{ off(0),on(1)  }
		MAX-ACCESS			 read-create
		STATUS					 current
		DESCRIPTION			 " -- "
		::=  { macSwitchTestInfoEntry  15 }


	macSwitchTestInfoUlPrescheTimeLimit		 OBJECT-TYPE
		SYNTAX					 INTEGER{ ms100(0),ms200(1),ms500(2),s1(3),s2(4),s5(5),s10(6),infinity(7),ms10(8),ms20(9),ms40(10),ms50(11),ms80(12)  }
		MAX-ACCESS			 read-create
		STATUS					 current
		DESCRIPTION			 " -- "
		::=  { macSwitchTestInfoEntry  16 }


	macSwitchTestInfoUlPreschePrbLimit		 OBJECT-TYPE
		SYNTAX					 Unsigned32( 1 .. 100 )
		MAX-ACCESS			 read-create
		STATUS					 current
		DESCRIPTION			 " -- "
		::=  { macSwitchTestInfoEntry  17 }


	macSwitchTestInfoActiveRrcPeriod		 OBJECT-TYPE
		SYNTAX					 INTEGER{ ms100(0),ms200(1),ms500(2),s1(3),s2(4),s5(5),s10(6)  }
		MAX-ACCESS			 read-create
		STATUS					 current
		DESCRIPTION			 " -- "
		::=  { macSwitchTestInfoEntry  18 }


	macTestSwitchInfoVoLTECdlStatPeriod		 OBJECT-TYPE
		SYNTAX					 Integer32( 1 .. 10 )
		MAX-ACCESS			 read-create
		STATUS					 current
		DESCRIPTION			 " -- "
		::=  { macSwitchTestInfoEntry  19 }


	macSwitchTestInfoRTPLossThreshold		 OBJECT-TYPE
		SYNTAX					 Unsigned32( 1 .. 50 )
		MAX-ACCESS			 read-create
		STATUS					 current
		DESCRIPTION			 " -- "
		::=  { macSwitchTestInfoEntry  20 }


	macSwitchTestInfoRohcFBNackThreshold		 OBJECT-TYPE
		SYNTAX					 Unsigned32( 1 .. 50 )
		MAX-ACCESS			 read-create
		STATUS					 current
		DESCRIPTION			 " -- "
		::=  { macSwitchTestInfoEntry  21 }


	macSwitchTestInfoAutoTransLog		 OBJECT-TYPE
		SYNTAX					 INTEGER{ off(0),on(1)  }
		MAX-ACCESS			 read-create
		STATUS					 current
		DESCRIPTION			 " -- "
		::=  { macSwitchTestInfoEntry  22 }


	macSwitchTestInfoPdcpAmOptimizeThr		 OBJECT-TYPE
		SYNTAX					 Unsigned32( 0 .. 4294967295 )
		MAX-ACCESS			 read-create
		STATUS					 current
		DESCRIPTION			 " -- "
		::=  { macSwitchTestInfoEntry  23 }


	macSwitchTestInfoVipCntLmt		 OBJECT-TYPE
		SYNTAX					 Unsigned32( 0 .. 100000 )
		MAX-ACCESS			 read-create
		STATUS					 current
		DESCRIPTION			 " -- "
		::=  { macSwitchTestInfoEntry  24 }


	macSwitchTestInfoTAReviseThre		 OBJECT-TYPE
		SYNTAX					 Unsigned32( 0 .. 60 )
		MAX-ACCESS			 read-create
		STATUS					 current
		DESCRIPTION			 " -- "
		::=  { macSwitchTestInfoEntry  25 }


	macSwitchTestInfoTAReviseLmt		 OBJECT-TYPE
		SYNTAX					 Unsigned32( 0 .. 10 )
		MAX-ACCESS			 read-create
		STATUS					 current
		DESCRIPTION			 " -- "
		::=  { macSwitchTestInfoEntry  26 }


	macSwitchTestInfoTCPDelayOpt		 OBJECT-TYPE
		SYNTAX					 Unsigned32( 0 .. 20000 )
		MAX-ACCESS			 read-create
		STATUS					 current
		DESCRIPTION			 " -- "
		::=  { macSwitchTestInfoEntry  27 }


	macSwitchTestInfoRohcOptSwitch		 OBJECT-TYPE
		SYNTAX					 INTEGER{ off(0),on(1)  }
		MAX-ACCESS			 read-create
		STATUS					 current
		DESCRIPTION			 " -- "
		::=  { macSwitchTestInfoEntry  28 }


	macSwitchTestInfoL2Reserve		 OBJECT-TYPE
		SYNTAX					 Unsigned32( 0 .. 4294967295 )
		MAX-ACCESS			 read-create
		STATUS					 current
		DESCRIPTION			 " -- "
		::=  { macSwitchTestInfoEntry  29 }


	macSwitchTestInfoRohcThreshold		 OBJECT-TYPE
		SYNTAX					 Unsigned32( 0 .. 1000 )
		MAX-ACCESS			 read-create
		STATUS					 current
		DESCRIPTION			 " -- "
		::=  { macSwitchTestInfoEntry  30 }


	macSwitchTestInfoIpPacketThr		 OBJECT-TYPE
		SYNTAX					 Unsigned32( 0 .. 255 )
		MAX-ACCESS			 read-create
		STATUS					 current
		DESCRIPTION			 " -- "
		::=  { macSwitchTestInfoEntry  31 }


	macSwitchTestInfoUlPrescheAllPrbLimit		 OBJECT-TYPE
		SYNTAX					 Unsigned32( 0 .. 100 )
		MAX-ACCESS			 read-create
		STATUS					 current
		DESCRIPTION			 " -- "
		::=  { macSwitchTestInfoEntry  32 }


	macSwitchTestInfoUlPrescheTbSizeLimit		 OBJECT-TYPE
		SYNTAX					 Unsigned32( 0 .. 80000 )
		MAX-ACCESS			 read-create
		STATUS					 current
		DESCRIPTION			 " -- "
		::=  { macSwitchTestInfoEntry  33 }


	macSwitchTestInfoUlPrescheInterval		 OBJECT-TYPE
		SYNTAX					 Unsigned32( 1 .. 100 )
		MAX-ACCESS			 read-create
		STATUS					 current
		DESCRIPTION			 " -- "
		::=  { macSwitchTestInfoEntry  34 }


	macSwitchTestInfoRlcMaxTransmitTimes		 OBJECT-TYPE
		SYNTAX					 Unsigned32( 1 .. 1000 )
		MAX-ACCESS			 read-create
		STATUS					 current
		DESCRIPTION			 " -- "
		::=  { macSwitchTestInfoEntry  36 }


	macSwitchTestInfoTaPdcchOrderTimes		 OBJECT-TYPE
		SYNTAX					 Unsigned32( 0 .. 10 )
		MAX-ACCESS			 read-create
		STATUS					 current
		DESCRIPTION			 " -- "
		::=  { macSwitchTestInfoEntry  37 }


	macSwitchTestInfoTaPdcchOrderTimerLen		 OBJECT-TYPE
		SYNTAX					 INTEGER{ ms200(0),ms300(1),ms500(2),s1(3),s2(4),s3(5),s4(6),s5(7),s6(8),s7(9),s8(10),s9(11)  }
		MAX-ACCESS			 read-create
		STATUS					 current
		DESCRIPTION			 " -- "
		::=  { macSwitchTestInfoEntry  38 }


	macStopLogByType		 OBJECT-TYPE
		SYNTAX					 Unsigned32( 0 .. 65535 )
		MAX-ACCESS			 read-create
		STATUS					 current
		DESCRIPTION			 " -- "
		::=  { macSwitchTestInfoEntry  40 }


	macSwitchTestInfoUlPreschePrbNumMin		 OBJECT-TYPE
		SYNTAX					 Unsigned32( 1 .. 10 )
		MAX-ACCESS			 read-create
		STATUS					 current
		DESCRIPTION			 " -- "
		::=  { macSwitchTestInfoEntry  45 }


	macSwitchTestInfoTCPActiveAckSwitch		 OBJECT-TYPE
		SYNTAX					 INTEGER{ off(0),on(1)  }
		MAX-ACCESS			 read-create
		STATUS					 current
		DESCRIPTION			 " -- "
		::=  { macSwitchTestInfoEntry  47 }


	macSwitchTestInfoTCPActiveAckNumber		 OBJECT-TYPE
		SYNTAX					 Unsigned32( 10 .. 100 )
		MAX-ACCESS			 read-create
		STATUS					 current
		DESCRIPTION			 " -- "
		::=  { macSwitchTestInfoEntry  48 }


	macSwitchTestInfoTm8MuSuMimoSwitchTLS		 OBJECT-TYPE
		SYNTAX					 INTEGER{ mumimo(0),sumimo(1),forbidtm8(2),sumuadapter(3)  }
		MAX-ACCESS			 read-create
		STATUS					 current
		DESCRIPTION			 " -- "
		::=  { macSwitchTestInfoEntry  51 }


	macSwitchTestInfoUlMuMIMOSwitchTLS		 OBJECT-TYPE
		SYNTAX					 INTEGER{ off(0),on(1)  }
		MAX-ACCESS			 read-create
		STATUS					 current
		DESCRIPTION			 " -- "
		::=  { macSwitchTestInfoEntry  52 }


	macSwitchTestInfoDlFsSwitchTLS		 OBJECT-TYPE
		SYNTAX					 INTEGER{ off(0),srson(1),cqion(2)  }
		MAX-ACCESS			 read-create
		STATUS					 current
		DESCRIPTION			 " -- "
		::=  { macSwitchTestInfoEntry  53 }


	macSwitchTestInfoDl8BitsQamTls		 OBJECT-TYPE
		SYNTAX					 INTEGER{ off(0),on(1)  }
		MAX-ACCESS			 read-create
		STATUS					 current
		DESCRIPTION			 " -- "
		::=  { macSwitchTestInfoEntry  54 }


	macSwitchTestInfoTm9MsmTLS		 OBJECT-TYPE
		SYNTAX					 INTEGER{ mumimo(0),sumimo(1),forbidtm9(2),mumimo4Stream2(3),sumimoAndMumimo2StreamAdaptive(4),mumimo4Stream1(5)  }
		MAX-ACCESS			 read-create
		STATUS					 current
		DESCRIPTION			 " -- "
		::=  { macSwitchTestInfoEntry  55 }


	macSwitchTestInfoRiaSwitchTLS		 OBJECT-TYPE
		SYNTAX					 INTEGER{ off(0),on(1)  }
		MAX-ACCESS			 read-create
		STATUS					 current
		DESCRIPTION			 " -- "
		::=  { macSwitchTestInfoEntry  56 }


	spsOptmzTable		 OBJECT-TYPE
		SYNTAX					 SEQUENCE  OF	 SpsOptmzEntry
		MAX-ACCESS			 not-accessible
		STATUS					 current
		DESCRIPTION			 " -- "
		::=  { macSwitchNode  4 }


	spsOptmzEntry		 OBJECT-TYPE
		SYNTAX					 SpsOptmzEntry
		MAX-ACCESS			 not-accessible
		STATUS					 current
		DESCRIPTION			 " -- "
		INDEX						{ spsOptmzLcId }
		::=  { spsOptmzTable  1 }


	SpsOptmzEntry		 ::=  SEQUENCE {
		spsOptmzLcId					Integer32,
		spsOptmzRowStatus					RowStatus,
		spsOptmzVPMPSThode					Unsigned32,
		spsOptmzVPMCPcktNum					Unsigned32,
		spsOptmzModifyTimer					Unsigned32,
		spsOptmzVoIPStatTimer					Unsigned32,
		spsOptmzUpAlgExplctRlThr					Unsigned32,
		spsOptmzUpAlgActvThr					Unsigned32,
		spsOptmzUpAlgPrsstDsThr					Unsigned32,
		spsOptmzDlnkPrsstActvThr					Unsigned32,
		spsOptmzDlnkPrsstIntThr					Unsigned32,
		spsOptmzDlnkPrsstDsThr					Unsigned32,
		spsOptmzDlSpsUserNum					Unsigned32,
		spsOptmzUpAlgPersistPrbLimitNum					Unsigned32,
		spsOptmzQci1NoSpsFlag					INTEGER,
		spsOptmzNoPktRptThr					Unsigned32,
		spsOptmzSrvccBlerThr					Unsigned32,
		spsOptmzSrvccBlerTag					INTEGER,
		spsOptmzUpSpsActiveMcsLowThr					Unsigned32,
		spsOptmzPacketLoseCopyNum					Integer32,
		spsOptmzDlLoseCopyFlag					INTEGER,
		spsOptmzUlLoseCopyFlag					INTEGER,
		spsOptmzPacketLoseTimer					Integer32,
		spsOptmzPacketLoseCopyUeNum					Integer32,
		spsOptmzAmrcSwitch					INTEGER,
		spsOptmzAmrcAjustPeriod					Integer32,
		spsOptmzAmrcRlcSegThr					Integer32,
		spsOptmzAmrcTgtRate					Integer32,
		spsOptmzRlcSegFlag					INTEGER,
		spsOptmzRlcSegLimit					Integer32,
		spsOptmzUlPacketRatio					Integer32,
		spsOptmzSidUlLoseCopyFlag					INTEGER,
		spsOptmzActiveUlLoseCopyFlag					INTEGER,
		spsOptmzMaxCopyUserNum					Unsigned32,
		spsOptmzMaxCopyPacketNum					Unsigned32,
		spsOptmzAmrcRlcSegThr1					Integer32
		}


	spsOptmzLcId		 OBJECT-TYPE
		SYNTAX					 Integer32( 0 .. 23 )
		MAX-ACCESS			 not-accessible
		STATUS					 current
		DESCRIPTION			 " -- "
		::=  { spsOptmzEntry  1 }


	spsOptmzRowStatus		 OBJECT-TYPE
		SYNTAX					 RowStatus
		MAX-ACCESS			 read-create
		STATUS					 current
		DESCRIPTION			 " -- "
		::=  { spsOptmzEntry  2 }


	spsOptmzVPMPSThode		 OBJECT-TYPE
		SYNTAX					 Unsigned32( 0 .. 560 )
		MAX-ACCESS			 read-create
		STATUS					 current
		DESCRIPTION			 " -- "
		::=  { spsOptmzEntry  3 }


	spsOptmzVPMCPcktNum		 OBJECT-TYPE
		SYNTAX					 Unsigned32( 0 .. 16 )
		MAX-ACCESS			 read-create
		STATUS					 current
		DESCRIPTION			 " -- "
		::=  { spsOptmzEntry  4 }


	spsOptmzModifyTimer		 OBJECT-TYPE
		SYNTAX					 Unsigned32( 100 .. 10000 )
		MAX-ACCESS			 read-create
		STATUS					 current
		DESCRIPTION			 " -- "
		::=  { spsOptmzEntry  5 }


	spsOptmzVoIPStatTimer		 OBJECT-TYPE
		SYNTAX					 Unsigned32( 1 .. 60 )
		MAX-ACCESS			 read-create
		STATUS					 current
		DESCRIPTION			 " -- "
		::=  { spsOptmzEntry  6 }


	spsOptmzUpAlgExplctRlThr		 OBJECT-TYPE
		SYNTAX					 Unsigned32( 1 .. 8 )
		MAX-ACCESS			 read-create
		STATUS					 current
		DESCRIPTION			 " -- "
		::=  { spsOptmzEntry  7 }


	spsOptmzUpAlgActvThr		 OBJECT-TYPE
		SYNTAX					 Unsigned32( 1 .. 8 )
		MAX-ACCESS			 read-create
		STATUS					 current
		DESCRIPTION			 " -- "
		::=  { spsOptmzEntry  8 }


	spsOptmzUpAlgPrsstDsThr		 OBJECT-TYPE
		SYNTAX					 Unsigned32( 0 .. 20000 )
		MAX-ACCESS			 read-create
		STATUS					 current
		DESCRIPTION			 " -- "
		::=  { spsOptmzEntry  9 }


	spsOptmzDlnkPrsstActvThr		 OBJECT-TYPE
		SYNTAX					 Unsigned32( 1 .. 6 )
		MAX-ACCESS			 read-create
		STATUS					 current
		DESCRIPTION			 " -- "
		::=  { spsOptmzEntry  10 }


	spsOptmzDlnkPrsstIntThr		 OBJECT-TYPE
		SYNTAX					 Unsigned32( 1 .. 6 )
		MAX-ACCESS			 read-create
		STATUS					 current
		DESCRIPTION			 " -- "
		::=  { spsOptmzEntry  11 }


	spsOptmzDlnkPrsstDsThr		 OBJECT-TYPE
		SYNTAX					 Unsigned32( 0 .. 20000 )
		MAX-ACCESS			 read-create
		STATUS					 current
		DESCRIPTION			 " -- "
		::=  { spsOptmzEntry  12 }


	spsOptmzDlSpsUserNum		 OBJECT-TYPE
		SYNTAX					 Unsigned32( 0 .. 50 )
		MAX-ACCESS			 read-create
		STATUS					 current
		DESCRIPTION			 " -- "
		::=  { spsOptmzEntry  13 }


	spsOptmzUpAlgPersistPrbLimitNum		 OBJECT-TYPE
		SYNTAX					 Unsigned32( 0 .. 100 )
		MAX-ACCESS			 read-create
		STATUS					 current
		DESCRIPTION			 " -- "
		::=  { spsOptmzEntry  14 }


	spsOptmzQci1NoSpsFlag		 OBJECT-TYPE
		SYNTAX					 INTEGER{ off(0),on(1)  }
		MAX-ACCESS			 read-create
		STATUS					 current
		DESCRIPTION			 " -- "
		::=  { spsOptmzEntry  15 }


	spsOptmzNoPktRptThr		 OBJECT-TYPE
		SYNTAX					 Unsigned32( 1 .. 120 )
		MAX-ACCESS			 read-create
		STATUS					 current
		DESCRIPTION			 " -- "
		::=  { spsOptmzEntry  16 }


	spsOptmzSrvccBlerThr		 OBJECT-TYPE
		SYNTAX					 Unsigned32( 0 .. 100 )
		MAX-ACCESS			 read-create
		STATUS					 current
		DESCRIPTION			 " -- "
		::=  { spsOptmzEntry  17 }


	spsOptmzSrvccBlerTag		 OBJECT-TYPE
		SYNTAX					 INTEGER{ off(0),on(1)  }
		MAX-ACCESS			 read-create
		STATUS					 current
		DESCRIPTION			 " -- "
		::=  { spsOptmzEntry  18 }


	spsOptmzUpSpsActiveMcsLowThr		 OBJECT-TYPE
		SYNTAX					 Unsigned32( 0 .. 15 )
		MAX-ACCESS			 read-create
		STATUS					 current
		DESCRIPTION			 " -- "
		::=  { spsOptmzEntry  19 }


	spsOptmzPacketLoseCopyNum		 OBJECT-TYPE
		SYNTAX					 Integer32( 0 .. 100 )
		MAX-ACCESS			 read-create
		STATUS					 current
		DESCRIPTION			 " -- "
		::=  { spsOptmzEntry  20 }


	spsOptmzDlLoseCopyFlag		 OBJECT-TYPE
		SYNTAX					 INTEGER{ off(0),on(1)  }
		MAX-ACCESS			 read-create
		STATUS					 current
		DESCRIPTION			 " -- "
		::=  { spsOptmzEntry  23 }


	spsOptmzUlLoseCopyFlag		 OBJECT-TYPE
		SYNTAX					 INTEGER{ off(0),on(1)  }
		MAX-ACCESS			 read-create
		STATUS					 current
		DESCRIPTION			 " -- "
		::=  { spsOptmzEntry  24 }


	spsOptmzPacketLoseTimer		 OBJECT-TYPE
		SYNTAX					 Integer32( 160 .. 320 )
		MAX-ACCESS			 read-create
		STATUS					 current
		DESCRIPTION			 " -- "
		::=  { spsOptmzEntry  25 }


	spsOptmzPacketLoseCopyUeNum		 OBJECT-TYPE
		SYNTAX					 Integer32( 1 .. 400 )
		MAX-ACCESS			 read-create
		STATUS					 current
		DESCRIPTION			 " -- "
		::=  { spsOptmzEntry  26 }


	spsOptmzAmrcSwitch		 OBJECT-TYPE
		SYNTAX					 INTEGER{ off(0),on(1)  }
		MAX-ACCESS			 read-create
		STATUS					 current
		DESCRIPTION			 " -- "
		::=  { spsOptmzEntry  27 }


	spsOptmzAmrcAjustPeriod		 OBJECT-TYPE
		SYNTAX					 Integer32( 1 .. 60 )
		MAX-ACCESS			 read-create
		STATUS					 current
		DESCRIPTION			 " -- "
		::=  { spsOptmzEntry  28 }


	spsOptmzAmrcRlcSegThr		 OBJECT-TYPE
		SYNTAX					 Integer32( 0 .. 80 )
		MAX-ACCESS			 read-create
		STATUS					 current
		DESCRIPTION			 " -- "
		::=  { spsOptmzEntry  29 }


	spsOptmzAmrcTgtRate		 OBJECT-TYPE
		SYNTAX					 Integer32( 0 .. 7 )
		MAX-ACCESS			 read-create
		STATUS					 current
		DESCRIPTION			 " -- "
		::=  { spsOptmzEntry  30 }


	spsOptmzRlcSegFlag		 OBJECT-TYPE
		SYNTAX					 INTEGER{ off(0),on(1)  }
		MAX-ACCESS			 read-create
		STATUS					 current
		DESCRIPTION			 " -- "
		::=  { spsOptmzEntry  31 }


	spsOptmzRlcSegLimit		 OBJECT-TYPE
		SYNTAX					 Integer32( 1 .. 8 )
		MAX-ACCESS			 read-create
		STATUS					 current
		DESCRIPTION			 " -- "
		::=  { spsOptmzEntry  32 }


	spsOptmzUlPacketRatio		 OBJECT-TYPE
		SYNTAX					 Integer32( 1 .. 100 )
		MAX-ACCESS			 read-create
		STATUS					 current
		DESCRIPTION			 " -- "
		::=  { spsOptmzEntry  33 }


	spsOptmzSidUlLoseCopyFlag		 OBJECT-TYPE
		SYNTAX					 INTEGER{ off(0),on(1)  }
		MAX-ACCESS			 read-create
		STATUS					 current
		DESCRIPTION			 " -- "
		::=  { spsOptmzEntry  34 }


	spsOptmzActiveUlLoseCopyFlag		 OBJECT-TYPE
		SYNTAX					 INTEGER{ off(0),on(1)  }
		MAX-ACCESS			 read-create
		STATUS					 current
		DESCRIPTION			 " -- "
		::=  { spsOptmzEntry  35 }


	spsOptmzMaxCopyUserNum		 OBJECT-TYPE
		SYNTAX					 Unsigned32( 0 .. 1000 )
		MAX-ACCESS			 read-create
		STATUS					 current
		DESCRIPTION			 " -- "
		::=  { spsOptmzEntry  36 }


	spsOptmzMaxCopyPacketNum		 OBJECT-TYPE
		SYNTAX					 Unsigned32( 0 .. 1000 )
		MAX-ACCESS			 read-create
		STATUS					 current
		DESCRIPTION			 " -- "
		::=  { spsOptmzEntry  37 }


	spsOptmzAmrcRlcSegThr1		 OBJECT-TYPE
		SYNTAX					 Integer32( 0 .. 80 )
		MAX-ACCESS			 read-create
		STATUS					 current
		DESCRIPTION			 " -- "
		::=  { spsOptmzEntry  38 }


	dlCAPowerControl		 OBJECT IDENTIFIER
		::=  { cellAlgorithm  8 }


	dlCAPowerControTable		 OBJECT-TYPE
		SYNTAX					 SEQUENCE  OF	 DlCAPowerControEntry
		MAX-ACCESS			 not-accessible
		STATUS					 current
		DESCRIPTION			 " -- "
		::=  { dlCAPowerControl  1 }


	dlCAPowerControEntry		 OBJECT-TYPE
		SYNTAX					 DlCAPowerControEntry
		MAX-ACCESS			 not-accessible
		STATUS					 current
		DESCRIPTION			 " -- "
		INDEX						{ dlCAPwrLcId }
		::=  { dlCAPowerControTable  1 }


	DlCAPowerControEntry		 ::=  SEQUENCE {
		dlCAPwrLcId					Integer32,
		dlCAPwrRowStatus					RowStatus,
		dlCAPwrPhichPowerCtrlSwitch					INTEGER,
		dlCAPwrUePdcchPowerCtrlSwitch					INTEGER,
		dlCAPwrDelta1Bf2Sfbc					Integer32,
		dlCAPwrDelta2Sdm2SfbcInTm3					Integer32,
		dlCAPwrDelta3Sdm2SfbcInTm4					Integer32,
		dlCAPwrDelta4Bf2SfbcInTm8					Integer32,
		dlCAPwrDeltaPowerMargin					Integer32,
		dlCAPwrDeltaPowerPhichMargin					Integer32,
		dlCAPwrPhichPowerDelta					Integer32,
		dlCAPwrTargetSinrPhich					Integer32,
		dlCAPwrTargetSinr1Cce1					Integer32,
		dlCAPwrTargetSinr1Cce2					Integer32,
		dlCAPwrTargetSinr1Cce3					Integer32,
		dlCAPwrTargetSinr2Cce1					Integer32,
		dlCAPwrTargetSinr2Cce2					Integer32,
		dlCAPwrTargetSinr2Cce3					Integer32,
		dlCAPwrTargetSinr4Cce1					Integer32,
		dlCAPwrTargetSinr4Cce2					Integer32,
		dlCAPwrTargetSinr4Cce3					Integer32,
		dlCAPwrTargetSinr8Cce1					Integer32,
		dlCAPwrTargetSinr8Cce2					Integer32,
		dlCAPwrTargetSinr8Cce3					Integer32,
		dlCAPwrPowerBoostCqi2					Integer32,
		dlCAPwrCellPdcchCceNum1					INTEGER,
		dlCAPwrCellPdcchCceNum2					INTEGER,
		dlCAPwrMaxPowerMargin					Integer32,
		dlCAPwrCce1CqiThreshHold					Integer32,
		dlCAPwrCce2CqiThreshHold					Integer32,
		dlCAPwrCce4CqiThreshHold					Integer32,
		dlCAPwrCceUsageTh1Low					Integer32,
		dlCAPwrCceUsageTh2Low					Integer32,
		dlCAPwrCceUsageTh1High					Integer32,
		dlCAPwrCceUsageTh2High					Integer32,
		dlCAPwrCfiTh1					Integer32,
		dlCAPwrMaxCfiNum					Integer32,
		dlCAPwrMaxDlCfiNum					Integer32,
		dlCAPwrCfiModT1					Unsigned32,
		dlCAPwrCfiModT2					Unsigned32,
		dlCAPwrCfiModT3					Unsigned32,
		dlCAPwrCchChooseCceOptimizeFlag					INTEGER,
		dlCAPwrCchChooseCceOptimizeLimit					Unsigned32,
		dlCAPwrCchDownCCeUpPower8to4					Unsigned32,
		dlCAPwrCchDownCCeUpPower4to2					Unsigned32,
		dlCAPwrCchDownCCeUpPower2to1					Unsigned32
		}


	dlCAPwrLcId		 OBJECT-TYPE
		SYNTAX					 Integer32( 0 .. 23 )
		MAX-ACCESS			 not-accessible
		STATUS					 current
		DESCRIPTION			 " -- "
		::=  { dlCAPowerControEntry  1 }


	dlCAPwrRowStatus		 OBJECT-TYPE
		SYNTAX					 RowStatus
		MAX-ACCESS			 read-create
		STATUS					 current
		DESCRIPTION			 " -- "
		::=  { dlCAPowerControEntry  2 }


	dlCAPwrPhichPowerCtrlSwitch		 OBJECT-TYPE
		SYNTAX					 INTEGER{ off(0),on(1)  }
		MAX-ACCESS			 read-create
		STATUS					 current
		DESCRIPTION			 " -- "
		::=  { dlCAPowerControEntry  3 }


	dlCAPwrUePdcchPowerCtrlSwitch		 OBJECT-TYPE
		SYNTAX					 INTEGER{ off(0),on(1)  }
		MAX-ACCESS			 read-create
		STATUS					 current
		DESCRIPTION			 " -- "
		::=  { dlCAPowerControEntry  4 }


	dlCAPwrDelta1Bf2Sfbc		 OBJECT-TYPE
		SYNTAX					 Integer32( 0 .. 100 )
		MAX-ACCESS			 read-create
		STATUS					 current
		DESCRIPTION			 " -- "
		::=  { dlCAPowerControEntry  5 }


	dlCAPwrDelta2Sdm2SfbcInTm3		 OBJECT-TYPE
		SYNTAX					 Integer32( 0 .. 100 )
		MAX-ACCESS			 read-create
		STATUS					 current
		DESCRIPTION			 " -- "
		::=  { dlCAPowerControEntry  6 }


	dlCAPwrDelta3Sdm2SfbcInTm4		 OBJECT-TYPE
		SYNTAX					 Integer32( 0 .. 100 )
		MAX-ACCESS			 read-create
		STATUS					 current
		DESCRIPTION			 " -- "
		::=  { dlCAPowerControEntry  7 }


	dlCAPwrDelta4Bf2SfbcInTm8		 OBJECT-TYPE
		SYNTAX					 Integer32( 0 .. 100 )
		MAX-ACCESS			 read-create
		STATUS					 current
		DESCRIPTION			 " -- "
		::=  { dlCAPowerControEntry  8 }


	dlCAPwrDeltaPowerMargin		 OBJECT-TYPE
		SYNTAX					 Integer32( 0 .. 50 )
		MAX-ACCESS			 read-create
		STATUS					 current
		DESCRIPTION			 " -- "
		::=  { dlCAPowerControEntry  9 }


	dlCAPwrDeltaPowerPhichMargin		 OBJECT-TYPE
		SYNTAX					 Integer32( 0 .. 50 )
		MAX-ACCESS			 read-create
		STATUS					 current
		DESCRIPTION			 " -- "
		::=  { dlCAPowerControEntry  10 }


	dlCAPwrPhichPowerDelta		 OBJECT-TYPE
		SYNTAX					 Integer32( 0 .. 200 )
		MAX-ACCESS			 read-create
		STATUS					 current
		DESCRIPTION			 " -- "
		::=  { dlCAPowerControEntry  11 }


	dlCAPwrTargetSinrPhich		 OBJECT-TYPE
		SYNTAX					 Integer32( -30 .. 250 )
		MAX-ACCESS			 read-create
		STATUS					 current
		DESCRIPTION			 " -- "
		::=  { dlCAPowerControEntry  12 }


	dlCAPwrTargetSinr1Cce1		 OBJECT-TYPE
		SYNTAX					 Integer32( -30 .. 250 )
		MAX-ACCESS			 read-create
		STATUS					 current
		DESCRIPTION			 " -- "
		::=  { dlCAPowerControEntry  13 }


	dlCAPwrTargetSinr1Cce2		 OBJECT-TYPE
		SYNTAX					 Integer32( -30 .. 250 )
		MAX-ACCESS			 read-create
		STATUS					 current
		DESCRIPTION			 " -- "
		::=  { dlCAPowerControEntry  14 }


	dlCAPwrTargetSinr1Cce3		 OBJECT-TYPE
		SYNTAX					 Integer32( -30 .. 250 )
		MAX-ACCESS			 read-create
		STATUS					 current
		DESCRIPTION			 " -- "
		::=  { dlCAPowerControEntry  15 }


	dlCAPwrTargetSinr2Cce1		 OBJECT-TYPE
		SYNTAX					 Integer32( -30 .. 250 )
		MAX-ACCESS			 read-create
		STATUS					 current
		DESCRIPTION			 " -- "
		::=  { dlCAPowerControEntry  16 }


	dlCAPwrTargetSinr2Cce2		 OBJECT-TYPE
		SYNTAX					 Integer32( -30 .. 250 )
		MAX-ACCESS			 read-create
		STATUS					 current
		DESCRIPTION			 " -- "
		::=  { dlCAPowerControEntry  17 }


	dlCAPwrTargetSinr2Cce3		 OBJECT-TYPE
		SYNTAX					 Integer32( -30 .. 250 )
		MAX-ACCESS			 read-create
		STATUS					 current
		DESCRIPTION			 " -- "
		::=  { dlCAPowerControEntry  18 }


	dlCAPwrTargetSinr4Cce1		 OBJECT-TYPE
		SYNTAX					 Integer32( -30 .. 250 )
		MAX-ACCESS			 read-create
		STATUS					 current
		DESCRIPTION			 " -- "
		::=  { dlCAPowerControEntry  19 }


	dlCAPwrTargetSinr4Cce2		 OBJECT-TYPE
		SYNTAX					 Integer32( -30 .. 250 )
		MAX-ACCESS			 read-create
		STATUS					 current
		DESCRIPTION			 " -- "
		::=  { dlCAPowerControEntry  20 }


	dlCAPwrTargetSinr4Cce3		 OBJECT-TYPE
		SYNTAX					 Integer32( -30 .. 250 )
		MAX-ACCESS			 read-create
		STATUS					 current
		DESCRIPTION			 " -- "
		::=  { dlCAPowerControEntry  21 }


	dlCAPwrTargetSinr8Cce1		 OBJECT-TYPE
		SYNTAX					 Integer32( -30 .. 250 )
		MAX-ACCESS			 read-create
		STATUS					 current
		DESCRIPTION			 " -- "
		::=  { dlCAPowerControEntry  22 }


	dlCAPwrTargetSinr8Cce2		 OBJECT-TYPE
		SYNTAX					 Integer32( -30 .. 250 )
		MAX-ACCESS			 read-create
		STATUS					 current
		DESCRIPTION			 " -- "
		::=  { dlCAPowerControEntry  23 }


	dlCAPwrTargetSinr8Cce3		 OBJECT-TYPE
		SYNTAX					 Integer32( -30 .. 250 )
		MAX-ACCESS			 read-create
		STATUS					 current
		DESCRIPTION			 " -- "
		::=  { dlCAPowerControEntry  24 }


	dlCAPwrPowerBoostCqi2		 OBJECT-TYPE
		SYNTAX					 Integer32( -60 .. 40 )
		MAX-ACCESS			 read-create
		STATUS					 current
		DESCRIPTION			 " -- "
		::=  { dlCAPowerControEntry  25 }


	dlCAPwrCellPdcchCceNum1		 OBJECT-TYPE
		SYNTAX					 INTEGER{ val4(4),val8(8)  }
		MAX-ACCESS			 read-create
		STATUS					 current
		DESCRIPTION			 " -- "
		::=  { dlCAPowerControEntry  26 }


	dlCAPwrCellPdcchCceNum2		 OBJECT-TYPE
		SYNTAX					 INTEGER{ val4(4),val8(8)  }
		MAX-ACCESS			 read-create
		STATUS					 current
		DESCRIPTION			 " -- "
		::=  { dlCAPowerControEntry  27 }


	dlCAPwrMaxPowerMargin		 OBJECT-TYPE
		SYNTAX					 Integer32( 0 .. 50 )
		MAX-ACCESS			 read-create
		STATUS					 current
		DESCRIPTION			 " -- "
		::=  { dlCAPowerControEntry  28 }


	dlCAPwrCce1CqiThreshHold		 OBJECT-TYPE
		SYNTAX					 Integer32( 1 .. 15 )
		MAX-ACCESS			 read-create
		STATUS					 current
		DESCRIPTION			 " -- "
		::=  { dlCAPowerControEntry  29 }


	dlCAPwrCce2CqiThreshHold		 OBJECT-TYPE
		SYNTAX					 Integer32( 1 .. 15 )
		MAX-ACCESS			 read-create
		STATUS					 current
		DESCRIPTION			 " -- "
		::=  { dlCAPowerControEntry  30 }


	dlCAPwrCce4CqiThreshHold		 OBJECT-TYPE
		SYNTAX					 Integer32( 1 .. 15 )
		MAX-ACCESS			 read-create
		STATUS					 current
		DESCRIPTION			 " -- "
		::=  { dlCAPowerControEntry  31 }


	dlCAPwrCceUsageTh1Low		 OBJECT-TYPE
		SYNTAX					 Integer32( 1 .. 70 )
		MAX-ACCESS			 read-create
		STATUS					 current
		DESCRIPTION			 " -- "
		::=  { dlCAPowerControEntry  32 }


	dlCAPwrCceUsageTh2Low		 OBJECT-TYPE
		SYNTAX					 Integer32( 1 .. 70 )
		MAX-ACCESS			 read-create
		STATUS					 current
		DESCRIPTION			 " -- "
		::=  { dlCAPowerControEntry  33 }


	dlCAPwrCceUsageTh1High		 OBJECT-TYPE
		SYNTAX					 Integer32( 70 .. 95 )
		MAX-ACCESS			 read-create
		STATUS					 current
		DESCRIPTION			 " -- "
		::=  { dlCAPowerControEntry  34 }


	dlCAPwrCceUsageTh2High		 OBJECT-TYPE
		SYNTAX					 Integer32( 70 .. 95 )
		MAX-ACCESS			 read-create
		STATUS					 current
		DESCRIPTION			 " -- "
		::=  { dlCAPowerControEntry  35 }


	dlCAPwrCfiTh1		 OBJECT-TYPE
		SYNTAX					 Integer32( 0 .. 100 )
		MAX-ACCESS			 read-create
		STATUS					 current
		DESCRIPTION			 " -- "
		::=  { dlCAPowerControEntry  36 }


	dlCAPwrMaxCfiNum		 OBJECT-TYPE
		SYNTAX					 Integer32( 1 .. 3 )
		MAX-ACCESS			 read-create
		STATUS					 current
		DESCRIPTION			 " -- "
		::=  { dlCAPowerControEntry  37 }


	dlCAPwrMaxDlCfiNum		 OBJECT-TYPE
		SYNTAX					 Integer32( 1 .. 3 )
		MAX-ACCESS			 read-create
		STATUS					 current
		DESCRIPTION			 " -- "
		::=  { dlCAPowerControEntry  38 }


	dlCAPwrCfiModT1		 OBJECT-TYPE
		SYNTAX					 Unsigned32( 40 .. 400 )
		MAX-ACCESS			 read-create
		STATUS					 current
		DESCRIPTION			 " -- "
		::=  { dlCAPowerControEntry  39 }


	dlCAPwrCfiModT2		 OBJECT-TYPE
		SYNTAX					 Unsigned32( 40 .. 400 )
		MAX-ACCESS			 read-create
		STATUS					 current
		DESCRIPTION			 " -- "
		::=  { dlCAPowerControEntry  40 }


	dlCAPwrCfiModT3		 OBJECT-TYPE
		SYNTAX					 Unsigned32( 40 .. 400 )
		MAX-ACCESS			 read-create
		STATUS					 current
		DESCRIPTION			 " -- "
		::=  { dlCAPowerControEntry  41 }


	dlCAPwrCchChooseCceOptimizeFlag		 OBJECT-TYPE
		SYNTAX					 INTEGER{ off(0),on(1)  }
		MAX-ACCESS			 read-create
		STATUS					 current
		DESCRIPTION			 " -- "
		::=  { dlCAPowerControEntry  42 }


	dlCAPwrCchChooseCceOptimizeLimit		 OBJECT-TYPE
		SYNTAX					 Unsigned32( 0 .. 100 )
		MAX-ACCESS			 read-create
		STATUS					 current
		DESCRIPTION			 " -- "
		::=  { dlCAPowerControEntry  43 }


	dlCAPwrCchDownCCeUpPower8to4		 OBJECT-TYPE
		SYNTAX					 Unsigned32( 0 .. 50 )
		MAX-ACCESS			 read-create
		STATUS					 current
		DESCRIPTION			 " -- "
		::=  { dlCAPowerControEntry  44 }


	dlCAPwrCchDownCCeUpPower4to2		 OBJECT-TYPE
		SYNTAX					 Unsigned32( 0 .. 50 )
		MAX-ACCESS			 read-create
		STATUS					 current
		DESCRIPTION			 " -- "
		::=  { dlCAPowerControEntry  45 }


	dlCAPwrCchDownCCeUpPower2to1		 OBJECT-TYPE
		SYNTAX					 Unsigned32( 0 .. 50 )
		MAX-ACCESS			 read-create
		STATUS					 current
		DESCRIPTION			 " -- "
		::=  { dlCAPowerControEntry  46 }


	softLicense		 OBJECT IDENTIFIER
		::=  { cellAlgorithm  9 }


	softLicenseTable		 OBJECT-TYPE
		SYNTAX					 SEQUENCE  OF	 SoftLicenseEntry
		MAX-ACCESS			 not-accessible
		STATUS					 current
		DESCRIPTION			 " -- "
		::=  { softLicense  1 }


	softLicenseEntry		 OBJECT-TYPE
		SYNTAX					 SoftLicenseEntry
		MAX-ACCESS			 not-accessible
		STATUS					 current
		DESCRIPTION			 " -- "
		INDEX						{ softLicenseLcId }
		::=  { softLicenseTable  1 }


	SoftLicenseEntry		 ::=  SEQUENCE {
		softLicenseLcId					Integer32,
		softLicenseRowStatus					RowStatus,
		softLicenseDlPrbNum					Integer32,
		softLicenseUlPrbNum					Integer32,
		softLicenseDlThroughput					Unsigned32,
		softLicenseUlThroughput					Unsigned32,
		softLicenseDlBucketT					Integer32,
		softLicenseUlBucketT					Integer32,
		softLicenseDlSfBalanceCoeff					Integer32,
		softLicenseUlSfBalanceCoeff					Integer32,
		softLicenseDlSfBalanceT					Integer32,
		softLicenseUlSfBalanceT					Integer32,
		softLicenseDlBalanceSwitch					INTEGER,
		softLicenseUlBalanceSwitch					INTEGER
		}


	softLicenseLcId		 OBJECT-TYPE
		SYNTAX					 Integer32( 0 .. 23 )
		MAX-ACCESS			 not-accessible
		STATUS					 current
		DESCRIPTION			 " -- "
		::=  { softLicenseEntry  1 }


	softLicenseRowStatus		 OBJECT-TYPE
		SYNTAX					 RowStatus
		MAX-ACCESS			 read-create
		STATUS					 current
		DESCRIPTION			 " -- "
		::=  { softLicenseEntry  2 }


	softLicenseDlPrbNum		 OBJECT-TYPE
		SYNTAX					 Integer32( 0 .. 100 )
		MAX-ACCESS			 read-create
		STATUS					 current
		DESCRIPTION			 " -- "
		::=  { softLicenseEntry  3 }


	softLicenseUlPrbNum		 OBJECT-TYPE
		SYNTAX					 Integer32( 0 .. 100 )
		MAX-ACCESS			 read-create
		STATUS					 current
		DESCRIPTION			 " -- "
		::=  { softLicenseEntry  4 }


	softLicenseDlThroughput		 OBJECT-TYPE
		SYNTAX					 Unsigned32( 5000 .. 200000 )
		MAX-ACCESS			 read-create
		STATUS					 current
		DESCRIPTION			 " -- "
		::=  { softLicenseEntry  5 }


	softLicenseUlThroughput		 OBJECT-TYPE
		SYNTAX					 Unsigned32( 5000 .. 200000 )
		MAX-ACCESS			 read-create
		STATUS					 current
		DESCRIPTION			 " -- "
		::=  { softLicenseEntry  6 }


	softLicenseDlBucketT		 OBJECT-TYPE
		SYNTAX					 Integer32( 0 .. 100 )
		MAX-ACCESS			 read-create
		STATUS					 current
		DESCRIPTION			 " -- "
		::=  { softLicenseEntry  7 }


	softLicenseUlBucketT		 OBJECT-TYPE
		SYNTAX					 Integer32( 0 .. 100 )
		MAX-ACCESS			 read-create
		STATUS					 current
		DESCRIPTION			 " -- "
		::=  { softLicenseEntry  8 }


	softLicenseDlSfBalanceCoeff		 OBJECT-TYPE
		SYNTAX					 Integer32( 100 .. 200 )
		MAX-ACCESS			 read-create
		STATUS					 current
		DESCRIPTION			 " -- "
		::=  { softLicenseEntry  9 }


	softLicenseUlSfBalanceCoeff		 OBJECT-TYPE
		SYNTAX					 Integer32( 100 .. 200 )
		MAX-ACCESS			 read-create
		STATUS					 current
		DESCRIPTION			 " -- "
		::=  { softLicenseEntry  10 }


	softLicenseDlSfBalanceT		 OBJECT-TYPE
		SYNTAX					 Integer32( 0 .. 100 )
		MAX-ACCESS			 read-create
		STATUS					 current
		DESCRIPTION			 " -- "
		::=  { softLicenseEntry  11 }


	softLicenseUlSfBalanceT		 OBJECT-TYPE
		SYNTAX					 Integer32( 0 .. 100 )
		MAX-ACCESS			 read-create
		STATUS					 current
		DESCRIPTION			 " -- "
		::=  { softLicenseEntry  12 }


	softLicenseDlBalanceSwitch		 OBJECT-TYPE
		SYNTAX					 INTEGER{ off(0),on(1)  }
		MAX-ACCESS			 read-create
		STATUS					 current
		DESCRIPTION			 " -- "
		::=  { softLicenseEntry  13 }


	softLicenseUlBalanceSwitch		 OBJECT-TYPE
		SYNTAX					 INTEGER{ off(0),on(1)  }
		MAX-ACCESS			 read-create
		STATUS					 current
		DESCRIPTION			 " -- "
		::=  { softLicenseEntry  14 }


	cellSoftLicenseTable		 OBJECT-TYPE
		SYNTAX					 SEQUENCE  OF	 CellSoftLicenseEntry
		MAX-ACCESS			 not-accessible
		STATUS					 current
		DESCRIPTION			 " -- "
		::=  { softLicense  2 }


	cellSoftLicenseEntry		 OBJECT-TYPE
		SYNTAX					 CellSoftLicenseEntry
		MAX-ACCESS			 not-accessible
		STATUS					 current
		DESCRIPTION			 " -- "
		INDEX						{ cellSoftLicenseLcId }
		::=  { cellSoftLicenseTable  1 }


	CellSoftLicenseEntry		 ::=  SEQUENCE {
		cellSoftLicenseLcId					Integer32,
		cellSoftLicenseRowStatus					RowStatus,
		cellSoftLicenseCombineEnhancedCell					INTEGER,
		cellSoftLicense932Fun					INTEGER,
		cellSoftLicenseRanSharing					INTEGER
		}


	cellSoftLicenseLcId		 OBJECT-TYPE
		SYNTAX					 Integer32( 0 .. 23 )
		MAX-ACCESS			 not-accessible
		STATUS					 current
		DESCRIPTION			 " -- "
		::=  { cellSoftLicenseEntry  1 }


	cellSoftLicenseRowStatus		 OBJECT-TYPE
		SYNTAX					 RowStatus
		MAX-ACCESS			 read-create
		STATUS					 current
		DESCRIPTION			 " -- "
		::=  { cellSoftLicenseEntry  2 }


	cellSoftLicenseCombineEnhancedCell		 OBJECT-TYPE
		SYNTAX					 INTEGER{ off(0),on(1)  }
		MAX-ACCESS			 read-create
		STATUS					 current
		DESCRIPTION			 " -- "
		::=  { cellSoftLicenseEntry  3 }


	cellSoftLicense932Fun		 OBJECT-TYPE
		SYNTAX					 INTEGER{ off(0),on(1)  }
		MAX-ACCESS			 read-create
		STATUS					 current
		DESCRIPTION			 " -- "
		::=  { cellSoftLicenseEntry  4 }


	cellSoftLicenseRanSharing		 OBJECT-TYPE
		SYNTAX					 INTEGER{ off(0),on(1)  }
		MAX-ACCESS			 read-create
		STATUS					 current
		DESCRIPTION			 " -- "
		::=  { cellSoftLicenseEntry  5 }


	lcc		 OBJECT IDENTIFIER
		::=  { cellAlgorithm  10 }


	lccTable		 OBJECT-TYPE
		SYNTAX					 SEQUENCE  OF	 LccEntry
		MAX-ACCESS			 not-accessible
		STATUS					 current
		DESCRIPTION			 " -- "
		::=  { lcc  1 }


	lccEntry		 OBJECT-TYPE
		SYNTAX					 LccEntry
		MAX-ACCESS			 not-accessible
		STATUS					 current
		DESCRIPTION			 " -- "
		INDEX						{ lccLcId }
		::=  { lccTable  1 }


	LccEntry		 ::=  SEQUENCE {
		lccLcId					Integer32,
		lccRowStatus					RowStatus,
		lccFilterCoeff					INTEGER,
		lccServeCellOff					INTEGER,
		lccNeighborCellQOff					INTEGER,
		lccAdjustAC					Integer32,
		lccProcessMethod1					INTEGER,
		lccProcessMethod2					INTEGER
		}


	lccLcId		 OBJECT-TYPE
		SYNTAX					 Integer32( 0 .. 23 )
		MAX-ACCESS			 not-accessible
		STATUS					 current
		DESCRIPTION			 " -- "
		::=  { lccEntry  1 }


	lccRowStatus		 OBJECT-TYPE
		SYNTAX					 RowStatus
		MAX-ACCESS			 read-create
		STATUS					 current
		DESCRIPTION			 " -- "
		::=  { lccEntry  2 }


	lccFilterCoeff		 OBJECT-TYPE
		SYNTAX					 INTEGER{ k0(0),k1(1),k2(2),k3(3),k4(4),k5(5),k6(6),k7(7),k8(8),k9(9),k11(10),k13(11),k15(12),k17(13),k19(14)  }
		MAX-ACCESS			 read-create
		STATUS					 current
		DESCRIPTION			 " -- "
		::=  { lccEntry  8 }


	lccServeCellOff		 OBJECT-TYPE
		SYNTAX					 INTEGER{ n24dB(0),n22dB(1),n20dB(2),n18dB(3),n16dB(4),n14dB(5),n12dB(6),n10dB(7),n8dB(8),n6dB(9),n5dB(10),n4dB(11),n3dB(12),n2dB(13),n1dB(14),p0dB(15),p1dB(16),p2dB(17),p3dB(18),p4dB(19),p5dB(20),p6dB(21),p8dB(22),p10dB(23),p12dB(24),p14dB(25),p16dB(26),p18dB(27),p20dB(28),p22dB(29),p24dB(30)  }
		MAX-ACCESS			 read-create
		STATUS					 current
		DESCRIPTION			 " -- "
		::=  { lccEntry  10 }


	lccNeighborCellQOff		 OBJECT-TYPE
		SYNTAX					 INTEGER{ n24dB(0),n22dB(1),n20dB(2),n18dB(3),n16dB(4),n14dB(5),n12dB(6),n10dB(7),n8dB(8),n6dB(9),n5dB(10),n4dB(11),n3dB(12),n2dB(13),n1dB(14),p0dB(15),p1dB(16),p2dB(17),p3dB(18),p4dB(19),p5dB(20),p6dB(21),p8dB(22),p10dB(23),p12dB(24),p14dB(25),p16dB(26),p18dB(27),p20dB(28),p22dB(29),p24dB(30)  }
		MAX-ACCESS			 read-create
		STATUS					 current
		DESCRIPTION			 " -- "
		::=  { lccEntry  11 }


	lccAdjustAC		 OBJECT-TYPE
		SYNTAX					 Integer32( 0 .. 255 )
		MAX-ACCESS			 read-create
		STATUS					 current
		DESCRIPTION			 " -- "
		::=  { lccEntry  12 }


	lccProcessMethod1		 OBJECT-TYPE
		SYNTAX					 INTEGER{ hc(0),deleteErab(1),close(7)  }
		MAX-ACCESS			 read-create
		STATUS					 current
		DESCRIPTION			 " -- "
		::=  { lccEntry  13 }


	lccProcessMethod2		 OBJECT-TYPE
		SYNTAX					 INTEGER{ hc(0),deleteErab(1),close(7)  }
		MAX-ACCESS			 read-create
		STATUS					 current
		DESCRIPTION			 " -- "
		::=  { lccEntry  14 }


	lbc40Fc		 OBJECT IDENTIFIER
		::=  { cellAlgorithm  11 }


	lbc40FcTable		 OBJECT-TYPE
		SYNTAX					 SEQUENCE  OF	 Lbc40FcEntry
		MAX-ACCESS			 not-accessible
		STATUS					 current
		DESCRIPTION			 " -- "
		::=  { lbc40Fc  1 }


	lbc40FcEntry		 OBJECT-TYPE
		SYNTAX					 Lbc40FcEntry
		MAX-ACCESS			 not-accessible
		STATUS					 current
		DESCRIPTION			 " -- "
		INDEX						{ lbc40FcLcId }
		::=  { lbc40FcTable  1 }


	Lbc40FcEntry		 ::=  SEQUENCE {
		lbc40FcLcId					Integer32,
		lbc40FcRowStatus					RowStatus,
		lbc40FcUlPrbDifferTh					Integer32,
		lbc40FcDlPrbDifferTh					Integer32,
		lbc40FcCpuDifferTh					Integer32,
		lbc40FcCpuLoadTag					INTEGER,
		lbc40FcFastHoDeltaTh					Integer32,
		lbc40FcHoUeChoseStrategy					INTEGER,
		lbc40FcUeListStrategy					INTEGER,
		lbc40FcUeListWithPrbUsageTag					INTEGER,
		lbc40FcUlLowestUePrbUsageTh					Integer32,
		lbc40FcDlLowestUePrbUsageTh					Integer32,
		lbcPpHcSuppressTimer					Unsigned32,
		lbc40FcStrategyRollbackTag					INTEGER,
		lbc40FcHoUeChoseStrategyPriority					Integer32,
		lbc40FcUeListWithPrbUsageStrategyPriority					Integer32,
		lbc40FcFobiddenQciStrategyPriority					Integer32,
		lbcUserNumTag					INTEGER,
		lbcUserNumThreshold					Unsigned32,
		lbcFastHoMaxUserNum					Integer32,
		lbcUserNumDifferTh					Integer32,
		lbc40FcFobiddenQciBitMap					BITS,
		lbcUsernodebswitch					INTEGER,
		lbcUserReDirectTag					INTEGER,
		lbcCacUserNumber					Unsigned32
		}


	lbc40FcLcId		 OBJECT-TYPE
		SYNTAX					 Integer32( 0 .. 23 )
		MAX-ACCESS			 not-accessible
		STATUS					 current
		DESCRIPTION			 " -- "
		::=  { lbc40FcEntry  1 }


	lbc40FcRowStatus		 OBJECT-TYPE
		SYNTAX					 RowStatus
		MAX-ACCESS			 read-create
		STATUS					 current
		DESCRIPTION			 " -- "
		::=  { lbc40FcEntry  2 }


	lbc40FcUlPrbDifferTh		 OBJECT-TYPE
		SYNTAX					 Integer32( 0 .. 100 )
		MAX-ACCESS			 read-create
		STATUS					 current
		DESCRIPTION			 " -- "
		::=  { lbc40FcEntry  7 }


	lbc40FcDlPrbDifferTh		 OBJECT-TYPE
		SYNTAX					 Integer32( 0 .. 100 )
		MAX-ACCESS			 read-create
		STATUS					 current
		DESCRIPTION			 " -- "
		::=  { lbc40FcEntry  8 }


	lbc40FcCpuDifferTh		 OBJECT-TYPE
		SYNTAX					 Integer32( 0 .. 100 )
		MAX-ACCESS			 read-create
		STATUS					 current
		DESCRIPTION			 " -- "
		::=  { lbc40FcEntry  9 }


	lbc40FcCpuLoadTag		 OBJECT-TYPE
		SYNTAX					 INTEGER{ off(0),on(1)  }
		MAX-ACCESS			 read-create
		STATUS					 current
		DESCRIPTION			 " -- "
		::=  { lbc40FcEntry  11 }


	lbc40FcFastHoDeltaTh		 OBJECT-TYPE
		SYNTAX					 Integer32( 0 .. 100 )
		MAX-ACCESS			 read-create
		STATUS					 current
		DESCRIPTION			 " -- "
		::=  { lbc40FcEntry  14 }


	lbc40FcHoUeChoseStrategy		 OBJECT-TYPE
		SYNTAX					 INTEGER{ a2AndA4(0),a4only(1)  }
		MAX-ACCESS			 read-create
		STATUS					 current
		DESCRIPTION			 " -- "
		::=  { lbc40FcEntry  15 }


	lbc40FcUeListStrategy		 OBJECT-TYPE
		SYNTAX					 INTEGER{ prbUsageRate(0),qciPriAndPrbUsageRate(1)  }
		MAX-ACCESS			 read-create
		STATUS					 current
		DESCRIPTION			 " -- "
		::=  { lbc40FcEntry  16 }


	lbc40FcUeListWithPrbUsageTag		 OBJECT-TYPE
		SYNTAX					 INTEGER{ off(0),on(1)  }
		MAX-ACCESS			 read-create
		STATUS					 current
		DESCRIPTION			 " -- "
		::=  { lbc40FcEntry  17 }


	lbc40FcUlLowestUePrbUsageTh		 OBJECT-TYPE
		SYNTAX					 Integer32( 0 .. 100 )
		MAX-ACCESS			 read-create
		STATUS					 current
		DESCRIPTION			 " -- "
		::=  { lbc40FcEntry  18 }


	lbc40FcDlLowestUePrbUsageTh		 OBJECT-TYPE
		SYNTAX					 Integer32( 0 .. 100 )
		MAX-ACCESS			 read-create
		STATUS					 current
		DESCRIPTION			 " -- "
		::=  { lbc40FcEntry  19 }


	lbcPpHcSuppressTimer		 OBJECT-TYPE
		SYNTAX					 Unsigned32( 0 .. 65535 )
		MAX-ACCESS			 read-create
		STATUS					 current
		DESCRIPTION			 " -- "
		::=  { lbc40FcEntry  22 }


	lbc40FcStrategyRollbackTag		 OBJECT-TYPE
		SYNTAX					 INTEGER{ off(0),on(1)  }
		MAX-ACCESS			 read-create
		STATUS					 current
		DESCRIPTION			 " -- "
		::=  { lbc40FcEntry  23 }


	lbc40FcHoUeChoseStrategyPriority		 OBJECT-TYPE
		SYNTAX					 Integer32( 1 .. 3 )
		MAX-ACCESS			 read-create
		STATUS					 current
		DESCRIPTION			 " -- "
		::=  { lbc40FcEntry  24 }


	lbc40FcUeListWithPrbUsageStrategyPriority		 OBJECT-TYPE
		SYNTAX					 Integer32( 1 .. 3 )
		MAX-ACCESS			 read-create
		STATUS					 current
		DESCRIPTION			 " -- "
		::=  { lbc40FcEntry  25 }


	lbc40FcFobiddenQciStrategyPriority		 OBJECT-TYPE
		SYNTAX					 Integer32( 1 .. 3 )
		MAX-ACCESS			 read-create
		STATUS					 current
		DESCRIPTION			 " -- "
		::=  { lbc40FcEntry  26 }


	lbcUserNumTag		 OBJECT-TYPE
		SYNTAX					 INTEGER{ off(0),on(1)  }
		MAX-ACCESS			 read-create
		STATUS					 current
		DESCRIPTION			 " -- "
		::=  { lbc40FcEntry  27 }


	lbcUserNumThreshold		 OBJECT-TYPE
		SYNTAX					 Unsigned32( 1 .. 2000 )
		MAX-ACCESS			 read-create
		STATUS					 current
		DESCRIPTION			 " -- "
		::=  { lbc40FcEntry  28 }


	lbcFastHoMaxUserNum		 OBJECT-TYPE
		SYNTAX					 Integer32( 1 .. 50 )
		MAX-ACCESS			 read-create
		STATUS					 current
		DESCRIPTION			 " -- "
		::=  { lbc40FcEntry  29 }


	lbcUserNumDifferTh		 OBJECT-TYPE
		SYNTAX					 Integer32( 1 .. 100 )
		MAX-ACCESS			 read-create
		STATUS					 current
		DESCRIPTION			 " -- "
		::=  { lbc40FcEntry  30 }


	lbc40FcFobiddenQciBitMap		 OBJECT-TYPE
		SYNTAX					 BITS{ qci1(0),qci2(1),qci3(2),qci4(3),qci5(4)  }
		MAX-ACCESS			 read-create
		STATUS					 current
		DESCRIPTION			 " -- "
		::=  { lbc40FcEntry  31 }


	lbcUsernodebswitch		 OBJECT-TYPE
		SYNTAX					 INTEGER{ off(0),on(1)  }
		MAX-ACCESS			 read-create
		STATUS					 current
		DESCRIPTION			 " -- "
		::=  { lbc40FcEntry  32 }


	lbcUserReDirectTag		 OBJECT-TYPE
		SYNTAX					 INTEGER{ off(0),on(1)  }
		MAX-ACCESS			 read-create
		STATUS					 current
		DESCRIPTION			 " -- "
		::=  { lbc40FcEntry  33 }


	lbcCacUserNumber		 OBJECT-TYPE
		SYNTAX					 Unsigned32( 1 .. 1200 )
		MAX-ACCESS			 read-create
		STATUS					 current
		DESCRIPTION			 " -- "
		::=  { lbc40FcEntry  35 }


	dlPowerAlgorithmControl		 OBJECT IDENTIFIER
		::=  { cellAlgorithm  12 }


	dlPATTable		 OBJECT-TYPE
		SYNTAX					 SEQUENCE  OF	 DlPATEntry
		MAX-ACCESS			 not-accessible
		STATUS					 current
		DESCRIPTION			 " -- "
		::=  { dlPowerAlgorithmControl  1 }


	dlPATEntry		 OBJECT-TYPE
		SYNTAX					 DlPATEntry
		MAX-ACCESS			 not-accessible
		STATUS					 current
		DESCRIPTION			 " -- "
		INDEX						{ dlPATLcId }
		::=  { dlPATTable  1 }


	DlPATEntry		 ::=  SEQUENCE {
		dlPATLcId					Integer32,
		dlPATRowStatus					RowStatus,
		dlPATPadynschuSwitch					INTEGER,
		dlPATPaDrb					INTEGER,
		dlPATPaSrb					INTEGER,
		dlPATTimerupdatepower					Integer32,
		dlPATFilterfactor					Integer32,
		dlPATSpeeffthred1TM7					Integer32,
		dlPATSpeeffthred2TM7					Integer32,
		dlPATSpeeffthred1TM8					Integer32,
		dlPATSpeeffthred2TM8					Integer32,
		dlPATSpeeffthred1QPSK					Integer32,
		dlPATSpeeffthred2QPSK					Integer32,
		dlPATDeltapowerup					INTEGER
		}


	dlPATLcId		 OBJECT-TYPE
		SYNTAX					 Integer32( 0 .. 23 )
		MAX-ACCESS			 not-accessible
		STATUS					 current
		DESCRIPTION			 " -- "
		::=  { dlPATEntry  1 }


	dlPATRowStatus		 OBJECT-TYPE
		SYNTAX					 RowStatus
		MAX-ACCESS			 read-create
		STATUS					 current
		DESCRIPTION			 " -- "
		::=  { dlPATEntry  2 }


	dlPATPadynschuSwitch		 OBJECT-TYPE
		SYNTAX					 INTEGER{ off(0),on(1)  }
		MAX-ACCESS			 read-create
		STATUS					 current
		DESCRIPTION			 " -- "
		::=  { dlPATEntry  3 }


	dlPATPaDrb		 OBJECT-TYPE
		SYNTAX					 INTEGER{ n6dB(0),n4dot77dB(1),n3dB(2),n1dot77dB(3),p0dB(4),p1dB(5),p2dB(6),p3dB(7)  }
		MAX-ACCESS			 read-create
		STATUS					 current
		DESCRIPTION			 " -- "
		::=  { dlPATEntry  4 }


	dlPATPaSrb		 OBJECT-TYPE
		SYNTAX					 INTEGER{ n6dB(0),n4dot77dB(1),n3dB(2),n1dot77dB(3),p0dB(4),p1dB(5),p2dB(6),p3dB(7)  }
		MAX-ACCESS			 read-create
		STATUS					 current
		DESCRIPTION			 " -- "
		::=  { dlPATEntry  5 }


	dlPATTimerupdatepower		 OBJECT-TYPE
		SYNTAX					 Integer32( 200 .. 2000 )
		MAX-ACCESS			 read-create
		STATUS					 current
		DESCRIPTION			 " -- "
		::=  { dlPATEntry  6 }


	dlPATFilterfactor		 OBJECT-TYPE
		SYNTAX					 Integer32( 0 .. 1000 )
		MAX-ACCESS			 read-create
		STATUS					 current
		DESCRIPTION			 " -- "
		::=  { dlPATEntry  7 }


	dlPATSpeeffthred1TM7		 OBJECT-TYPE
		SYNTAX					 Integer32( 0 .. 50000 )
		MAX-ACCESS			 read-create
		STATUS					 current
		DESCRIPTION			 " -- "
		::=  { dlPATEntry  8 }


	dlPATSpeeffthred2TM7		 OBJECT-TYPE
		SYNTAX					 Integer32( 0 .. 50000 )
		MAX-ACCESS			 read-create
		STATUS					 current
		DESCRIPTION			 " -- "
		::=  { dlPATEntry  9 }


	dlPATSpeeffthred1TM8		 OBJECT-TYPE
		SYNTAX					 Integer32( 0 .. 50000 )
		MAX-ACCESS			 read-create
		STATUS					 current
		DESCRIPTION			 " -- "
		::=  { dlPATEntry  10 }


	dlPATSpeeffthred2TM8		 OBJECT-TYPE
		SYNTAX					 Integer32( 0 .. 50000 )
		MAX-ACCESS			 read-create
		STATUS					 current
		DESCRIPTION			 " -- "
		::=  { dlPATEntry  11 }


	dlPATSpeeffthred1QPSK		 OBJECT-TYPE
		SYNTAX					 Integer32( 0 .. 50000 )
		MAX-ACCESS			 read-create
		STATUS					 current
		DESCRIPTION			 " -- "
		::=  { dlPATEntry  12 }


	dlPATSpeeffthred2QPSK		 OBJECT-TYPE
		SYNTAX					 Integer32( 0 .. 50000 )
		MAX-ACCESS			 read-create
		STATUS					 current
		DESCRIPTION			 " -- "
		::=  { dlPATEntry  13 }


	dlPATDeltapowerup		 OBJECT-TYPE
		SYNTAX					 INTEGER{ dB0(0),dB1(1),dB2(2),dB3(3)  }
		MAX-ACCESS			 read-create
		STATUS					 current
		DESCRIPTION			 " -- "
		::=  { dlPATEntry  14 }


	lmc		 OBJECT IDENTIFIER
		::=  { cellAlgorithm  13 }


	lmcTable		 OBJECT-TYPE
		SYNTAX					 SEQUENCE  OF	 LmcEntry
		MAX-ACCESS			 not-accessible
		STATUS					 current
		DESCRIPTION			 " -- "
		::=  { lmc  1 }


	lmcEntry		 OBJECT-TYPE
		SYNTAX					 LmcEntry
		MAX-ACCESS			 not-accessible
		STATUS					 current
		DESCRIPTION			 " -- "
		INDEX						{ lmcLcId }
		::=  { lmcTable  1 }


	LmcEntry		 ::=  SEQUENCE {
		lmcLcId					Integer32,
		lmcRowStatus					RowStatus,
		lmclccAlgorithmTag					INTEGER,
		lmclbc40FcAlgorithmTag					INTEGER,
		lmcUlCongestionTh					Integer32,
		lmcDlCongestionTh					Integer32,
		lmcUlCongestRestoreTh					Integer32,
		lmcDlCongestRestoreTh					Integer32,
		lmcUlPrbHighLoadTh					Integer32,
		lmcDlPrbHighLoadTh					Integer32,
		lmcCpuHighLoadTh					Integer32,
		lmcUlPrbPreAlarmTh					Integer32,
		lmcDlPrbPreAlarmTh					Integer32,
		lmcUlPrbRestoreTh					Integer32,
		lmcDlPrbRestroeTh					Integer32,
		lmcLccLoadDetectPrd					Unsigned32,
		lmcScLoadDetectPrd					Unsigned32,
		lmcResStateUpdatePeriod					INTEGER,
		lmcAdjCellNum					Integer32,
		lmcInterRatLoadBalanceTag					INTEGER,
		lmcVoiceNumTag					INTEGER,
		lmcVoiceNumThreshold					Unsigned32,
		lmcVoiceNumRestoreTh					Unsigned32,
		lmcIntraVoiceLbTag					INTEGER,
		lmcIntreVoiceLbTag					INTEGER,
		lmcPrbCongestionTag					INTEGER,
		lmcPrbUlCongestionTh					Integer32,
		lmcPrbDlCongestionTh					Integer32,
		lmcPrbUlCongestRestoreTh					Integer32,
		lmcPrbDlCongestRestoreTh					Integer32,
		lmcPrbCongestionDetectDuration					Unsigned32,
		lmcPrbCongestionRestoreDetectDuration					Unsigned32,
		lmcCongestionExecutePrd					Unsigned32,
		lmcMlbAlgorithmTag					INTEGER,
		lmcMlbLoadDetectPrd					Unsigned32,
		lmcMlbOcnAdjustUpperLimit					Integer32,
		lmcMlbOcnAdjustLowerLimit					Integer32,
		lmcMlbOcnAdjustMaxNum					Integer32,
		lmcMlbHighLoadThDl					Integer32,
		lmcMlbHighLoadThUl					Integer32,
		lmcMlbLoadRestoreThDl					Integer32,
		lmcMlbLoadRestoreThUl					Integer32,
		lmcMlbAdjCellJudgeTimer					Unsigned32,
		lmcMlbParaBackoffTag					INTEGER,
		lmcMlbBackoffMonitorTime					Unsigned32,
		lmcMlbAdjustProtectTh					Integer32,
		lmcMlbTrueAdjCellJudge					INTEGER,
		lmcMlbMrDeltaRsrp					Integer32,
		lmcMlbMrDeltaRsrpRatio					Integer32,
		lmcMlbMrEstimatePrd					Unsigned32,
		lmcPucchTag					INTEGER,
		lmcPucchThreshold					Integer32,
		lmcCacUlPrbLoadTh					Integer32,
		lmcCacDlPrbLoadTh					Integer32
		}


	lmcLcId		 OBJECT-TYPE
		SYNTAX					 Integer32( 0 .. 23 )
		MAX-ACCESS			 not-accessible
		STATUS					 current
		DESCRIPTION			 " -- "
		::=  { lmcEntry  1 }


	lmcRowStatus		 OBJECT-TYPE
		SYNTAX					 RowStatus
		MAX-ACCESS			 read-create
		STATUS					 current
		DESCRIPTION			 " -- "
		::=  { lmcEntry  2 }


	lmclccAlgorithmTag		 OBJECT-TYPE
		SYNTAX					 INTEGER{ off(0),on(1)  }
		MAX-ACCESS			 read-create
		STATUS					 current
		DESCRIPTION			 " -- "
		::=  { lmcEntry  3 }


	lmclbc40FcAlgorithmTag		 OBJECT-TYPE
		SYNTAX					 INTEGER{ off(0),on(1)  }
		MAX-ACCESS			 read-create
		STATUS					 current
		DESCRIPTION			 " -- "
		::=  { lmcEntry  4 }


	lmcUlCongestionTh		 OBJECT-TYPE
		SYNTAX					 Integer32( 0 .. 100 )
		MAX-ACCESS			 read-create
		STATUS					 current
		DESCRIPTION			 " -- "
		::=  { lmcEntry  6 }


	lmcDlCongestionTh		 OBJECT-TYPE
		SYNTAX					 Integer32( 0 .. 100 )
		MAX-ACCESS			 read-create
		STATUS					 current
		DESCRIPTION			 " -- "
		::=  { lmcEntry  7 }


	lmcUlCongestRestoreTh		 OBJECT-TYPE
		SYNTAX					 Integer32( 0 .. 100 )
		MAX-ACCESS			 read-create
		STATUS					 current
		DESCRIPTION			 " -- "
		::=  { lmcEntry  8 }


	lmcDlCongestRestoreTh		 OBJECT-TYPE
		SYNTAX					 Integer32( 0 .. 100 )
		MAX-ACCESS			 read-create
		STATUS					 current
		DESCRIPTION			 " -- "
		::=  { lmcEntry  9 }


	lmcUlPrbHighLoadTh		 OBJECT-TYPE
		SYNTAX					 Integer32( 0 .. 100 )
		MAX-ACCESS			 read-create
		STATUS					 current
		DESCRIPTION			 " -- "
		::=  { lmcEntry  10 }


	lmcDlPrbHighLoadTh		 OBJECT-TYPE
		SYNTAX					 Integer32( 0 .. 100 )
		MAX-ACCESS			 read-create
		STATUS					 current
		DESCRIPTION			 " -- "
		::=  { lmcEntry  11 }


	lmcCpuHighLoadTh		 OBJECT-TYPE
		SYNTAX					 Integer32( 0 .. 100 )
		MAX-ACCESS			 read-create
		STATUS					 current
		DESCRIPTION			 " -- "
		::=  { lmcEntry  12 }


	lmcUlPrbPreAlarmTh		 OBJECT-TYPE
		SYNTAX					 Integer32( 0 .. 100 )
		MAX-ACCESS			 read-create
		STATUS					 current
		DESCRIPTION			 " -- "
		::=  { lmcEntry  13 }


	lmcDlPrbPreAlarmTh		 OBJECT-TYPE
		SYNTAX					 Integer32( 0 .. 100 )
		MAX-ACCESS			 read-create
		STATUS					 current
		DESCRIPTION			 " -- "
		::=  { lmcEntry  14 }


	lmcUlPrbRestoreTh		 OBJECT-TYPE
		SYNTAX					 Integer32( 0 .. 100 )
		MAX-ACCESS			 read-create
		STATUS					 current
		DESCRIPTION			 " -- "
		::=  { lmcEntry  15 }


	lmcDlPrbRestroeTh		 OBJECT-TYPE
		SYNTAX					 Integer32( 0 .. 100 )
		MAX-ACCESS			 read-create
		STATUS					 current
		DESCRIPTION			 " -- "
		::=  { lmcEntry  16 }


	lmcLccLoadDetectPrd		 OBJECT-TYPE
		SYNTAX					 Unsigned32( 0 .. 4294967295 )
		MAX-ACCESS			 read-create
		STATUS					 current
		DESCRIPTION			 " -- "
		::=  { lmcEntry  17 }


	lmcScLoadDetectPrd		 OBJECT-TYPE
		SYNTAX					 Unsigned32( 1 .. 65535 )
		MAX-ACCESS			 read-create
		STATUS					 current
		DESCRIPTION			 " -- "
		::=  { lmcEntry  18 }


	lmcResStateUpdatePeriod		 OBJECT-TYPE
		SYNTAX					 INTEGER{ lmcOneThousandMs(0),lmcTwoThousandMs(1),lmcFiveThousandMs(2),lmcTenThousandMs(3)  }
		MAX-ACCESS			 read-create
		STATUS					 current
		DESCRIPTION			 " -- "
		::=  { lmcEntry  19 }


	lmcAdjCellNum		 OBJECT-TYPE
		SYNTAX					 Integer32( 1 .. 10 )
		MAX-ACCESS			 read-create
		STATUS					 current
		DESCRIPTION			 " -- "
		::=  { lmcEntry  21 }


	lmcInterRatLoadBalanceTag		 OBJECT-TYPE
		SYNTAX					 INTEGER{ off(0),on(1)  }
		MAX-ACCESS			 read-create
		STATUS					 current
		DESCRIPTION			 " -- "
		::=  { lmcEntry  22 }


	lmcVoiceNumTag		 OBJECT-TYPE
		SYNTAX					 INTEGER{ off(0),on(1)  }
		MAX-ACCESS			 read-create
		STATUS					 current
		DESCRIPTION			 " -- "
		::=  { lmcEntry  24 }


	lmcVoiceNumThreshold		 OBJECT-TYPE
		SYNTAX					 Unsigned32( 1 .. 1000 )
		MAX-ACCESS			 read-create
		STATUS					 current
		DESCRIPTION			 " -- "
		::=  { lmcEntry  25 }


	lmcVoiceNumRestoreTh		 OBJECT-TYPE
		SYNTAX					 Unsigned32( 1 .. 1000 )
		MAX-ACCESS			 read-create
		STATUS					 current
		DESCRIPTION			 " -- "
		::=  { lmcEntry  26 }


	lmcIntraVoiceLbTag		 OBJECT-TYPE
		SYNTAX					 INTEGER{ off(0),on(1)  }
		MAX-ACCESS			 read-create
		STATUS					 current
		DESCRIPTION			 " -- "
		::=  { lmcEntry  27 }


	lmcIntreVoiceLbTag		 OBJECT-TYPE
		SYNTAX					 INTEGER{ off(0),on(1)  }
		MAX-ACCESS			 read-create
		STATUS					 current
		DESCRIPTION			 " -- "
		::=  { lmcEntry  28 }


	lmcPrbCongestionTag		 OBJECT-TYPE
		SYNTAX					 INTEGER{ off(0),on(1)  }
		MAX-ACCESS			 read-create
		STATUS					 current
		DESCRIPTION			 " -- "
		::=  { lmcEntry  29 }


	lmcPrbUlCongestionTh		 OBJECT-TYPE
		SYNTAX					 Integer32( 0 .. 100 )
		MAX-ACCESS			 read-create
		STATUS					 current
		DESCRIPTION			 " -- "
		::=  { lmcEntry  30 }


	lmcPrbDlCongestionTh		 OBJECT-TYPE
		SYNTAX					 Integer32( 0 .. 100 )
		MAX-ACCESS			 read-create
		STATUS					 current
		DESCRIPTION			 " -- "
		::=  { lmcEntry  31 }


	lmcPrbUlCongestRestoreTh		 OBJECT-TYPE
		SYNTAX					 Integer32( 0 .. 100 )
		MAX-ACCESS			 read-create
		STATUS					 current
		DESCRIPTION			 " -- "
		::=  { lmcEntry  32 }


	lmcPrbDlCongestRestoreTh		 OBJECT-TYPE
		SYNTAX					 Integer32( 0 .. 100 )
		MAX-ACCESS			 read-create
		STATUS					 current
		DESCRIPTION			 " -- "
		::=  { lmcEntry  33 }


	lmcPrbCongestionDetectDuration		 OBJECT-TYPE
		SYNTAX					 Unsigned32( 1 .. 3600 )
		MAX-ACCESS			 read-create
		STATUS					 current
		DESCRIPTION			 " -- "
		::=  { lmcEntry  34 }


	lmcPrbCongestionRestoreDetectDuration		 OBJECT-TYPE
		SYNTAX					 Unsigned32( 1 .. 3600 )
		MAX-ACCESS			 read-create
		STATUS					 current
		DESCRIPTION			 " -- "
		::=  { lmcEntry  35 }


	lmcCongestionExecutePrd		 OBJECT-TYPE
		SYNTAX					 Unsigned32( 1 .. 3600 )
		MAX-ACCESS			 read-create
		STATUS					 current
		DESCRIPTION			 " -- "
		::=  { lmcEntry  36 }


	lmcMlbAlgorithmTag		 OBJECT-TYPE
		SYNTAX					 INTEGER{ off(0),on(1)  }
		MAX-ACCESS			 read-create
		STATUS					 current
		DESCRIPTION			 " -- "
		::=  { lmcEntry  37 }


	lmcMlbLoadDetectPrd		 OBJECT-TYPE
		SYNTAX					 Unsigned32( 1 .. 65535 )
		MAX-ACCESS			 read-create
		STATUS					 current
		DESCRIPTION			 " -- "
		::=  { lmcEntry  38 }


	lmcMlbOcnAdjustUpperLimit		 OBJECT-TYPE
		SYNTAX					 Integer32( -24 .. 24 )
		MAX-ACCESS			 read-create
		STATUS					 current
		DESCRIPTION			 " -- "
		::=  { lmcEntry  39 }


	lmcMlbOcnAdjustLowerLimit		 OBJECT-TYPE
		SYNTAX					 Integer32( -24 .. 24 )
		MAX-ACCESS			 read-create
		STATUS					 current
		DESCRIPTION			 " -- "
		::=  { lmcEntry  40 }


	lmcMlbOcnAdjustMaxNum		 OBJECT-TYPE
		SYNTAX					 Integer32( 0 .. 24 )
		MAX-ACCESS			 read-create
		STATUS					 current
		DESCRIPTION			 " -- "
		::=  { lmcEntry  41 }


	lmcMlbHighLoadThDl		 OBJECT-TYPE
		SYNTAX					 Integer32( 0 .. 100 )
		MAX-ACCESS			 read-create
		STATUS					 current
		DESCRIPTION			 " -- "
		::=  { lmcEntry  42 }


	lmcMlbHighLoadThUl		 OBJECT-TYPE
		SYNTAX					 Integer32( 0 .. 100 )
		MAX-ACCESS			 read-create
		STATUS					 current
		DESCRIPTION			 " -- "
		::=  { lmcEntry  43 }


	lmcMlbLoadRestoreThDl		 OBJECT-TYPE
		SYNTAX					 Integer32( 0 .. 100 )
		MAX-ACCESS			 read-create
		STATUS					 current
		DESCRIPTION			 " -- "
		::=  { lmcEntry  44 }


	lmcMlbLoadRestoreThUl		 OBJECT-TYPE
		SYNTAX					 Integer32( 0 .. 100 )
		MAX-ACCESS			 read-create
		STATUS					 current
		DESCRIPTION			 " -- "
		::=  { lmcEntry  45 }


	lmcMlbAdjCellJudgeTimer		 OBJECT-TYPE
		SYNTAX					 Unsigned32( 1 .. 300 )
		MAX-ACCESS			 read-create
		STATUS					 current
		DESCRIPTION			 " -- "
		::=  { lmcEntry  46 }


	lmcMlbParaBackoffTag		 OBJECT-TYPE
		SYNTAX					 INTEGER{ off(0),on(1)  }
		MAX-ACCESS			 read-create
		STATUS					 current
		DESCRIPTION			 " -- "
		::=  { lmcEntry  47 }


	lmcMlbBackoffMonitorTime		 OBJECT-TYPE
		SYNTAX					 Unsigned32( 1 .. 3000 )
		MAX-ACCESS			 read-create
		STATUS					 current
		DESCRIPTION			 " -- "
		::=  { lmcEntry  48 }


	lmcMlbAdjustProtectTh		 OBJECT-TYPE
		SYNTAX					 Integer32( 0 .. 100 )
		MAX-ACCESS			 read-create
		STATUS					 current
		DESCRIPTION			 " -- "
		::=  { lmcEntry  49 }


	lmcMlbTrueAdjCellJudge		 OBJECT-TYPE
		SYNTAX					 INTEGER{ a3(0),mr(1)  }
		MAX-ACCESS			 read-create
		STATUS					 current
		DESCRIPTION			 " -- "
		::=  { lmcEntry  50 }


	lmcMlbMrDeltaRsrp		 OBJECT-TYPE
		SYNTAX					 Integer32( -10 .. 10 )
		MAX-ACCESS			 read-create
		STATUS					 current
		DESCRIPTION			 " -- "
		::=  { lmcEntry  51 }


	lmcMlbMrDeltaRsrpRatio		 OBJECT-TYPE
		SYNTAX					 Integer32( 0 .. 100 )
		MAX-ACCESS			 read-create
		STATUS					 current
		DESCRIPTION			 " -- "
		::=  { lmcEntry  52 }


	lmcMlbMrEstimatePrd		 OBJECT-TYPE
		SYNTAX					 Unsigned32( 0 .. 300 )
		MAX-ACCESS			 read-create
		STATUS					 current
		DESCRIPTION			 " -- "
		::=  { lmcEntry  53 }


	lmcPucchTag		 OBJECT-TYPE
		SYNTAX					 INTEGER{ off(0),on(1)  }
		MAX-ACCESS			 read-create
		STATUS					 current
		DESCRIPTION			 " -- "
		::=  { lmcEntry  54 }


	lmcPucchThreshold		 OBJECT-TYPE
		SYNTAX					 Integer32( 0 .. 100 )
		MAX-ACCESS			 read-create
		STATUS					 current
		DESCRIPTION			 " -- "
		::=  { lmcEntry  55 }


	lmcCacUlPrbLoadTh		 OBJECT-TYPE
		SYNTAX					 Integer32( 0 .. 100 )
		MAX-ACCESS			 read-create
		STATUS					 current
		DESCRIPTION			 " -- "
		::=  { lmcEntry  57 }


	lmcCacDlPrbLoadTh		 OBJECT-TYPE
		SYNTAX					 Integer32( 0 .. 100 )
		MAX-ACCESS			 read-create
		STATUS					 current
		DESCRIPTION			 " -- "
		::=  { lmcEntry  58 }


	cellCAPara		 OBJECT IDENTIFIER
		::=  { cellAlgorithm  14 }


	cellCAParaTable		 OBJECT-TYPE
		SYNTAX					 SEQUENCE  OF	 CellCAParaEntry
		MAX-ACCESS			 not-accessible
		STATUS					 current
		DESCRIPTION			 " -- "
		::=  { cellCAPara  1 }


	cellCAParaEntry		 OBJECT-TYPE
		SYNTAX					 CellCAParaEntry
		MAX-ACCESS			 not-accessible
		STATUS					 current
		DESCRIPTION			 " -- "
		INDEX						{ caLcId }
		::=  { cellCAParaTable  1 }


	CellCAParaEntry		 ::=  SEQUENCE {
		caLcId					Integer32,
		caRowStatus					RowStatus,
		caUplinkSwitch					INTEGER,
		caDownlinkSwitch					INTEGER,
		caSCellSINRAbsThr					Integer32,
		caSCellSINRRelativeThr					Integer32,
		caSCellDeactivationTimer					INTEGER,
		caSCellConfigAlgorithm					INTEGER,
		caCrossCarrierSchedulingSwitch					INTEGER,
		caDectWindow					Unsigned32,
		caActiveDataThr					Unsigned32,
		caDeActiveDataThr					Unsigned32,
		caRetioThr					Unsigned32,
		caMacScellActSwitch					INTEGER,
		caMacScellHiddenDeActSwitch					INTEGER,
		caActiveNumThr					Unsigned32,
		caScellActiveAlgoPeriod					INTEGER,
		caRlcOveloadThr					Unsigned32,
		caScellActiveRlcOveloadThr					Unsigned32,
		caMcsDeActPeriod					INTEGER,
		caMcsDeActiveThr					Unsigned32,
		caScellActiveThroughputThrforUl					Unsigned32,
		caScellDeActiveThroughputThrforUl					Unsigned32,
		caMcsDeActiveThrUl					Unsigned32,
		caScellQosPrbActiveThrDl					Unsigned32,
		caScellQosPrbActiveThrUl					Unsigned32,
		caScellActualPrbActiveThrDl					Unsigned32,
		caScellActualPrbActiveThrUl					Unsigned32,
		caRlcBoAllocAlgN					INTEGER,
		caRlcBoAllocAlgAlpha					INTEGER,
		caRlcBoAllocSwitch					INTEGER,
		caRlcNonOverloadThr					Unsigned32,
		caScellDeactiveRlcOverloadThr					Unsigned32,
		caBsrActOverloadThr					Unsigned32,
		caBsrDeactOverloadThr					Unsigned32,
		caQosSatisfyProportionThrUl					Unsigned32,
		caQosSatisfyProportionThrDl					Unsigned32,
		caBoAllocPeriod					Unsigned32,
		caPrbThrforBoReAlloc					Unsigned32,
		caBoProportionAdjustStep					Unsigned32,
		caDRXActSwitch					INTEGER,
		caUlBsrAllocSwitch					INTEGER,
		caUlBsrProportionAdjustStep					Unsigned32,
		caPrbThrforUlBsrReAlloc					Unsigned32,
		caUlBsrRlcAllocAlgoT					INTEGER,
		caUlRlcBsrAllocAlgoAlpha					INTEGER,
		caUlBsrAllocPeriod					Unsigned32,
		caUserLimitSwitch					INTEGER,
		caUserLimitNum					Unsigned32
		}


	caLcId		 OBJECT-TYPE
		SYNTAX					 Integer32( 0 .. 23 )
		MAX-ACCESS			 not-accessible
		STATUS					 current
		DESCRIPTION			 " -- "
		::=  { cellCAParaEntry  1 }


	caRowStatus		 OBJECT-TYPE
		SYNTAX					 RowStatus
		MAX-ACCESS			 read-create
		STATUS					 current
		DESCRIPTION			 " -- "
		::=  { cellCAParaEntry  2 }


	caUplinkSwitch		 OBJECT-TYPE
		SYNTAX					 INTEGER{ off(0),on(1)  }
		MAX-ACCESS			 read-create
		STATUS					 current
		DESCRIPTION			 " -- "
		::=  { cellCAParaEntry  3 }


	caDownlinkSwitch		 OBJECT-TYPE
		SYNTAX					 INTEGER{ off(0),on(1)  }
		MAX-ACCESS			 read-create
		STATUS					 current
		DESCRIPTION			 " -- "
		::=  { cellCAParaEntry  4 }


	caSCellSINRAbsThr		 OBJECT-TYPE
		SYNTAX					 Integer32( 0 .. 15 )
		MAX-ACCESS			 read-create
		STATUS					 current
		DESCRIPTION			 " -- "
		::=  { cellCAParaEntry  5 }


	caSCellSINRRelativeThr		 OBJECT-TYPE
		SYNTAX					 Integer32( 0 .. 15 )
		MAX-ACCESS			 read-create
		STATUS					 current
		DESCRIPTION			 " -- "
		::=  { cellCAParaEntry  6 }


	caSCellDeactivationTimer		 OBJECT-TYPE
		SYNTAX					 INTEGER{ rf0(0),rf2(1),rf4(2),rf8(3),rf16(4),rf32(5),rf64(6),rf128(7)  }
		MAX-ACCESS			 read-create
		STATUS					 current
		DESCRIPTION			 " -- "
		::=  { cellCAParaEntry  7 }


	caSCellConfigAlgorithm		 OBJECT-TYPE
		SYNTAX					 INTEGER{ caRelation(0),relativeRSRP(1),sinr(2),absoluteRSRP(3)  }
		MAX-ACCESS			 read-create
		STATUS					 current
		DESCRIPTION			 " -- "
		::=  { cellCAParaEntry  8 }


	caCrossCarrierSchedulingSwitch		 OBJECT-TYPE
		SYNTAX					 INTEGER{ off(0),on(1)  }
		MAX-ACCESS			 read-create
		STATUS					 current
		DESCRIPTION			 " -- "
		::=  { cellCAParaEntry  9 }


	caDectWindow		 OBJECT-TYPE
		SYNTAX					 Unsigned32( 80 .. 200 )
		MAX-ACCESS			 read-create
		STATUS					 current
		DESCRIPTION			 " -- "
		::=  { cellCAParaEntry  10 }


	caActiveDataThr		 OBJECT-TYPE
		SYNTAX					 Unsigned32( 0 .. 200 )
		MAX-ACCESS			 read-create
		STATUS					 current
		DESCRIPTION			 " -- "
		::=  { cellCAParaEntry  11 }


	caDeActiveDataThr		 OBJECT-TYPE
		SYNTAX					 Unsigned32( 0 .. 200 )
		MAX-ACCESS			 read-create
		STATUS					 current
		DESCRIPTION			 " -- "
		::=  { cellCAParaEntry  12 }


	caRetioThr		 OBJECT-TYPE
		SYNTAX					 Unsigned32( 0 .. 100 )
		MAX-ACCESS			 read-create
		STATUS					 current
		DESCRIPTION			 " -- "
		::=  { cellCAParaEntry  13 }


	caMacScellActSwitch		 OBJECT-TYPE
		SYNTAX					 INTEGER{ off(0),dataflow(1),qos(2)  }
		MAX-ACCESS			 read-create
		STATUS					 current
		DESCRIPTION			 " -- "
		::=  { cellCAParaEntry  14 }


	caMacScellHiddenDeActSwitch		 OBJECT-TYPE
		SYNTAX					 INTEGER{ off(0),on(1)  }
		MAX-ACCESS			 read-create
		STATUS					 current
		DESCRIPTION			 " -- "
		::=  { cellCAParaEntry  15 }


	caActiveNumThr		 OBJECT-TYPE
		SYNTAX					 Unsigned32( 1 .. 20 )
		MAX-ACCESS			 read-create
		STATUS					 current
		DESCRIPTION			 " -- "
		::=  { cellCAParaEntry  16 }


	caScellActiveAlgoPeriod		 OBJECT-TYPE
		SYNTAX					 INTEGER{ ms100(0),ms200(1),ms400(2),ms600(3),ms800(4),ms1000(5),ms2000(6)  }
		MAX-ACCESS			 read-create
		STATUS					 current
		DESCRIPTION			 " -- "
		::=  { cellCAParaEntry  17 }


	caRlcOveloadThr		 OBJECT-TYPE
		SYNTAX					 Unsigned32( 0 .. 100 )
		MAX-ACCESS			 read-create
		STATUS					 current
		DESCRIPTION			 " -- "
		::=  { cellCAParaEntry  19 }


	caScellActiveRlcOveloadThr		 OBJECT-TYPE
		SYNTAX					 Unsigned32( 0 .. 100 )
		MAX-ACCESS			 read-create
		STATUS					 current
		DESCRIPTION			 " -- "
		::=  { cellCAParaEntry  20 }


	caMcsDeActPeriod		 OBJECT-TYPE
		SYNTAX					 INTEGER{ ms10(0),ms20(1),ms40(2),ms80(3),ms100(4),ms200(5)  }
		MAX-ACCESS			 read-create
		STATUS					 current
		DESCRIPTION			 " -- "
		::=  { cellCAParaEntry  21 }


	caMcsDeActiveThr		 OBJECT-TYPE
		SYNTAX					 Unsigned32( 0 .. 28 )
		MAX-ACCESS			 read-create
		STATUS					 current
		DESCRIPTION			 " -- "
		::=  { cellCAParaEntry  22 }


	caScellActiveThroughputThrforUl		 OBJECT-TYPE
		SYNTAX					 Unsigned32( 0 .. 50 )
		MAX-ACCESS			 read-create
		STATUS					 current
		DESCRIPTION			 " -- "
		::=  { cellCAParaEntry  25 }


	caScellDeActiveThroughputThrforUl		 OBJECT-TYPE
		SYNTAX					 Unsigned32( 0 .. 50 )
		MAX-ACCESS			 read-create
		STATUS					 current
		DESCRIPTION			 " -- "
		::=  { cellCAParaEntry  26 }


	caMcsDeActiveThrUl		 OBJECT-TYPE
		SYNTAX					 Unsigned32( 0 .. 28 )
		MAX-ACCESS			 read-create
		STATUS					 current
		DESCRIPTION			 " -- "
		::=  { cellCAParaEntry  27 }


	caScellQosPrbActiveThrDl		 OBJECT-TYPE
		SYNTAX					 Unsigned32( 0 .. 100 )
		MAX-ACCESS			 read-create
		STATUS					 current
		DESCRIPTION			 " -- "
		::=  { cellCAParaEntry  28 }


	caScellQosPrbActiveThrUl		 OBJECT-TYPE
		SYNTAX					 Unsigned32( 0 .. 100 )
		MAX-ACCESS			 read-create
		STATUS					 current
		DESCRIPTION			 " -- "
		::=  { cellCAParaEntry  29 }


	caScellActualPrbActiveThrDl		 OBJECT-TYPE
		SYNTAX					 Unsigned32( 0 .. 100 )
		MAX-ACCESS			 read-create
		STATUS					 current
		DESCRIPTION			 " -- "
		::=  { cellCAParaEntry  30 }


	caScellActualPrbActiveThrUl		 OBJECT-TYPE
		SYNTAX					 Unsigned32( 0 .. 100 )
		MAX-ACCESS			 read-create
		STATUS					 current
		DESCRIPTION			 " -- "
		::=  { cellCAParaEntry  31 }


	caRlcBoAllocAlgN		 OBJECT-TYPE
		SYNTAX					 INTEGER{ ms500(0),s1(1),s2(2),s3(3),s5(4)  }
		MAX-ACCESS			 read-create
		STATUS					 current
		DESCRIPTION			 " -- "
		::=  { cellCAParaEntry  32 }


	caRlcBoAllocAlgAlpha		 OBJECT-TYPE
		SYNTAX					 INTEGER{ val4(0),val8(1),val16(2),val32(3),val64(4),val128(5),val256(6)  }
		MAX-ACCESS			 read-create
		STATUS					 current
		DESCRIPTION			 " -- "
		::=  { cellCAParaEntry  33 }


	caRlcBoAllocSwitch		 OBJECT-TYPE
		SYNTAX					 INTEGER{ off(0),on(1)  }
		MAX-ACCESS			 read-create
		STATUS					 current
		DESCRIPTION			 " -- "
		::=  { cellCAParaEntry  34 }


	caRlcNonOverloadThr		 OBJECT-TYPE
		SYNTAX					 Unsigned32( 0 .. 100 )
		MAX-ACCESS			 read-create
		STATUS					 current
		DESCRIPTION			 " -- "
		::=  { cellCAParaEntry  35 }


	caScellDeactiveRlcOverloadThr		 OBJECT-TYPE
		SYNTAX					 Unsigned32( 0 .. 100 )
		MAX-ACCESS			 read-create
		STATUS					 current
		DESCRIPTION			 " -- "
		::=  { cellCAParaEntry  36 }


	caBsrActOverloadThr		 OBJECT-TYPE
		SYNTAX					 Unsigned32( 0 .. 63 )
		MAX-ACCESS			 read-create
		STATUS					 current
		DESCRIPTION			 " -- "
		::=  { cellCAParaEntry  37 }


	caBsrDeactOverloadThr		 OBJECT-TYPE
		SYNTAX					 Unsigned32( 0 .. 63 )
		MAX-ACCESS			 read-create
		STATUS					 current
		DESCRIPTION			 " -- "
		::=  { cellCAParaEntry  38 }


	caQosSatisfyProportionThrUl		 OBJECT-TYPE
		SYNTAX					 Unsigned32( 0 .. 100 )
		MAX-ACCESS			 read-create
		STATUS					 current
		DESCRIPTION			 " -- "
		::=  { cellCAParaEntry  39 }


	caQosSatisfyProportionThrDl		 OBJECT-TYPE
		SYNTAX					 Unsigned32( 0 .. 100 )
		MAX-ACCESS			 read-create
		STATUS					 current
		DESCRIPTION			 " -- "
		::=  { cellCAParaEntry  40 }


	caBoAllocPeriod		 OBJECT-TYPE
		SYNTAX					 Unsigned32( 1 .. 5 )
		MAX-ACCESS			 read-create
		STATUS					 current
		DESCRIPTION			 " -- "
		::=  { cellCAParaEntry  41 }


	caPrbThrforBoReAlloc		 OBJECT-TYPE
		SYNTAX					 Unsigned32( 0 .. 50 )
		MAX-ACCESS			 read-create
		STATUS					 current
		DESCRIPTION			 " -- "
		::=  { cellCAParaEntry  42 }


	caBoProportionAdjustStep		 OBJECT-TYPE
		SYNTAX					 Unsigned32( 1 .. 50 )
		MAX-ACCESS			 read-create
		STATUS					 current
		DESCRIPTION			 " -- "
		::=  { cellCAParaEntry  43 }


	caDRXActSwitch		 OBJECT-TYPE
		SYNTAX					 INTEGER{ off(0),on(1)  }
		MAX-ACCESS			 read-create
		STATUS					 current
		DESCRIPTION			 " -- "
		::=  { cellCAParaEntry  44 }


	caUlBsrAllocSwitch		 OBJECT-TYPE
		SYNTAX					 INTEGER{ off(0),on(1)  }
		MAX-ACCESS			 read-create
		STATUS					 current
		DESCRIPTION			 " -- "
		::=  { cellCAParaEntry  45 }


	caUlBsrProportionAdjustStep		 OBJECT-TYPE
		SYNTAX					 Unsigned32( 1 .. 50 )
		MAX-ACCESS			 read-create
		STATUS					 current
		DESCRIPTION			 " -- "
		::=  { cellCAParaEntry  46 }


	caPrbThrforUlBsrReAlloc		 OBJECT-TYPE
		SYNTAX					 Unsigned32( 0 .. 50 )
		MAX-ACCESS			 read-create
		STATUS					 current
		DESCRIPTION			 " -- "
		::=  { cellCAParaEntry  47 }


	caUlBsrRlcAllocAlgoT		 OBJECT-TYPE
		SYNTAX					 INTEGER{ ms500(0),s1(1),s2(2),s3(3),s5(4)  }
		MAX-ACCESS			 read-create
		STATUS					 current
		DESCRIPTION			 " -- "
		::=  { cellCAParaEntry  48 }


	caUlRlcBsrAllocAlgoAlpha		 OBJECT-TYPE
		SYNTAX					 INTEGER{ val4(0),val8(1),val16(2),val32(3),val64(4),val128(5),val256(6)  }
		MAX-ACCESS			 read-create
		STATUS					 current
		DESCRIPTION			 " -- "
		::=  { cellCAParaEntry  49 }


	caUlBsrAllocPeriod		 OBJECT-TYPE
		SYNTAX					 Unsigned32( 1 .. 5 )
		MAX-ACCESS			 read-create
		STATUS					 current
		DESCRIPTION			 " -- "
		::=  { cellCAParaEntry  50 }


	caUserLimitSwitch		 OBJECT-TYPE
		SYNTAX					 INTEGER{ off(0),on(1)  }
		MAX-ACCESS			 read-create
		STATUS					 current
		DESCRIPTION			 " -- "
		::=  { cellCAParaEntry  51 }


	caUserLimitNum		 OBJECT-TYPE
		SYNTAX					 Unsigned32( 0 .. 600 )
		MAX-ACCESS			 read-create
		STATUS					 current
		DESCRIPTION			 " -- "
		::=  { cellCAParaEntry  52 }


	cellCARelationTable		 OBJECT-TYPE
		SYNTAX					 SEQUENCE  OF	 CellCARelationEntry
		MAX-ACCESS			 not-accessible
		STATUS					 current
		DESCRIPTION			 " -- "
		::=  { cellCAPara  2 }


	cellCARelationEntry		 OBJECT-TYPE
		SYNTAX					 CellCARelationEntry
		MAX-ACCESS			 not-accessible
		STATUS					 current
		DESCRIPTION			 " -- "
		INDEX						{ cellCACellLcId,cellCACellIndex }
		::=  { cellCARelationTable  1 }


	CellCARelationEntry		 ::=  SEQUENCE {
		cellCACellLcId					Integer32,
		cellCACellIndex					Integer32,
		cellCACellRowStatus					RowStatus,
		cellCACellLocalId					Integer32
		}


	cellCACellLcId		 OBJECT-TYPE
		SYNTAX					 Integer32( 0 .. 23 )
		MAX-ACCESS			 not-accessible
		STATUS					 current
		DESCRIPTION			 " -- "
		::=  { cellCARelationEntry  1 }


	cellCACellIndex		 OBJECT-TYPE
		SYNTAX					 Integer32( 1 .. 4 )
		MAX-ACCESS			 not-accessible
		STATUS					 current
		DESCRIPTION			 " -- "
		::=  { cellCARelationEntry  2 }


	cellCACellRowStatus		 OBJECT-TYPE
		SYNTAX					 RowStatus
		MAX-ACCESS			 read-create
		STATUS					 current
		DESCRIPTION			 " -- "
		::=  { cellCARelationEntry  3 }


	cellCACellLocalId		 OBJECT-TYPE
		SYNTAX					 Integer32( 0 .. 23 )
		MAX-ACCESS			 read-create
		STATUS					 current
		DESCRIPTION			 " -- "
		::=  { cellCARelationEntry  4 }


	comp		 OBJECT IDENTIFIER
		::=  { cellAlgorithm  15 }


	ulCompTable		 OBJECT-TYPE
		SYNTAX					 SEQUENCE  OF	 UlCompEntry
		MAX-ACCESS			 not-accessible
		STATUS					 current
		DESCRIPTION			 " -- "
		::=  { comp  1 }


	ulCompEntry		 OBJECT-TYPE
		SYNTAX					 UlCompEntry
		MAX-ACCESS			 not-accessible
		STATUS					 current
		DESCRIPTION			 " -- "
		INDEX						{ ulCompLcId }
		::=  { ulCompTable  1 }


	UlCompEntry		 ::=  SEQUENCE {
		ulCompLcId					Integer32,
		ulCompRowStatus					RowStatus,
		ulCompMode					INTEGER,
		ulCompConfigSwitch					INTEGER,
		ulCompNonCoBandPrbEnd					Integer32,
		ulCompFuncSwitch					INTEGER,
		ulCompForceSwitch					INTEGER,
		ulCompMcsThres					Integer32,
		ulCompMcsOffset					Integer32,
		ulCompJrJeqInd					INTEGER,
		ulCompFuncTestSwitch					INTEGER
		}


	ulCompLcId		 OBJECT-TYPE
		SYNTAX					 Integer32( 0 .. 23 )
		MAX-ACCESS			 not-accessible
		STATUS					 current
		DESCRIPTION			 " -- "
		::=  { ulCompEntry  1 }


	ulCompRowStatus		 OBJECT-TYPE
		SYNTAX					 RowStatus
		MAX-ACCESS			 read-create
		STATUS					 current
		DESCRIPTION			 " -- "
		::=  { ulCompEntry  2 }


	ulCompMode		 OBJECT-TYPE
		SYNTAX					 INTEGER{ sujr(0),mujr(1)  }
		MAX-ACCESS			 read-create
		STATUS					 current
		DESCRIPTION			 " -- "
		::=  { ulCompEntry  3 }


	ulCompConfigSwitch		 OBJECT-TYPE
		SYNTAX					 INTEGER{ off(0),on(1)  }
		MAX-ACCESS			 read-create
		STATUS					 current
		DESCRIPTION			 " -- "
		::=  { ulCompEntry  4 }


	ulCompNonCoBandPrbEnd		 OBJECT-TYPE
		SYNTAX					 Integer32( 0 .. 100 )
		MAX-ACCESS			 read-create
		STATUS					 current
		DESCRIPTION			 " -- "
		::=  { ulCompEntry  5 }


	ulCompFuncSwitch		 OBJECT-TYPE
		SYNTAX					 INTEGER{ off(0),on(1)  }
		MAX-ACCESS			 read-create
		STATUS					 current
		DESCRIPTION			 " -- "
		::=  { ulCompEntry  6 }


	ulCompForceSwitch		 OBJECT-TYPE
		SYNTAX					 INTEGER{ off(0),on(1)  }
		MAX-ACCESS			 read-create
		STATUS					 current
		DESCRIPTION			 " -- "
		::=  { ulCompEntry  7 }


	ulCompMcsThres		 OBJECT-TYPE
		SYNTAX					 Integer32( 0 .. 27 )
		MAX-ACCESS			 read-create
		STATUS					 current
		DESCRIPTION			 " -- "
		::=  { ulCompEntry  8 }


	ulCompMcsOffset		 OBJECT-TYPE
		SYNTAX					 Integer32( 0 .. 27 )
		MAX-ACCESS			 read-create
		STATUS					 current
		DESCRIPTION			 " -- "
		::=  { ulCompEntry  9 }


	ulCompJrJeqInd		 OBJECT-TYPE
		SYNTAX					 INTEGER{ send(0),no(1)  }
		MAX-ACCESS			 read-create
		STATUS					 current
		DESCRIPTION			 " -- "
		::=  { ulCompEntry  10 }


	ulCompFuncTestSwitch		 OBJECT-TYPE
		SYNTAX					 INTEGER{ off(0),on(1)  }
		MAX-ACCESS			 read-create
		STATUS					 current
		DESCRIPTION			 " -- "
		::=  { ulCompEntry  11 }


	dlCompTable		 OBJECT-TYPE
		SYNTAX					 SEQUENCE  OF	 DlCompEntry
		MAX-ACCESS			 not-accessible
		STATUS					 current
		DESCRIPTION			 " -- "
		::=  { comp  2 }


	dlCompEntry		 OBJECT-TYPE
		SYNTAX					 DlCompEntry
		MAX-ACCESS			 not-accessible
		STATUS					 current
		DESCRIPTION			 " -- "
		INDEX						{ dlCompLcId }
		::=  { dlCompTable  1 }


	DlCompEntry		 ::=  SEQUENCE {
		dlCompLcId					Integer32,
		dlCompRowStatus					RowStatus,
		dlCompMode					INTEGER,
		dlCompConfigSwitch					INTEGER,
		dlCompFuncSwitch					INTEGER,
		dlCompCoBandPrbNum					Integer32,
		dlCompCqiThres					Integer32,
		dlCompCqiOffset					Integer32,
		dlCompSrsMeaSwitch					INTEGER,
		dlCompPrbConflictThres					Integer32,
		dlCompCsPrbThres					Integer32
		}


	dlCompLcId		 OBJECT-TYPE
		SYNTAX					 Integer32( 0 .. 23 )
		MAX-ACCESS			 not-accessible
		STATUS					 current
		DESCRIPTION			 " -- "
		::=  { dlCompEntry  1 }


	dlCompRowStatus		 OBJECT-TYPE
		SYNTAX					 RowStatus
		MAX-ACCESS			 read-create
		STATUS					 current
		DESCRIPTION			 " -- "
		::=  { dlCompEntry  2 }


	dlCompMode		 OBJECT-TYPE
		SYNTAX					 INTEGER{ sujt(0),mujt(1),cs(2),njtcs(3),cb(4),ncbcs(5)  }
		MAX-ACCESS			 read-create
		STATUS					 current
		DESCRIPTION			 " -- "
		::=  { dlCompEntry  3 }


	dlCompConfigSwitch		 OBJECT-TYPE
		SYNTAX					 INTEGER{ off(0),on(1)  }
		MAX-ACCESS			 read-create
		STATUS					 current
		DESCRIPTION			 " -- "
		::=  { dlCompEntry  4 }


	dlCompFuncSwitch		 OBJECT-TYPE
		SYNTAX					 INTEGER{ off(0),on(1)  }
		MAX-ACCESS			 read-create
		STATUS					 current
		DESCRIPTION			 " -- "
		::=  { dlCompEntry  5 }


	dlCompCoBandPrbNum		 OBJECT-TYPE
		SYNTAX					 Integer32( 0 .. 99 )
		MAX-ACCESS			 read-create
		STATUS					 current
		DESCRIPTION			 " -- "
		::=  { dlCompEntry  6 }


	dlCompCqiThres		 OBJECT-TYPE
		SYNTAX					 Integer32( 0 .. 15 )
		MAX-ACCESS			 read-create
		STATUS					 current
		DESCRIPTION			 " -- "
		::=  { dlCompEntry  7 }


	dlCompCqiOffset		 OBJECT-TYPE
		SYNTAX					 Integer32( 0 .. 15 )
		MAX-ACCESS			 read-create
		STATUS					 current
		DESCRIPTION			 " -- "
		::=  { dlCompEntry  8 }


	dlCompSrsMeaSwitch		 OBJECT-TYPE
		SYNTAX					 INTEGER{ off(0),on(1)  }
		MAX-ACCESS			 read-create
		STATUS					 current
		DESCRIPTION			 " -- "
		::=  { dlCompEntry  9 }


	dlCompPrbConflictThres		 OBJECT-TYPE
		SYNTAX					 Integer32( 0 .. 100 )
		MAX-ACCESS			 read-create
		STATUS					 current
		DESCRIPTION			 " -- "
		::=  { dlCompEntry  10 }


	dlCompCsPrbThres		 OBJECT-TYPE
		SYNTAX					 Integer32( 0 .. 100 )
		MAX-ACCESS			 read-create
		STATUS					 current
		DESCRIPTION			 " -- "
		::=  { dlCompEntry  11 }


	sdc		 OBJECT IDENTIFIER
		::=  { cellAlgorithm  16 }


	sdcTable		 OBJECT-TYPE
		SYNTAX					 SEQUENCE  OF	 SdcEntry
		MAX-ACCESS			 not-accessible
		STATUS					 current
		DESCRIPTION			 " -- "
		::=  { sdc  1 }


	sdcEntry		 OBJECT-TYPE
		SYNTAX					 SdcEntry
		MAX-ACCESS			 not-accessible
		STATUS					 current
		DESCRIPTION			 " -- "
		INDEX						{ sdcLcId }
		::=  { sdcTable  1 }


	SdcEntry		 ::=  SEQUENCE {
		sdcLcId					Integer32,
		sdcRowStatus					RowStatus,
		sdcDlTransMode					INTEGER,
		sdcRru1TdlMaxPwr					Unsigned32,
		sdcRru2TdlMaxPwr					Unsigned32
		}


	sdcLcId		 OBJECT-TYPE
		SYNTAX					 Integer32( 0 .. 23 )
		MAX-ACCESS			 not-accessible
		STATUS					 current
		DESCRIPTION			 " -- "
		::=  { sdcEntry  1 }


	sdcRowStatus		 OBJECT-TYPE
		SYNTAX					 RowStatus
		MAX-ACCESS			 read-create
		STATUS					 current
		DESCRIPTION			 " -- "
		::=  { sdcEntry  2 }


	sdcDlTransMode		 OBJECT-TYPE
		SYNTAX					 INTEGER{ single8ante(1),double8anteNew(3)  }
		MAX-ACCESS			 read-create
		STATUS					 current
		DESCRIPTION			 " -- "
		::=  { sdcEntry  3 }


	sdcRru1TdlMaxPwr		 OBJECT-TYPE
		SYNTAX					 Unsigned32( 0 .. 550 )
		MAX-ACCESS			 read-create
		STATUS					 current
		DESCRIPTION			 " -- "
		::=  { sdcEntry  5 }


	sdcRru2TdlMaxPwr		 OBJECT-TYPE
		SYNTAX					 Unsigned32( 0 .. 550 )
		MAX-ACCESS			 read-create
		STATUS					 current
		DESCRIPTION			 " -- "
		::=  { sdcEntry  6 }


	interRatLbPara		 OBJECT IDENTIFIER
		::=  { cellAlgorithm  17 }


	interRatLbParaTable		 OBJECT-TYPE
		SYNTAX					 SEQUENCE  OF	 InterRatLbParaEntry
		MAX-ACCESS			 not-accessible
		STATUS					 current
		DESCRIPTION			 " -- "
		::=  { interRatLbPara  1 }


	interRatLbParaEntry		 OBJECT-TYPE
		SYNTAX					 InterRatLbParaEntry
		MAX-ACCESS			 not-accessible
		STATUS					 current
		DESCRIPTION			 " -- "
		INDEX						{ interRatLbParaLcId }
		::=  { interRatLbParaTable  1 }


	InterRatLbParaEntry		 ::=  SEQUENCE {
		interRatLbParaLcId					Integer32,
		interRatLbParaRowStatus					RowStatus,
		interRatLoadBalanceVoiceTag					INTEGER
		}


	interRatLbParaLcId		 OBJECT-TYPE
		SYNTAX					 Integer32( 0 .. 23 )
		MAX-ACCESS			 not-accessible
		STATUS					 current
		DESCRIPTION			 " -- "
		::=  { interRatLbParaEntry  1 }


	interRatLbParaRowStatus		 OBJECT-TYPE
		SYNTAX					 RowStatus
		MAX-ACCESS			 read-create
		STATUS					 current
		DESCRIPTION			 " -- "
		::=  { interRatLbParaEntry  2 }


	interRatLoadBalanceVoiceTag		 OBJECT-TYPE
		SYNTAX					 INTEGER{ off(0),on(1)  }
		MAX-ACCESS			 read-create
		STATUS					 current
		DESCRIPTION			 " -- "
		::=  { interRatLbParaEntry  3 }


	atu		 OBJECT IDENTIFIER
		::=  { cellAlgorithm  18 }


	atuParaTable		 OBJECT-TYPE
		SYNTAX					 SEQUENCE  OF	 AtuParaEntry
		MAX-ACCESS			 not-accessible
		STATUS					 current
		DESCRIPTION			 " -- "
		::=  { atu  1 }


	atuParaEntry		 OBJECT-TYPE
		SYNTAX					 AtuParaEntry
		MAX-ACCESS			 not-accessible
		STATUS					 current
		DESCRIPTION			 " -- "
		INDEX						{ atuLcId }
		::=  { atuParaTable  1 }


	AtuParaEntry		 ::=  SEQUENCE {
		atuLcId					Integer32,
		atuRowStatus					RowStatus,
		atuDlSwitch					INTEGER,
		atuDlDataRateThr					Integer32,
		atuUlBoTime					Unsigned32,
		atuVIPTransferFlag					INTEGER,
		atuUlFlag					INTEGER,
		atuUlDataRateThr					Integer32,
		atuUlBoTforUL					Unsigned32,
		atuSrRestrictFlag					INTEGER,
		atuSmallPrbNumUsedFlag					INTEGER,
		atuVIPInactivePeriod					Unsigned32,
		atuDLQuitFlag					INTEGER,
		atuDLQuitRateThreshold					Integer32,
		atuDLQuitPeriodThreshold					Unsigned32,
		atuDlPeriodThr					Unsigned32,
		atuULQuitFlag					INTEGER,
		atuULQuitRateThreshold					Integer32,
		atuULQuitPeriodThreshold					Unsigned32,
		atuUlPeriodThr					Unsigned32,
		atuUeIdentityRequestSwitch					INTEGER,
		atuUeUlPowerAdd					Integer32,
		atuUlAndDlScheSRLmint					Integer32,
		atuUlOrDlScheSRLmint					Integer32,
		atuDlImsiOrIpAtuUeNum					Integer32,
		atuUlImsiOrIpAtuUeNum					Integer32,
		atuVolteRecDelayTime					Integer32,
		atuDldataTendcellBand					INTEGER,
		atuDldataTendcellFreq					Integer32,
		atuUldataTendcellBand					INTEGER,
		atuUldataTendcellFreq					Integer32,
		atuVoiceTendcellBand					INTEGER,
		atuVoiceTendcellFreq					Integer32,
		atuVideoTendcellBand					INTEGER,
		atuVideoTendcellFreq					Integer32,
		atuVipUserAppointFreqTag					INTEGER,
		atuRetxCfgSwitch					INTEGER,
		atuRlcMaxRetxThreshold					INTEGER,
		atuHarqMaxUlTx					INTEGER,
		atuHarqMaxDlTx					Integer32,
		atuQRxlevMinCfgSwitch					INTEGER,
		atuQRxlevMin					INTEGER,
		atuMrRecoverDelayTime					Integer32,
		atuAdjCellMrStopSwitch					INTEGER,
		atu16QAMPUSCHTargetSinrUpLimit					Integer32,
		atuSrUserUlPrbLimit					Integer32,
		atuVipUserIoTup					Integer32,
		atuHoInterFrqCfgSwitch					INTEGER,
		atuGoldUeSwitch					INTEGER,
		atuGoldUserAppointFrqTag					INTEGER,
		atuGoldVoiceTendcellFreq					Integer32,
		atuGoldVoiceTendcellBand					INTEGER,
		atuGoldUserMRStopInd					INTEGER,
		atuGoldUserIoTup					Integer32,
		atuGoldUserCfiFixSwitch					INTEGER,
		atuCommonUserMRDelSwitch					INTEGER,
		atuVipMROptSwitch					INTEGER,
		atuVipUserAppointFreqUserTypeInd					BITS,
		atucellUserBasedAdjCellReducePowerUserThr					Integer32,
		atuSrNormalVolteLimitSwitch					INTEGER,
		atuAdjCellPrbLimitSwitch					INTEGER,
		atuAdjCellUlPrbLimit					Integer32,
		atuAdjCellDlPrbLimit					Integer32,
		atuAdjCellUlPrbPerUserLimit					Integer32,
		atuAdjCellDlPrbPerUserLimit					Integer32,
		atuUserGapScheOptimizationSwitch					INTEGER,
		atuNormalUserFirstPrbLimitSwitch					INTEGER,
		atuNormalUserDlFirstPrbLimit					Integer32
		}


	atuLcId		 OBJECT-TYPE
		SYNTAX					 Integer32( 0 .. 23 )
		MAX-ACCESS			 not-accessible
		STATUS					 current
		DESCRIPTION			 " -- "
		::=  { atuParaEntry  1 }


	atuRowStatus		 OBJECT-TYPE
		SYNTAX					 RowStatus
		MAX-ACCESS			 read-create
		STATUS					 current
		DESCRIPTION			 " -- "
		::=  { atuParaEntry  2 }


	atuDlSwitch		 OBJECT-TYPE
		SYNTAX					 INTEGER{ off(0),on(1)  }
		MAX-ACCESS			 read-create
		STATUS					 current
		DESCRIPTION			 " -- "
		::=  { atuParaEntry  3 }


	atuDlDataRateThr		 OBJECT-TYPE
		SYNTAX					 Integer32( 1 .. 100 )
		MAX-ACCESS			 read-create
		STATUS					 current
		DESCRIPTION			 " -- "
		::=  { atuParaEntry  4 }


	atuUlBoTime		 OBJECT-TYPE
		SYNTAX					 Unsigned32( 0 .. 1000 )
		MAX-ACCESS			 read-create
		STATUS					 current
		DESCRIPTION			 " -- "
		::=  { atuParaEntry  5 }


	atuVIPTransferFlag		 OBJECT-TYPE
		SYNTAX					 INTEGER{ off(0),on(1)  }
		MAX-ACCESS			 read-create
		STATUS					 current
		DESCRIPTION			 " -- "
		::=  { atuParaEntry  6 }


	atuUlFlag		 OBJECT-TYPE
		SYNTAX					 INTEGER{ off(0),on(1)  }
		MAX-ACCESS			 read-create
		STATUS					 current
		DESCRIPTION			 " -- "
		::=  { atuParaEntry  7 }


	atuUlDataRateThr		 OBJECT-TYPE
		SYNTAX					 Integer32( 1 .. 100 )
		MAX-ACCESS			 read-create
		STATUS					 current
		DESCRIPTION			 " -- "
		::=  { atuParaEntry  8 }


	atuUlBoTforUL		 OBJECT-TYPE
		SYNTAX					 Unsigned32( 0 .. 1000 )
		MAX-ACCESS			 read-create
		STATUS					 current
		DESCRIPTION			 " -- "
		::=  { atuParaEntry  9 }


	atuSrRestrictFlag		 OBJECT-TYPE
		SYNTAX					 INTEGER{ off(0),on(1)  }
		MAX-ACCESS			 read-create
		STATUS					 current
		DESCRIPTION			 " -- "
		::=  { atuParaEntry  10 }


	atuSmallPrbNumUsedFlag		 OBJECT-TYPE
		SYNTAX					 INTEGER{ off(0),on(1)  }
		MAX-ACCESS			 read-create
		STATUS					 current
		DESCRIPTION			 " -- "
		::=  { atuParaEntry  11 }


	atuVIPInactivePeriod		 OBJECT-TYPE
		SYNTAX					 Unsigned32( 0 .. 65535 )
		MAX-ACCESS			 read-create
		STATUS					 current
		DESCRIPTION			 " -- "
		::=  { atuParaEntry  12 }


	atuDLQuitFlag		 OBJECT-TYPE
		SYNTAX					 INTEGER{ off(0),on(1)  }
		MAX-ACCESS			 read-create
		STATUS					 current
		DESCRIPTION			 " -- "
		::=  { atuParaEntry  13 }


	atuDLQuitRateThreshold		 OBJECT-TYPE
		SYNTAX					 Integer32( 0 .. 200 )
		MAX-ACCESS			 read-create
		STATUS					 current
		DESCRIPTION			 " -- "
		::=  { atuParaEntry  14 }


	atuDLQuitPeriodThreshold		 OBJECT-TYPE
		SYNTAX					 Unsigned32( 0 .. 65535 )
		MAX-ACCESS			 read-create
		STATUS					 current
		DESCRIPTION			 " -- "
		::=  { atuParaEntry  15 }


	atuDlPeriodThr		 OBJECT-TYPE
		SYNTAX					 Unsigned32( 0 .. 65535 )
		MAX-ACCESS			 read-create
		STATUS					 current
		DESCRIPTION			 " -- "
		::=  { atuParaEntry  16 }


	atuULQuitFlag		 OBJECT-TYPE
		SYNTAX					 INTEGER{ off(0),on(1)  }
		MAX-ACCESS			 read-create
		STATUS					 current
		DESCRIPTION			 " -- "
		::=  { atuParaEntry  17 }


	atuULQuitRateThreshold		 OBJECT-TYPE
		SYNTAX					 Integer32( 0 .. 200 )
		MAX-ACCESS			 read-create
		STATUS					 current
		DESCRIPTION			 " -- "
		::=  { atuParaEntry  18 }


	atuULQuitPeriodThreshold		 OBJECT-TYPE
		SYNTAX					 Unsigned32( 0 .. 65535 )
		MAX-ACCESS			 read-create
		STATUS					 current
		DESCRIPTION			 " -- "
		::=  { atuParaEntry  19 }


	atuUlPeriodThr		 OBJECT-TYPE
		SYNTAX					 Unsigned32( 0 .. 65535 )
		MAX-ACCESS			 read-create
		STATUS					 current
		DESCRIPTION			 " -- "
		::=  { atuParaEntry  20 }


	atuUeIdentityRequestSwitch		 OBJECT-TYPE
		SYNTAX					 INTEGER{ off(0),imsi(1),imei(2)  }
		MAX-ACCESS			 read-create
		STATUS					 current
		DESCRIPTION			 " -- "
		::=  { atuParaEntry  21 }


	atuUeUlPowerAdd		 OBJECT-TYPE
		SYNTAX					 Integer32( 0 .. 25 )
		MAX-ACCESS			 read-create
		STATUS					 current
		DESCRIPTION			 " -- "
		::=  { atuParaEntry  22 }


	atuUlAndDlScheSRLmint		 OBJECT-TYPE
		SYNTAX					 Integer32( 0 .. 25 )
		MAX-ACCESS			 read-create
		STATUS					 current
		DESCRIPTION			 " -- "
		::=  { atuParaEntry  23 }


	atuUlOrDlScheSRLmint		 OBJECT-TYPE
		SYNTAX					 Integer32( 0 .. 25 )
		MAX-ACCESS			 read-create
		STATUS					 current
		DESCRIPTION			 " -- "
		::=  { atuParaEntry  24 }


	atuDlImsiOrIpAtuUeNum		 OBJECT-TYPE
		SYNTAX					 Integer32( 0 .. 5 )
		MAX-ACCESS			 read-create
		STATUS					 current
		DESCRIPTION			 " -- "
		::=  { atuParaEntry  25 }


	atuUlImsiOrIpAtuUeNum		 OBJECT-TYPE
		SYNTAX					 Integer32( 0 .. 5 )
		MAX-ACCESS			 read-create
		STATUS					 current
		DESCRIPTION			 " -- "
		::=  { atuParaEntry  26 }


	atuVolteRecDelayTime		 OBJECT-TYPE
		SYNTAX					 Integer32( 10 .. 1000 )
		MAX-ACCESS			 read-create
		STATUS					 current
		DESCRIPTION			 " -- "
		::=  { atuParaEntry  27 }


	atuDldataTendcellBand		 OBJECT-TYPE
		SYNTAX					 INTEGER{ band1(1),band2(2),band3(3),band4(4),band5(5),band7(7),band8(8),band9(9),band10(10),band11(11),band12(12),band13(13),band14(14),band17(17),band18(18),band19(19),band20(20),band21(21),band22(22),band23(23),band24(24),band25(25),band33(33),band34(34),band35(35),band36(36),band37(37),band38(38),band39(39),band40(40),band41(41),band44(44),band61(61),band62(62)  }
		MAX-ACCESS			 read-create
		STATUS					 current
		DESCRIPTION			 " -- "
		::=  { atuParaEntry  28 }


	atuDldataTendcellFreq		 OBJECT-TYPE
		SYNTAX					 Integer32( 0 .. 65535 )
		MAX-ACCESS			 read-create
		STATUS					 current
		DESCRIPTION			 " -- "
		::=  { atuParaEntry  29 }


	atuUldataTendcellBand		 OBJECT-TYPE
		SYNTAX					 INTEGER{ band1(1),band2(2),band3(3),band4(4),band5(5),band7(7),band8(8),band9(9),band10(10),band11(11),band12(12),band13(13),band14(14),band17(17),band18(18),band19(19),band20(20),band21(21),band22(22),band23(23),band24(24),band25(25),band33(33),band34(34),band35(35),band36(36),band37(37),band38(38),band39(39),band40(40),band41(41),band44(44),band61(61),band62(62)  }
		MAX-ACCESS			 read-create
		STATUS					 current
		DESCRIPTION			 " -- "
		::=  { atuParaEntry  30 }


	atuUldataTendcellFreq		 OBJECT-TYPE
		SYNTAX					 Integer32( 0 .. 65535 )
		MAX-ACCESS			 read-create
		STATUS					 current
		DESCRIPTION			 " -- "
		::=  { atuParaEntry  31 }


	atuVoiceTendcellBand		 OBJECT-TYPE
		SYNTAX					 INTEGER{ band1(1),band2(2),band3(3),band4(4),band5(5),band7(7),band8(8),band9(9),band10(10),band11(11),band12(12),band13(13),band14(14),band17(17),band18(18),band19(19),band20(20),band21(21),band22(22),band23(23),band24(24),band25(25),band33(33),band34(34),band35(35),band36(36),band37(37),band38(38),band39(39),band40(40),band41(41),band44(44),band61(61),band62(62)  }
		MAX-ACCESS			 read-create
		STATUS					 current
		DESCRIPTION			 " -- "
		::=  { atuParaEntry  32 }


	atuVoiceTendcellFreq		 OBJECT-TYPE
		SYNTAX					 Integer32( 0 .. 65535 )
		MAX-ACCESS			 read-create
		STATUS					 current
		DESCRIPTION			 " -- "
		::=  { atuParaEntry  33 }


	atuVideoTendcellBand		 OBJECT-TYPE
		SYNTAX					 INTEGER{ band1(1),band2(2),band3(3),band4(4),band5(5),band7(7),band8(8),band9(9),band10(10),band11(11),band12(12),band13(13),band14(14),band17(17),band18(18),band19(19),band20(20),band21(21),band22(22),band23(23),band24(24),band25(25),band33(33),band34(34),band35(35),band36(36),band37(37),band38(38),band39(39),band40(40),band41(41),band44(44),band61(61),band62(62)  }
		MAX-ACCESS			 read-create
		STATUS					 current
		DESCRIPTION			 " -- "
		::=  { atuParaEntry  34 }


	atuVideoTendcellFreq		 OBJECT-TYPE
		SYNTAX					 Integer32( 0 .. 65535 )
		MAX-ACCESS			 read-create
		STATUS					 current
		DESCRIPTION			 " -- "
		::=  { atuParaEntry  35 }


	atuVipUserAppointFreqTag		 OBJECT-TYPE
		SYNTAX					 INTEGER{ off(0),on(1)  }
		MAX-ACCESS			 read-create
		STATUS					 current
		DESCRIPTION			 " -- "
		::=  { atuParaEntry  36 }


	atuRetxCfgSwitch		 OBJECT-TYPE
		SYNTAX					 INTEGER{ off(0),on(1)  }
		MAX-ACCESS			 read-create
		STATUS					 current
		DESCRIPTION			 " -- "
		::=  { atuParaEntry  38 }


	atuRlcMaxRetxThreshold		 OBJECT-TYPE
		SYNTAX					 INTEGER{ t1(0),t2(1),t3(2),t4(3),t6(4),t8(5),t16(6),t32(7)  }
		MAX-ACCESS			 read-create
		STATUS					 current
		DESCRIPTION			 " -- "
		::=  { atuParaEntry  39 }


	atuHarqMaxUlTx		 OBJECT-TYPE
		SYNTAX					 INTEGER{ n1(0),n2(1),n3(2),n4(3),n5(4),n6(5),n7(6),n8(7),n10(8),n12(9),n16(10),n20(11),n24(12),n28(13)  }
		MAX-ACCESS			 read-create
		STATUS					 current
		DESCRIPTION			 " -- "
		::=  { atuParaEntry  40 }


	atuHarqMaxDlTx		 OBJECT-TYPE
		SYNTAX					 Integer32( 1 .. 28 )
		MAX-ACCESS			 read-create
		STATUS					 current
		DESCRIPTION			 " -- "
		::=  { atuParaEntry  41 }


	atuQRxlevMinCfgSwitch		 OBJECT-TYPE
		SYNTAX					 INTEGER{ off(0),on(1)  }
		MAX-ACCESS			 read-create
		STATUS					 current
		DESCRIPTION			 " -- "
		::=  { atuParaEntry  42 }


	atuQRxlevMin		 OBJECT-TYPE
		SYNTAX					 INTEGER{ rxLevMinMinusDbm140(0),rxLevMinMinusDbm138(1),rxLevMinMinusDbm136(2),rxLevMinMinusDbm134(3),rxLevMinMinusDbm132(4),rxLevMinMinusDbm130(5),rxLevMinMinusDbm128(6),rxLevMinMinusDbm126(7),rxLevMinMinusDbm124(8),rxLevMinMinusDbm122(9),rxLevMinMinusDbm120(10),rxLevMinMinusDbm118(11),rxLevMinMinusDbm116(12),rxLevMinMinusDbm114(13),rxLevMinMinusDbm112(14),rxLevMinMinusDbm110(15),rxLevMinMinusDbm108(16),rxLevMinMinusDbm106(17),rxLevMinMinusDbm104(18),rxLevMinMinusDbm102(19),rxLevMinMinusDbm100(20),rxLevMinMinusDbm98(21),rxLevMinMinusDbm96(22),rxLevMinMinusDbm94(23),rxLevMinMinusDbm92(24),rxLevMinMinusDbm90(25),rxLevMinMinusDbm88(26),rxLevMinMinusDbm86(27),rxLevMinMinusDbm84(28),rxLevMinMinusDbm82(29),rxLevMinMinusDbm80(30),rxLevMinMinusDbm78(31),rxLevMinMinusDbm76(32),rxLevMinMinusDbm74(33),rxLevMinMinusDbm72(34),rxLevMinMinusDbm70(35),rxLevMinMinusDbm68(36),rxLevMinMinusDbm66(37),rxLevMinMinusDbm64(38),rxLevMinMinusDbm62(39),rxLevMinMinusDbm60(40),rxLevMinMinusDbm58(41),rxLevMinMinusDbm56(42),rxLevMinMinusDbm54(43),rxLevMinMinusDbm52(44),rxLevMinMinusDbm50(45),rxLevMinMinusDbm48(46),rxLevMinMinusDbm46(47),rxLevMinMinusDbm44(48)  }
		MAX-ACCESS			 read-create
		STATUS					 current
		DESCRIPTION			 " -- "
		::=  { atuParaEntry  43 }


	atuMrRecoverDelayTime		 OBJECT-TYPE
		SYNTAX					 Integer32( 0 .. 1200 )
		MAX-ACCESS			 read-create
		STATUS					 current
		DESCRIPTION			 " -- "
		::=  { atuParaEntry  60 }


	atuAdjCellMrStopSwitch		 OBJECT-TYPE
		SYNTAX					 INTEGER{ off(0),on(1)  }
		MAX-ACCESS			 read-create
		STATUS					 current
		DESCRIPTION			 " -- "
		::=  { atuParaEntry  61 }


	atu16QAMPUSCHTargetSinrUpLimit		 OBJECT-TYPE
		SYNTAX					 Integer32( 1 .. 100 )
		MAX-ACCESS			 read-create
		STATUS					 current
		DESCRIPTION			 " -- "
		::=  { atuParaEntry  62 }


	atuSrUserUlPrbLimit		 OBJECT-TYPE
		SYNTAX					 Integer32( 1 .. 100 )
		MAX-ACCESS			 read-create
		STATUS					 current
		DESCRIPTION			 " -- "
		::=  { atuParaEntry  63 }


	atuVipUserIoTup		 OBJECT-TYPE
		SYNTAX					 Integer32( -20 .. 50 )
		MAX-ACCESS			 read-create
		STATUS					 current
		DESCRIPTION			 " -- "
		::=  { atuParaEntry  64 }


	atuHoInterFrqCfgSwitch		 OBJECT-TYPE
		SYNTAX					 INTEGER{ off(0),on(1)  }
		MAX-ACCESS			 read-create
		STATUS					 current
		DESCRIPTION			 " -- "
		::=  { atuParaEntry  66 }


	atuGoldUeSwitch		 OBJECT-TYPE
		SYNTAX					 INTEGER{ off(0),open(1)  }
		MAX-ACCESS			 read-create
		STATUS					 current
		DESCRIPTION			 " -- "
		::=  { atuParaEntry  67 }


	atuGoldUserAppointFrqTag		 OBJECT-TYPE
		SYNTAX					 INTEGER{ off(0),open(1)  }
		MAX-ACCESS			 read-create
		STATUS					 current
		DESCRIPTION			 " -- "
		::=  { atuParaEntry  68 }


	atuGoldVoiceTendcellFreq		 OBJECT-TYPE
		SYNTAX					 Integer32( 0 .. 65535 )
		MAX-ACCESS			 read-create
		STATUS					 current
		DESCRIPTION			 " -- "
		::=  { atuParaEntry  69 }


	atuGoldVoiceTendcellBand		 OBJECT-TYPE
		SYNTAX					 INTEGER{ band1(1),band3(3),band32(32),band33(33),band34(34),band35(35),band36(36),band37(37),band38(38),band39(39),band40(40),band41(41),band61(61)  }
		MAX-ACCESS			 read-create
		STATUS					 current
		DESCRIPTION			 " -- "
		::=  { atuParaEntry  70 }


	atuGoldUserMRStopInd		 OBJECT-TYPE
		SYNTAX					 INTEGER{ unstop(0),stopMR(1)  }
		MAX-ACCESS			 read-create
		STATUS					 current
		DESCRIPTION			 " -- "
		::=  { atuParaEntry  71 }


	atuGoldUserIoTup		 OBJECT-TYPE
		SYNTAX					 Integer32( -20 .. 50 )
		MAX-ACCESS			 read-create
		STATUS					 current
		DESCRIPTION			 " -- "
		::=  { atuParaEntry  72 }


	atuGoldUserCfiFixSwitch		 OBJECT-TYPE
		SYNTAX					 INTEGER{ off(0),on(1)  }
		MAX-ACCESS			 read-create
		STATUS					 current
		DESCRIPTION			 " -- "
		::=  { atuParaEntry  73 }


	atuCommonUserMRDelSwitch		 OBJECT-TYPE
		SYNTAX					 INTEGER{ off(0),on(1)  }
		MAX-ACCESS			 read-create
		STATUS					 current
		DESCRIPTION			 " -- "
		::=  { atuParaEntry  90 }


	atuVipMROptSwitch		 OBJECT-TYPE
		SYNTAX					 INTEGER{ off(0),on(1)  }
		MAX-ACCESS			 read-create
		STATUS					 current
		DESCRIPTION			 " -- "
		::=  { atuParaEntry  91 }


	atuVipUserAppointFreqUserTypeInd		 OBJECT-TYPE
		SYNTAX					 BITS{ ul(0),dl(1),voice(2),video(3)  }
		MAX-ACCESS			 read-create
		STATUS					 current
		DESCRIPTION			 " -- "
		::=  { atuParaEntry  92 }


	atucellUserBasedAdjCellReducePowerUserThr		 OBJECT-TYPE
		SYNTAX					 Integer32( 1 .. 1000 )
		MAX-ACCESS			 read-create
		STATUS					 current
		DESCRIPTION			 " -- "
		::=  { atuParaEntry  93 }


	atuSrNormalVolteLimitSwitch		 OBJECT-TYPE
		SYNTAX					 INTEGER{ off(0),on(1)  }
		MAX-ACCESS			 read-create
		STATUS					 current
		DESCRIPTION			 " -- "
		::=  { atuParaEntry  94 }


	atuAdjCellPrbLimitSwitch		 OBJECT-TYPE
		SYNTAX					 INTEGER{ off(0),open(1)  }
		MAX-ACCESS			 read-create
		STATUS					 current
		DESCRIPTION			 " -- "
		::=  { atuParaEntry  95 }


	atuAdjCellUlPrbLimit		 OBJECT-TYPE
		SYNTAX					 Integer32( 5 .. 100 )
		MAX-ACCESS			 read-create
		STATUS					 current
		DESCRIPTION			 " -- "
		::=  { atuParaEntry  96 }


	atuAdjCellDlPrbLimit		 OBJECT-TYPE
		SYNTAX					 Integer32( 5 .. 100 )
		MAX-ACCESS			 read-create
		STATUS					 current
		DESCRIPTION			 " -- "
		::=  { atuParaEntry  97 }


	atuAdjCellUlPrbPerUserLimit		 OBJECT-TYPE
		SYNTAX					 Integer32( 5 .. 100 )
		MAX-ACCESS			 read-create
		STATUS					 current
		DESCRIPTION			 " -- "
		::=  { atuParaEntry  98 }


	atuAdjCellDlPrbPerUserLimit		 OBJECT-TYPE
		SYNTAX					 Integer32( 5 .. 100 )
		MAX-ACCESS			 read-create
		STATUS					 current
		DESCRIPTION			 " -- "
		::=  { atuParaEntry  99 }


	atuUserGapScheOptimizationSwitch		 OBJECT-TYPE
		SYNTAX					 INTEGER{ off(0),open(1)  }
		MAX-ACCESS			 read-create
		STATUS					 current
		DESCRIPTION			 " -- "
		::=  { atuParaEntry  100 }


	atuNormalUserFirstPrbLimitSwitch		 OBJECT-TYPE
		SYNTAX					 INTEGER{ off(0),open(1)  }
		MAX-ACCESS			 read-create
		STATUS					 current
		DESCRIPTION			 " -- "
		::=  { atuParaEntry  101 }


	atuNormalUserDlFirstPrbLimit		 OBJECT-TYPE
		SYNTAX					 Integer32( 0 .. 100 )
		MAX-ACCESS			 read-create
		STATUS					 current
		DESCRIPTION			 " -- "
		::=  { atuParaEntry  102 }


	atuByIpTable		 OBJECT-TYPE
		SYNTAX					 SEQUENCE  OF	 AtuByIpEntry
		MAX-ACCESS			 not-accessible
		STATUS					 current
		DESCRIPTION			 " -- "
		::=  { atu  2 }


	atuByIpEntry		 OBJECT-TYPE
		SYNTAX					 AtuByIpEntry
		MAX-ACCESS			 not-accessible
		STATUS					 current
		DESCRIPTION			 " -- "
		INDEX						{ atuByIpLcId }
		::=  { atuByIpTable  1 }


	AtuByIpEntry		 ::=  SEQUENCE {
		atuByIpLcId					Integer32,
		atuByIpRowStatus					RowStatus,
		atuByIpFlag					INTEGER,
		atuByIpAddrType					InetAddressType,
		atuByIpAddr1					InetAddress,
		atuByIpAddr2					InetAddress,
		atuByIpAddr3					InetAddress,
		atuByIpAddr4					InetAddress,
		atuByIpAddr5					InetAddress,
		atuByIpAddr6					InetAddress,
		atuByIpAddr7					InetAddress,
		atuByIpAddr8					InetAddress,
		atuByIpAddr9					InetAddress,
		atuByIpAddr10					InetAddress
		}


	atuByIpLcId		 OBJECT-TYPE
		SYNTAX					 Integer32( 0 .. 35 )
		MAX-ACCESS			 not-accessible
		STATUS					 current
		DESCRIPTION			 " -- "
		::=  { atuByIpEntry  1 }


	atuByIpRowStatus		 OBJECT-TYPE
		SYNTAX					 RowStatus
		MAX-ACCESS			 read-create
		STATUS					 current
		DESCRIPTION			 " -- "
		::=  { atuByIpEntry  2 }


	atuByIpFlag		 OBJECT-TYPE
		SYNTAX					 INTEGER{ off(0),on(1)  }
		MAX-ACCESS			 read-create
		STATUS					 current
		DESCRIPTION			 " -- "
		::=  { atuByIpEntry  3 }


	atuByIpAddrType		 OBJECT-TYPE
		SYNTAX					 InetAddressType
		MAX-ACCESS			 read-write
		STATUS					 current
		DESCRIPTION			 " -- "
		::=  { atuByIpEntry  4 }


	atuByIpAddr1		 OBJECT-TYPE
		SYNTAX					 InetAddress
		MAX-ACCESS			 read-write
		STATUS					 current
		DESCRIPTION			 " -- "
		::=  { atuByIpEntry  5 }


	atuByIpAddr2		 OBJECT-TYPE
		SYNTAX					 InetAddress
		MAX-ACCESS			 read-write
		STATUS					 current
		DESCRIPTION			 " -- "
		::=  { atuByIpEntry  6 }


	atuByIpAddr3		 OBJECT-TYPE
		SYNTAX					 InetAddress
		MAX-ACCESS			 read-write
		STATUS					 current
		DESCRIPTION			 " -- "
		::=  { atuByIpEntry  7 }


	atuByIpAddr4		 OBJECT-TYPE
		SYNTAX					 InetAddress
		MAX-ACCESS			 read-write
		STATUS					 current
		DESCRIPTION			 " -- "
		::=  { atuByIpEntry  8 }


	atuByIpAddr5		 OBJECT-TYPE
		SYNTAX					 InetAddress
		MAX-ACCESS			 read-write
		STATUS					 current
		DESCRIPTION			 " -- "
		::=  { atuByIpEntry  9 }


	atuByIpAddr6		 OBJECT-TYPE
		SYNTAX					 InetAddress
		MAX-ACCESS			 read-write
		STATUS					 current
		DESCRIPTION			 " -- "
		::=  { atuByIpEntry  10 }


	atuByIpAddr7		 OBJECT-TYPE
		SYNTAX					 InetAddress
		MAX-ACCESS			 read-write
		STATUS					 current
		DESCRIPTION			 " -- "
		::=  { atuByIpEntry  11 }


	atuByIpAddr8		 OBJECT-TYPE
		SYNTAX					 InetAddress
		MAX-ACCESS			 read-write
		STATUS					 current
		DESCRIPTION			 " -- "
		::=  { atuByIpEntry  12 }


	atuByIpAddr9		 OBJECT-TYPE
		SYNTAX					 InetAddress
		MAX-ACCESS			 read-write
		STATUS					 current
		DESCRIPTION			 " -- "
		::=  { atuByIpEntry  13 }


	atuByIpAddr10		 OBJECT-TYPE
		SYNTAX					 InetAddress
		MAX-ACCESS			 read-write
		STATUS					 current
		DESCRIPTION			 " -- "
		::=  { atuByIpEntry  14 }


	atuUeIMSI		 OBJECT IDENTIFIER
		::=  { atu  3 }


	atuUeIMSISwitch		 OBJECT-TYPE
		SYNTAX					 INTEGER{ close(0),open(1)  }
		MAX-ACCESS			 read-write
		STATUS					 current
		DESCRIPTION			 " -- "
		::=  { atuUeIMSI  1 }


	atuImsiGetTimer		 OBJECT-TYPE
		SYNTAX					 Unsigned32( 0 .. 6000 )
		MAX-ACCESS			 read-create
		STATUS					 current
		DESCRIPTION			 " -- "
		::=  { atuUeIMSI  2 }


	atuUeIMSI1		 OBJECT-TYPE
		SYNTAX					 DisplayString( SIZE ( 1 .. 15 ) )
		MAX-ACCESS			 read-create
		STATUS					 current
		DESCRIPTION			 " -- "
		::=  { atuUeIMSI  3 }


	atuUeIMSI2		 OBJECT-TYPE
		SYNTAX					 DisplayString( SIZE ( 1 .. 15 ) )
		MAX-ACCESS			 read-create
		STATUS					 current
		DESCRIPTION			 " -- "
		::=  { atuUeIMSI  4 }


	atuUeIMSI3		 OBJECT-TYPE
		SYNTAX					 DisplayString( SIZE ( 1 .. 15 ) )
		MAX-ACCESS			 read-create
		STATUS					 current
		DESCRIPTION			 " -- "
		::=  { atuUeIMSI  5 }


	atuUeIMSI4		 OBJECT-TYPE
		SYNTAX					 DisplayString( SIZE ( 1 .. 15 ) )
		MAX-ACCESS			 read-create
		STATUS					 current
		DESCRIPTION			 " -- "
		::=  { atuUeIMSI  6 }


	atuUeIMSI5		 OBJECT-TYPE
		SYNTAX					 DisplayString( SIZE ( 1 .. 15 ) )
		MAX-ACCESS			 read-create
		STATUS					 current
		DESCRIPTION			 " -- "
		::=  { atuUeIMSI  7 }


	atuUeIMSI6		 OBJECT-TYPE
		SYNTAX					 DisplayString( SIZE ( 1 .. 15 ) )
		MAX-ACCESS			 read-create
		STATUS					 current
		DESCRIPTION			 " -- "
		::=  { atuUeIMSI  8 }


	atuUeIMSI7		 OBJECT-TYPE
		SYNTAX					 DisplayString( SIZE ( 1 .. 15 ) )
		MAX-ACCESS			 read-create
		STATUS					 current
		DESCRIPTION			 " -- "
		::=  { atuUeIMSI  9 }


	atuUeIMSI8		 OBJECT-TYPE
		SYNTAX					 DisplayString( SIZE ( 1 .. 15 ) )
		MAX-ACCESS			 read-create
		STATUS					 current
		DESCRIPTION			 " -- "
		::=  { atuUeIMSI  10 }


	atuUeIMSI9		 OBJECT-TYPE
		SYNTAX					 DisplayString( SIZE ( 1 .. 15 ) )
		MAX-ACCESS			 read-create
		STATUS					 current
		DESCRIPTION			 " -- "
		::=  { atuUeIMSI  11 }


	atuUeIMSI10		 OBJECT-TYPE
		SYNTAX					 DisplayString( SIZE ( 1 .. 15 ) )
		MAX-ACCESS			 read-create
		STATUS					 current
		DESCRIPTION			 " -- "
		::=  { atuUeIMSI  12 }


	atuHoBasedRec		 OBJECT IDENTIFIER
		::=  { atu  4 }


	atuDataHoBasedVolteRecFlag		 OBJECT-TYPE
		SYNTAX					 Integer32( 0 .. 1 )
		MAX-ACCESS			 read-write
		STATUS					 current
		DESCRIPTION			 " -- "
		::=  { atuHoBasedRec  1 }


	atuVolteDataUserTimeInterval		 OBJECT-TYPE
		SYNTAX					 Integer32( 1 .. 30 )
		MAX-ACCESS			 read-write
		STATUS					 current
		DESCRIPTION			 " -- "
		::=  { atuHoBasedRec  2 }


	atuHoBasedVolteRecNum		 OBJECT-TYPE
		SYNTAX					 Integer32( 0 .. 20 )
		MAX-ACCESS			 read-write
		STATUS					 current
		DESCRIPTION			 " -- "
		::=  { atuHoBasedRec  3 }


	atuGoldUeIMSI		 OBJECT IDENTIFIER
		::=  { atu  5 }


	atuGoldUeIMSISwitch		 OBJECT-TYPE
		SYNTAX					 INTEGER{ close(0),open(1)  }
		MAX-ACCESS			 read-write
		STATUS					 current
		DESCRIPTION			 " -- "
		::=  { atuGoldUeIMSI  1 }


	atuGoldUeIMSI1		 OBJECT-TYPE
		SYNTAX					 DisplayString( SIZE ( 1 .. 15 ) )
		MAX-ACCESS			 read-create
		STATUS					 current
		DESCRIPTION			 " -- "
		::=  { atuGoldUeIMSI  2 }


	atuGoldUeIMSI2		 OBJECT-TYPE
		SYNTAX					 DisplayString( SIZE ( 1 .. 15 ) )
		MAX-ACCESS			 read-create
		STATUS					 current
		DESCRIPTION			 " -- "
		::=  { atuGoldUeIMSI  3 }


	atuGoldUeIMSI3		 OBJECT-TYPE
		SYNTAX					 DisplayString( SIZE ( 1 .. 15 ) )
		MAX-ACCESS			 read-create
		STATUS					 current
		DESCRIPTION			 " -- "
		::=  { atuGoldUeIMSI  4 }


	atuGoldUeIMSI4		 OBJECT-TYPE
		SYNTAX					 DisplayString( SIZE ( 1 .. 15 ) )
		MAX-ACCESS			 read-create
		STATUS					 current
		DESCRIPTION			 " -- "
		::=  { atuGoldUeIMSI  5 }


	atuGoldUeIMSI5		 OBJECT-TYPE
		SYNTAX					 DisplayString( SIZE ( 1 .. 15 ) )
		MAX-ACCESS			 read-create
		STATUS					 current
		DESCRIPTION			 " -- "
		::=  { atuGoldUeIMSI  6 }


	atuGoldUeIMSI6		 OBJECT-TYPE
		SYNTAX					 DisplayString( SIZE ( 1 .. 15 ) )
		MAX-ACCESS			 read-create
		STATUS					 current
		DESCRIPTION			 " -- "
		::=  { atuGoldUeIMSI  7 }


	atuGoldUeIMSI7		 OBJECT-TYPE
		SYNTAX					 DisplayString( SIZE ( 1 .. 15 ) )
		MAX-ACCESS			 read-create
		STATUS					 current
		DESCRIPTION			 " -- "
		::=  { atuGoldUeIMSI  8 }


	atuGoldUeIMSI8		 OBJECT-TYPE
		SYNTAX					 DisplayString( SIZE ( 1 .. 15 ) )
		MAX-ACCESS			 read-create
		STATUS					 current
		DESCRIPTION			 " -- "
		::=  { atuGoldUeIMSI  9 }


	atuGoldUeIMSI9		 OBJECT-TYPE
		SYNTAX					 DisplayString( SIZE ( 1 .. 15 ) )
		MAX-ACCESS			 read-create
		STATUS					 current
		DESCRIPTION			 " -- "
		::=  { atuGoldUeIMSI  10 }


	atuGoldUeIMSI10		 OBJECT-TYPE
		SYNTAX					 DisplayString( SIZE ( 1 .. 15 ) )
		MAX-ACCESS			 read-create
		STATUS					 current
		DESCRIPTION			 " -- "
		::=  { atuGoldUeIMSI  11 }


	atuGoldUeIMSI11		 OBJECT-TYPE
		SYNTAX					 DisplayString( SIZE ( 1 .. 15 ) )
		MAX-ACCESS			 read-create
		STATUS					 current
		DESCRIPTION			 " -- "
		::=  { atuGoldUeIMSI  12 }


	atuGoldUeIMSI12		 OBJECT-TYPE
		SYNTAX					 DisplayString( SIZE ( 1 .. 15 ) )
		MAX-ACCESS			 read-create
		STATUS					 current
		DESCRIPTION			 " -- "
		::=  { atuGoldUeIMSI  13 }


	atuGoldUeIMSI13		 OBJECT-TYPE
		SYNTAX					 DisplayString( SIZE ( 1 .. 15 ) )
		MAX-ACCESS			 read-create
		STATUS					 current
		DESCRIPTION			 " -- "
		::=  { atuGoldUeIMSI  14 }


	atuGoldUeIMSI14		 OBJECT-TYPE
		SYNTAX					 DisplayString( SIZE ( 1 .. 15 ) )
		MAX-ACCESS			 read-create
		STATUS					 current
		DESCRIPTION			 " -- "
		::=  { atuGoldUeIMSI  15 }


	atuGoldUeIMSI15		 OBJECT-TYPE
		SYNTAX					 DisplayString( SIZE ( 1 .. 15 ) )
		MAX-ACCESS			 read-create
		STATUS					 current
		DESCRIPTION			 " -- "
		::=  { atuGoldUeIMSI  16 }


	atuGoldUeIMSI16		 OBJECT-TYPE
		SYNTAX					 DisplayString( SIZE ( 1 .. 15 ) )
		MAX-ACCESS			 read-create
		STATUS					 current
		DESCRIPTION			 " -- "
		::=  { atuGoldUeIMSI  17 }


	atuGoldUeIMSI17		 OBJECT-TYPE
		SYNTAX					 DisplayString( SIZE ( 1 .. 15 ) )
		MAX-ACCESS			 read-create
		STATUS					 current
		DESCRIPTION			 " -- "
		::=  { atuGoldUeIMSI  18 }


	atuGoldUeIMSI18		 OBJECT-TYPE
		SYNTAX					 DisplayString( SIZE ( 1 .. 15 ) )
		MAX-ACCESS			 read-create
		STATUS					 current
		DESCRIPTION			 " -- "
		::=  { atuGoldUeIMSI  19 }


	atuGoldUeIMSI19		 OBJECT-TYPE
		SYNTAX					 DisplayString( SIZE ( 1 .. 15 ) )
		MAX-ACCESS			 read-create
		STATUS					 current
		DESCRIPTION			 " -- "
		::=  { atuGoldUeIMSI  20 }


	atuGoldUeIMSI20		 OBJECT-TYPE
		SYNTAX					 DisplayString( SIZE ( 1 .. 15 ) )
		MAX-ACCESS			 read-create
		STATUS					 current
		DESCRIPTION			 " -- "
		::=  { atuGoldUeIMSI  21 }


	atuGoldUeIMSI21		 OBJECT-TYPE
		SYNTAX					 DisplayString( SIZE ( 1 .. 15 ) )
		MAX-ACCESS			 read-create
		STATUS					 current
		DESCRIPTION			 " -- "
		::=  { atuGoldUeIMSI  22 }


	atuGoldUeIMSI22		 OBJECT-TYPE
		SYNTAX					 DisplayString( SIZE ( 1 .. 15 ) )
		MAX-ACCESS			 read-create
		STATUS					 current
		DESCRIPTION			 " -- "
		::=  { atuGoldUeIMSI  23 }


	atuGoldUeIMSI23		 OBJECT-TYPE
		SYNTAX					 DisplayString( SIZE ( 1 .. 15 ) )
		MAX-ACCESS			 read-create
		STATUS					 current
		DESCRIPTION			 " -- "
		::=  { atuGoldUeIMSI  24 }


	atuGoldUeIMSI24		 OBJECT-TYPE
		SYNTAX					 DisplayString( SIZE ( 1 .. 15 ) )
		MAX-ACCESS			 read-create
		STATUS					 current
		DESCRIPTION			 " -- "
		::=  { atuGoldUeIMSI  25 }


	atuGoldUeIMSI25		 OBJECT-TYPE
		SYNTAX					 DisplayString( SIZE ( 1 .. 15 ) )
		MAX-ACCESS			 read-create
		STATUS					 current
		DESCRIPTION			 " -- "
		::=  { atuGoldUeIMSI  26 }


	atuGoldUeIMSI26		 OBJECT-TYPE
		SYNTAX					 DisplayString( SIZE ( 1 .. 15 ) )
		MAX-ACCESS			 read-create
		STATUS					 current
		DESCRIPTION			 " -- "
		::=  { atuGoldUeIMSI  27 }


	atuGoldUeIMSI27		 OBJECT-TYPE
		SYNTAX					 DisplayString( SIZE ( 1 .. 15 ) )
		MAX-ACCESS			 read-create
		STATUS					 current
		DESCRIPTION			 " -- "
		::=  { atuGoldUeIMSI  28 }


	atuGoldUeIMSI28		 OBJECT-TYPE
		SYNTAX					 DisplayString( SIZE ( 1 .. 15 ) )
		MAX-ACCESS			 read-create
		STATUS					 current
		DESCRIPTION			 " -- "
		::=  { atuGoldUeIMSI  29 }


	atuGoldUeIMSI29		 OBJECT-TYPE
		SYNTAX					 DisplayString( SIZE ( 1 .. 15 ) )
		MAX-ACCESS			 read-create
		STATUS					 current
		DESCRIPTION			 " -- "
		::=  { atuGoldUeIMSI  30 }


	atuGoldUeIMSI30		 OBJECT-TYPE
		SYNTAX					 DisplayString( SIZE ( 1 .. 15 ) )
		MAX-ACCESS			 read-create
		STATUS					 current
		DESCRIPTION			 " -- "
		::=  { atuGoldUeIMSI  31 }


	atuGoldUeIMSI31		 OBJECT-TYPE
		SYNTAX					 DisplayString( SIZE ( 1 .. 15 ) )
		MAX-ACCESS			 read-create
		STATUS					 current
		DESCRIPTION			 " -- "
		::=  { atuGoldUeIMSI  32 }


	atuGoldUeIMSI32		 OBJECT-TYPE
		SYNTAX					 DisplayString( SIZE ( 1 .. 15 ) )
		MAX-ACCESS			 read-create
		STATUS					 current
		DESCRIPTION			 " -- "
		::=  { atuGoldUeIMSI  33 }


	atuGoldUeIMSI33		 OBJECT-TYPE
		SYNTAX					 DisplayString( SIZE ( 1 .. 15 ) )
		MAX-ACCESS			 read-create
		STATUS					 current
		DESCRIPTION			 " -- "
		::=  { atuGoldUeIMSI  34 }


	atuGoldUeIMSI34		 OBJECT-TYPE
		SYNTAX					 DisplayString( SIZE ( 1 .. 15 ) )
		MAX-ACCESS			 read-create
		STATUS					 current
		DESCRIPTION			 " -- "
		::=  { atuGoldUeIMSI  35 }


	atuGoldUeIMSI35		 OBJECT-TYPE
		SYNTAX					 DisplayString( SIZE ( 1 .. 15 ) )
		MAX-ACCESS			 read-create
		STATUS					 current
		DESCRIPTION			 " -- "
		::=  { atuGoldUeIMSI  36 }


	atuGoldUeIMSI36		 OBJECT-TYPE
		SYNTAX					 DisplayString( SIZE ( 1 .. 15 ) )
		MAX-ACCESS			 read-create
		STATUS					 current
		DESCRIPTION			 " -- "
		::=  { atuGoldUeIMSI  37 }


	atuGoldUeIMSI37		 OBJECT-TYPE
		SYNTAX					 DisplayString( SIZE ( 1 .. 15 ) )
		MAX-ACCESS			 read-create
		STATUS					 current
		DESCRIPTION			 " -- "
		::=  { atuGoldUeIMSI  38 }


	atuGoldUeIMSI38		 OBJECT-TYPE
		SYNTAX					 DisplayString( SIZE ( 1 .. 15 ) )
		MAX-ACCESS			 read-create
		STATUS					 current
		DESCRIPTION			 " -- "
		::=  { atuGoldUeIMSI  39 }


	atuGoldUeIMSI39		 OBJECT-TYPE
		SYNTAX					 DisplayString( SIZE ( 1 .. 15 ) )
		MAX-ACCESS			 read-create
		STATUS					 current
		DESCRIPTION			 " -- "
		::=  { atuGoldUeIMSI  40 }


	atuGoldUeIMSI40		 OBJECT-TYPE
		SYNTAX					 DisplayString( SIZE ( 1 .. 15 ) )
		MAX-ACCESS			 read-create
		STATUS					 current
		DESCRIPTION			 " -- "
		::=  { atuGoldUeIMSI  41 }


	pubAlgorithmPara		 OBJECT IDENTIFIER
		::=  { cellAlgorithm  19 }


	pubAlgorithmParaTable		 OBJECT-TYPE
		SYNTAX					 SEQUENCE  OF	 PubAlgorithmParaEntry
		MAX-ACCESS			 not-accessible
		STATUS					 current
		DESCRIPTION			 " -- "
		::=  { pubAlgorithmPara  1 }


	pubAlgorithmParaEntry		 OBJECT-TYPE
		SYNTAX					 PubAlgorithmParaEntry
		MAX-ACCESS			 not-accessible
		STATUS					 current
		DESCRIPTION			 " -- "
		INDEX						{ pubAlgorithmParaLcId }
		::=  { pubAlgorithmParaTable  1 }


	PubAlgorithmParaEntry		 ::=  SEQUENCE {
		pubAlgorithmParaLcId					Integer32,
		pubAlgorithmParaRowStatus					RowStatus,
		pubAlgorithmParaHSpdSwitch					INTEGER,
		pubAlgorithmParaHSpucchSwitch					INTEGER,
		pubAlgorithmParaHSpdInactiveSwitch					INTEGER,
		pubAlgorithmParaHSpdDlFreqShiftSwitch					INTEGER
		}


	pubAlgorithmParaLcId		 OBJECT-TYPE
		SYNTAX					 Integer32( 0 .. 23 )
		MAX-ACCESS			 not-accessible
		STATUS					 current
		DESCRIPTION			 " -- "
		::=  { pubAlgorithmParaEntry  1 }


	pubAlgorithmParaRowStatus		 OBJECT-TYPE
		SYNTAX					 RowStatus
		MAX-ACCESS			 read-create
		STATUS					 current
		DESCRIPTION			 " -- "
		::=  { pubAlgorithmParaEntry  2 }


	pubAlgorithmParaHSpdSwitch		 OBJECT-TYPE
		SYNTAX					 INTEGER{ off(0),on(1)  }
		MAX-ACCESS			 read-create
		STATUS					 current
		DESCRIPTION			 " -- "
		::=  { pubAlgorithmParaEntry  3 }


	pubAlgorithmParaHSpucchSwitch		 OBJECT-TYPE
		SYNTAX					 INTEGER{ off(0),on(1)  }
		MAX-ACCESS			 read-create
		STATUS					 current
		DESCRIPTION			 " -- "
		::=  { pubAlgorithmParaEntry  4 }


	pubAlgorithmParaHSpdInactiveSwitch		 OBJECT-TYPE
		SYNTAX					 INTEGER{ off(0),on(1)  }
		MAX-ACCESS			 read-create
		STATUS					 current
		DESCRIPTION			 " -- "
		::=  { pubAlgorithmParaEntry  5 }


	pubAlgorithmParaHSpdDlFreqShiftSwitch		 OBJECT-TYPE
		SYNTAX					 INTEGER{ off(0),on(1)  }
		MAX-ACCESS			 read-create
		STATUS					 current
		DESCRIPTION			 " -- "
		::=  { pubAlgorithmParaEntry  6 }


	gsmCell		 OBJECT IDENTIFIER
		::=  { cellAlgorithm  20 }


	gsmCellTable		 OBJECT-TYPE
		SYNTAX					 SEQUENCE  OF	 GsmCellEntry
		MAX-ACCESS			 not-accessible
		STATUS					 current
		DESCRIPTION			 " -- "
		::=  { gsmCell  1 }


	gsmCellEntry		 OBJECT-TYPE
		SYNTAX					 GsmCellEntry
		MAX-ACCESS			 not-accessible
		STATUS					 current
		DESCRIPTION			 " -- "
		INDEX						{ gsmCellRackNo,gsmCellShelfNo,gsmCellSlotNo,gsmCellOptIndex }
		::=  { gsmCellTable  1 }


	GsmCellEntry		 ::=  SEQUENCE {
		gsmCellRackNo					Integer32,
		gsmCellShelfNo					Integer32,
		gsmCellSlotNo					Integer32,
		gsmCellOptIndex					Integer32,
		gsmCellRowStatus					RowStatus,
		gsmCellCenterFreq					Integer32,
		gsmCellSignalTxRxSwitch					INTEGER
		}


	gsmCellRackNo		 OBJECT-TYPE
		SYNTAX					 Integer32( 0 .. 0 )
		MAX-ACCESS			 not-accessible
		STATUS					 current
		DESCRIPTION			 " -- "
		::=  { gsmCellEntry  1 }


	gsmCellShelfNo		 OBJECT-TYPE
		SYNTAX					 Integer32( 0 .. 0 )
		MAX-ACCESS			 not-accessible
		STATUS					 current
		DESCRIPTION			 " -- "
		::=  { gsmCellEntry  2 }


	gsmCellSlotNo		 OBJECT-TYPE
		SYNTAX					 Integer32( 0 .. 16 )
		MAX-ACCESS			 not-accessible
		STATUS					 current
		DESCRIPTION			 " -- "
		::=  { gsmCellEntry  3 }


	gsmCellOptIndex		 OBJECT-TYPE
		SYNTAX					 Integer32( 0 .. 5 )
		MAX-ACCESS			 not-accessible
		STATUS					 current
		DESCRIPTION			 " -- "
		::=  { gsmCellEntry  4 }


	gsmCellRowStatus		 OBJECT-TYPE
		SYNTAX					 RowStatus
		MAX-ACCESS			 read-create
		STATUS					 current
		DESCRIPTION			 " -- "
		::=  { gsmCellEntry  5 }


	gsmCellCenterFreq		 OBJECT-TYPE
		SYNTAX					 Integer32( 0 .. 65535 )
		MAX-ACCESS			 read-create
		STATUS					 current
		DESCRIPTION			 " -- "
		::=  { gsmCellEntry  6 }


	gsmCellSignalTxRxSwitch		 OBJECT-TYPE
		SYNTAX					 INTEGER{ off(0),on(1)  }
		MAX-ACCESS			 read-create
		STATUS					 current
		DESCRIPTION			 " -- "
		::=  { gsmCellEntry  7 }


	cellMeasure		 OBJECT IDENTIFIER
		::=  { networkElementPlanCell  9 }


	eueMeasCellCfgTable		 OBJECT-TYPE
		SYNTAX					 SEQUENCE  OF	 EueMeasCellCfgEntry
		MAX-ACCESS			 not-accessible
		STATUS					 current
		DESCRIPTION			 " -- "
		::=  { cellMeasure  1 }


	eueMeasCellCfgEntry		 OBJECT-TYPE
		SYNTAX					 EueMeasCellCfgEntry
		MAX-ACCESS			 not-accessible
		STATUS					 current
		DESCRIPTION			 " -- "
		INDEX						{ eueMeasCellCfgLcId }
		::=  { eueMeasCellCfgTable  1 }


	EueMeasCellCfgEntry		 ::=  SEQUENCE {
		eueMeasCellCfgLcId					Integer32,
		eueMeasCellRowStatus					RowStatus,
		eueMeasCellTimeEvalution					INTEGER,
		eueMeasCellTimeHystNormal					INTEGER,
		eueMeasCellNumCellChangeMedium					Integer32,
		eueMeasCellNumCellChangeHigh					Integer32,
		eueMeasCellsfMedium					INTEGER,
		eueMeasCellsfHigh					INTEGER,
		eueMeasCellSMeasureRsrp					Integer32,
		eueMeasCellRsrpFilterCoeff					INTEGER,
		eueMeasCellRsrqFilterCoeff					INTEGER
		}


	eueMeasCellCfgLcId		 OBJECT-TYPE
		SYNTAX					 Integer32( 0 .. 23 )
		MAX-ACCESS			 not-accessible
		STATUS					 current
		DESCRIPTION			 " -- "
		::=  { eueMeasCellCfgEntry  1 }


	eueMeasCellRowStatus		 OBJECT-TYPE
		SYNTAX					 RowStatus
		MAX-ACCESS			 read-create
		STATUS					 current
		DESCRIPTION			 " -- "
		::=  { eueMeasCellCfgEntry  2 }


	eueMeasCellTimeEvalution		 OBJECT-TYPE
		SYNTAX					 INTEGER{ s30(0),s60(1),s120(2),s180(3),s240(4)  }
		MAX-ACCESS			 read-create
		STATUS					 current
		DESCRIPTION			 " -- "
		::=  { eueMeasCellCfgEntry  3 }


	eueMeasCellTimeHystNormal		 OBJECT-TYPE
		SYNTAX					 INTEGER{ s30(0),s60(1),s120(2),s180(3),s240(4)  }
		MAX-ACCESS			 read-create
		STATUS					 current
		DESCRIPTION			 " -- "
		::=  { eueMeasCellCfgEntry  4 }


	eueMeasCellNumCellChangeMedium		 OBJECT-TYPE
		SYNTAX					 Integer32( 1 .. 16 )
		MAX-ACCESS			 read-create
		STATUS					 current
		DESCRIPTION			 " -- "
		::=  { eueMeasCellCfgEntry  5 }


	eueMeasCellNumCellChangeHigh		 OBJECT-TYPE
		SYNTAX					 Integer32( 1 .. 16 )
		MAX-ACCESS			 read-create
		STATUS					 current
		DESCRIPTION			 " -- "
		::=  { eueMeasCellCfgEntry  6 }


	eueMeasCellsfMedium		 OBJECT-TYPE
		SYNTAX					 INTEGER{ oDt25(0),oDot5(1),oDot75(2),one(3)  }
		MAX-ACCESS			 read-create
		STATUS					 current
		DESCRIPTION			 " -- "
		::=  { eueMeasCellCfgEntry  7 }


	eueMeasCellsfHigh		 OBJECT-TYPE
		SYNTAX					 INTEGER{ oDot25(0),oDot5(1),oDot75(2),one(3)  }
		MAX-ACCESS			 read-create
		STATUS					 current
		DESCRIPTION			 " -- "
		::=  { eueMeasCellCfgEntry  8 }


	eueMeasCellSMeasureRsrp		 OBJECT-TYPE
		SYNTAX					 Integer32( -140 .. -44 )
		MAX-ACCESS			 read-create
		STATUS					 current
		DESCRIPTION			 " -- "
		::=  { eueMeasCellCfgEntry  9 }


	eueMeasCellRsrpFilterCoeff		 OBJECT-TYPE
		SYNTAX					 INTEGER{ k0(0),k1(1),k2(2),k3(3),k4(4),k5(5),k6(6),k7(7),k8(8),k9(9),k11(10),k13(11),k15(12),k17(13),k19(14)  }
		MAX-ACCESS			 read-create
		STATUS					 current
		DESCRIPTION			 " -- "
		::=  { eueMeasCellCfgEntry  10 }


	eueMeasCellRsrqFilterCoeff		 OBJECT-TYPE
		SYNTAX					 INTEGER{ k0(0),k1(1),k2(2),k3(3),k4(4),k5(5),k6(6),k7(7),k8(8),k9(9),k11(10),k13(11),k15(12),k17(13),k19(14)  }
		MAX-ACCESS			 read-create
		STATUS					 current
		DESCRIPTION			 " -- "
		::=  { eueMeasCellCfgEntry  11 }


	eventA1Table		 OBJECT-TYPE
		SYNTAX					 SEQUENCE  OF	 EventA1Entry
		MAX-ACCESS			 not-accessible
		STATUS					 current
		DESCRIPTION			 " -- "
		::=  { cellMeasure  2 }


	eventA1Entry		 OBJECT-TYPE
		SYNTAX					 EventA1Entry
		MAX-ACCESS			 not-accessible
		STATUS					 current
		DESCRIPTION			 " -- "
		INDEX						{ a1LcId,a1CfgId }
		::=  { eventA1Table  1 }


	EventA1Entry		 ::=  SEQUENCE {
		a1LcId					Integer32,
		a1CfgId					Integer32,
		a1RowStatus					RowStatus,
		a1TrigQuantity					INTEGER,
		a1RptQuantity					INTEGER,
		a1Hysteresis					INTEGER,
		a1TimetoTrig					INTEGER,
		a1MaxReportCell					Integer32,
		a1RptInterval					INTEGER,
		a1RptAmount					INTEGER,
		a1RptThresholdRsrp					Integer32,
		a1RptThresholdRsrq					INTEGER,
		a1MeasPurpose					INTEGER,
		a1MeasAlgoType					INTEGER
		}


	a1LcId		 OBJECT-TYPE
		SYNTAX					 Integer32( 0 .. 23 )
		MAX-ACCESS			 not-accessible
		STATUS					 current
		DESCRIPTION			 " -- "
		::=  { eventA1Entry  1 }


	a1CfgId		 OBJECT-TYPE
		SYNTAX					 Integer32( 0 .. 15 )
		MAX-ACCESS			 not-accessible
		STATUS					 current
		DESCRIPTION			 " -- "
		::=  { eventA1Entry  2 }


	a1RowStatus		 OBJECT-TYPE
		SYNTAX					 RowStatus
		MAX-ACCESS			 read-create
		STATUS					 current
		DESCRIPTION			 " -- "
		::=  { eventA1Entry  3 }


	a1TrigQuantity		 OBJECT-TYPE
		SYNTAX					 INTEGER{ rsrp(0),rsrq(1)  }
		MAX-ACCESS			 read-create
		STATUS					 current
		DESCRIPTION			 " -- "
		::=  { eventA1Entry  4 }


	a1RptQuantity		 OBJECT-TYPE
		SYNTAX					 INTEGER{ trigQuant(0),both(1)  }
		MAX-ACCESS			 read-create
		STATUS					 current
		DESCRIPTION			 " -- "
		::=  { eventA1Entry  5 }


	a1Hysteresis		 OBJECT-TYPE
		SYNTAX					 INTEGER{ hysteresis0(0),hysteresisPoint5(1),hysteresis1(2),hysteresis1point5(3),hysteresis2(4),hysteresis2point5(5),hysteresis3(6),hysteresis3point5(7),hysteresis4(8),hysteresis4point5(9),hysteresis5(10),hysteresis5point5(11),hysteresis6(12),hysteresis6point5(13),hysteresis7(14),hysteresis7point5(15),hysteresis8(16),hysteresis8point5(17),hysteresis9(18),hysteresis9point5(19),hysteresis10(20),hysteresis10point5(21),hysteresis11(22),hysteresis11point5(23),hysteresis12(24),hysteresis12point5(25),hysteresis13(26),hysteresis13point5(27),hysteresis14(28),hysteresis14point5(29),hysteresis15(30)  }
		MAX-ACCESS			 read-create
		STATUS					 current
		DESCRIPTION			 " -- "
		::=  { eventA1Entry  6 }


	a1TimetoTrig		 OBJECT-TYPE
		SYNTAX					 INTEGER{ ms0(0),ms40(1),ms64(2),ms80(3),ms100(4),ms128(5),ms160(6),ms256(7),ms320(8),ms480(9),ms512(10),ms640(11),ms1024(12),ms1280(13),ms2560(14),ms5120(15)  }
		MAX-ACCESS			 read-create
		STATUS					 current
		DESCRIPTION			 " -- "
		::=  { eventA1Entry  7 }


	a1MaxReportCell		 OBJECT-TYPE
		SYNTAX					 Integer32( 1 .. 8 )
		MAX-ACCESS			 read-create
		STATUS					 current
		DESCRIPTION			 " -- "
		::=  { eventA1Entry  8 }


	a1RptInterval		 OBJECT-TYPE
		SYNTAX					 INTEGER{ ms120(0),ms240(1),ms480(2),ms640(3),ms1024(4),ms2048(5),ms65120(6),ms10240(7),min1(8),min6(9),min12(10),min30(11),min60(12)  }
		MAX-ACCESS			 read-create
		STATUS					 current
		DESCRIPTION			 " -- "
		::=  { eventA1Entry  9 }


	a1RptAmount		 OBJECT-TYPE
		SYNTAX					 INTEGER{ r1(0),r2(1),r4(2),r8(3),r16(4),r32(5),r64(6),infinity(7)  }
		MAX-ACCESS			 read-create
		STATUS					 current
		DESCRIPTION			 " -- "
		::=  { eventA1Entry  10 }


	a1RptThresholdRsrp		 OBJECT-TYPE
		SYNTAX					 Integer32( -140 .. -44 )
		MAX-ACCESS			 read-create
		STATUS					 current
		DESCRIPTION			 " -- "
		::=  { eventA1Entry  11 }


	a1RptThresholdRsrq		 OBJECT-TYPE
		SYNTAX					 INTEGER{ rsrqLessMinus19point5(0),rsrqMinus19point5(1),rsrqMinus19(2),rsrqMinus18point5(3),rsrqMinus18(4),rsrqMinus17point5(5),rsrqMinus17(6),rsrqMinus16point5(7),rsrqMinus16(8),rsrqMinus15point5(9),rsrqMinus15(10),rsrqMinus14point5(11),rsrqMinus14(12),rsrqMinus13point5(13),rsrqMinus13(14),rsrqMinus12point5(15),rsrqMinus12(16),rsrqMinus11point5(17),rsrqMinus11(18),rsrqMinus10poing5(19),rsrqMinus10(20),rsrqMinus9point5(21),rsrqMinus9(22),rsrqMinus8point5(23),rsrqMinus8(24),rsrqMinus7point5(25),rsrqMinus7(26),rsrqMinus6point5(27),rsrqMinus6(28),rsrqMinus5point5(29),rsrqMinus5(30),rsrqMinus4point5(31),rsrqMinus4(32),rsrqMinus3point5(33),rsrqMinus3(34)  }
		MAX-ACCESS			 read-create
		STATUS					 current
		DESCRIPTION			 " -- "
		::=  { eventA1Entry  12 }


	a1MeasPurpose		 OBJECT-TYPE
		SYNTAX					 INTEGER{ csStopInterFreqMeas(0),tendFreqGoldUserStopInterFreqMeas(1),untendFreqGoldUserStopInterFreqMeas(2),tendFreqStopInterFreqMeas(3),untendFreqStopInterFreqMeas(4),stopInterratPSServiceMeas(5),stopInterratCSServiceMeas(6),stopInterFreqMeas(7),invalid(8)  }
		MAX-ACCESS			 read-create
		STATUS					 current
		DESCRIPTION			 " -- "
		::=  { eventA1Entry  13 }


	a1MeasAlgoType		 OBJECT-TYPE
		SYNTAX					 INTEGER{ handover(0),invalid(5)  }
		MAX-ACCESS			 read-create
		STATUS					 current
		DESCRIPTION			 " -- "
		::=  { eventA1Entry  14 }


	eventA2Table		 OBJECT-TYPE
		SYNTAX					 SEQUENCE  OF	 EventA2Entry
		MAX-ACCESS			 not-accessible
		STATUS					 current
		DESCRIPTION			 " -- "
		::=  { cellMeasure  3 }


	eventA2Entry		 OBJECT-TYPE
		SYNTAX					 EventA2Entry
		MAX-ACCESS			 not-accessible
		STATUS					 current
		DESCRIPTION			 " -- "
		INDEX						{ a2LcId,a2CfgId }
		::=  { eventA2Table  1 }


	EventA2Entry		 ::=  SEQUENCE {
		a2LcId					Integer32,
		a2CfgId					Integer32,
		a2RowStatus					RowStatus,
		a2TrigQuantity					INTEGER,
		a2RptQuantity					INTEGER,
		a2Hysteresis					INTEGER,
		a2TimetoTrig					INTEGER,
		a2MaxReportCell					Integer32,
		a2RptInterval					INTEGER,
		a2RptAmount					INTEGER,
		a2RptThresholdRsrp					Integer32,
		a2RptThresholdRsrq					INTEGER,
		a2MeasPurpose					INTEGER,
		a2MeasAlgoType					INTEGER,
		a2MdtRptThresholdRsrp					Integer32,
		a2MdtRptThresholdRsrq					INTEGER
		}


	a2LcId		 OBJECT-TYPE
		SYNTAX					 Integer32( 0 .. 23 )
		MAX-ACCESS			 not-accessible
		STATUS					 current
		DESCRIPTION			 " -- "
		::=  { eventA2Entry  1 }


	a2CfgId		 OBJECT-TYPE
		SYNTAX					 Integer32( 0 .. 15 )
		MAX-ACCESS			 not-accessible
		STATUS					 current
		DESCRIPTION			 " -- "
		::=  { eventA2Entry  2 }


	a2RowStatus		 OBJECT-TYPE
		SYNTAX					 RowStatus
		MAX-ACCESS			 read-create
		STATUS					 current
		DESCRIPTION			 " -- "
		::=  { eventA2Entry  3 }


	a2TrigQuantity		 OBJECT-TYPE
		SYNTAX					 INTEGER{ rsrp(0),rsrq(1)  }
		MAX-ACCESS			 read-create
		STATUS					 current
		DESCRIPTION			 " -- "
		::=  { eventA2Entry  4 }


	a2RptQuantity		 OBJECT-TYPE
		SYNTAX					 INTEGER{ trigQuant(0),both(1)  }
		MAX-ACCESS			 read-create
		STATUS					 current
		DESCRIPTION			 " -- "
		::=  { eventA2Entry  5 }


	a2Hysteresis		 OBJECT-TYPE
		SYNTAX					 INTEGER{ hysteresis0(0),hysteresisPoint5(1),hysteresis1(2),hysteresis1point5(3),hysteresis2(4),hysteresis2point5(5),hysteresis3(6),hysteresis3point5(7),hysteresis4(8),hysteresis4point5(9),hysteresis5(10),hysteresis5point5(11),hysteresis6(12),hysteresis6point5(13),hysteresis7(14),hysteresis7point5(15),hysteresis8(16),hysteresis8point5(17),hysteresis9(18),hysteresis9point5(19),hysteresis10(20),hysteresis10point5(21),hysteresis11(22),hysteresis11point5(23),hysteresis12(24),hysteresis12point5(25),hysteresis13(26),hysteresis13point5(27),hysteresis14(28),hysteresis14point5(29),hysteresis15(30)  }
		MAX-ACCESS			 read-create
		STATUS					 current
		DESCRIPTION			 " -- "
		::=  { eventA2Entry  6 }


	a2TimetoTrig		 OBJECT-TYPE
		SYNTAX					 INTEGER{ ms0(0),ms40(1),ms64(2),ms80(3),ms100(4),ms128(5),ms160(6),ms256(7),ms320(8),ms480(9),ms512(10),ms640(11),ms1024(12),ms1280(13),ms2560(14),ms5120(15)  }
		MAX-ACCESS			 read-create
		STATUS					 current
		DESCRIPTION			 " -- "
		::=  { eventA2Entry  7 }


	a2MaxReportCell		 OBJECT-TYPE
		SYNTAX					 Integer32( 1 .. 8 )
		MAX-ACCESS			 read-create
		STATUS					 current
		DESCRIPTION			 " -- "
		::=  { eventA2Entry  8 }


	a2RptInterval		 OBJECT-TYPE
		SYNTAX					 INTEGER{ ms120(0),ms240(1),ms480(2),ms640(3),ms1024(4),ms2048(5),ms65120(6),ms10240(7),min1(8),min6(9),min12(10),min30(11),min60(12)  }
		MAX-ACCESS			 read-create
		STATUS					 current
		DESCRIPTION			 " -- "
		::=  { eventA2Entry  9 }


	a2RptAmount		 OBJECT-TYPE
		SYNTAX					 INTEGER{ r1(0),r2(1),r4(2),r8(3),r16(4),r32(5),r64(6),infinity(7)  }
		MAX-ACCESS			 read-create
		STATUS					 current
		DESCRIPTION			 " -- "
		::=  { eventA2Entry  10 }


	a2RptThresholdRsrp		 OBJECT-TYPE
		SYNTAX					 Integer32( -140 .. -44 )
		MAX-ACCESS			 read-create
		STATUS					 current
		DESCRIPTION			 " -- "
		::=  { eventA2Entry  11 }


	a2RptThresholdRsrq		 OBJECT-TYPE
		SYNTAX					 INTEGER{ rsrqLessMinus19point5(0),rsrqMinus19point5(1),rsrqMinus19(2),rsrqMinus18point5(3),rsrqMinus18(4),rsrqMinus17point5(5),rsrqMinus17(6),rsrqMinus16point5(7),rsrqMinus16(8),rsrqMinus15point5(9),rsrqMinus15(10),rsrqMinus14point5(11),rsrqMinus14(12),rsrqMinus13point5(13),rsrqMinus13(14),rsrqMinus12point5(15),rsrqMinus12(16),rsrqMinus11point5(17),rsrqMinus11(18),rsrqMinus10poing5(19),rsrqMinus10(20),rsrqMinus9point5(21),rsrqMinus9(22),rsrqMinus8point5(23),rsrqMinus8(24),rsrqMinus7point5(25),rsrqMinus7(26),rsrqMinus6point5(27),rsrqMinus6(28),rsrqMinus5point5(29),rsrqMinus5(30),rsrqMinus4point5(31),rsrqMinus4(32),rsrqMinus3point5(33),rsrqMinus3(34)  }
		MAX-ACCESS			 read-create
		STATUS					 current
		DESCRIPTION			 " -- "
		::=  { eventA2Entry  12 }


	a2MeasPurpose		 OBJECT-TYPE
		SYNTAX					 INTEGER{ csStartInterFreqMeas(0),rejectQci1Setup(1),startInterRatMeasfordata(2),mdt(3),blindRedirectHO(4),startInterRatMeasforspeech(5),startInterFreqMeas(6),disActiveScell(7),invalid(8),tendFreqStartInterFreqMeas(9),untendFreqStartInterFreqMeas(10),tendFreqGoldUserStartInterFreqMeas(11),untendFreqGoldUserStartInterFreqMeas(12)  }
		MAX-ACCESS			 read-create
		STATUS					 current
		DESCRIPTION			 " -- "
		::=  { eventA2Entry  13 }


	a2MeasAlgoType		 OBJECT-TYPE
		SYNTAX					 INTEGER{ handover(0),casCellConfig(1),mdt(2),invalid(5)  }
		MAX-ACCESS			 read-create
		STATUS					 current
		DESCRIPTION			 " -- "
		::=  { eventA2Entry  14 }


	a2MdtRptThresholdRsrp		 OBJECT-TYPE
		SYNTAX					 Integer32( -140 .. -44 )
		MAX-ACCESS			 read-create
		STATUS					 current
		DESCRIPTION			 " -- "
		::=  { eventA2Entry  15 }


	a2MdtRptThresholdRsrq		 OBJECT-TYPE
		SYNTAX					 INTEGER{ rsrqLessMinus19point5(0),rsrqMinus19point5(1),rsrqMinus19(2),rsrqMinus18point5(3),rsrqMinus18(4),rsrqMinus17point5(5),rsrqMinus17(6),rsrqMinus16point5(7),rsrqMinus16(8),rsrqMinus15point5(9),rsrqMinus15(10),rsrqMinus14point5(11),rsrqMinus14(12),rsrqMinus13point5(13),rsrqMinus13(14),rsrqMinus12point5(15),rsrqMinus12(16),rsrqMinus11point5(17),rsrqMinus11(18),rsrqMinus10poing5(19),rsrqMinus10(20),rsrqMinus9point5(21),rsrqMinus9(22),rsrqMinus8point5(23),rsrqMinus8(24),rsrqMinus7point5(25),rsrqMinus7(26),rsrqMinus6point5(27),rsrqMinus6(28),rsrqMinus5point5(29),rsrqMinus5(30),rsrqMinus4point5(31),rsrqMinus4(32),rsrqMinus3point5(33),rsrqMinus3(34)  }
		MAX-ACCESS			 read-create
		STATUS					 current
		DESCRIPTION			 " -- "
		::=  { eventA2Entry  16 }


	eventA3Table		 OBJECT-TYPE
		SYNTAX					 SEQUENCE  OF	 EventA3Entry
		MAX-ACCESS			 not-accessible
		STATUS					 current
		DESCRIPTION			 " -- "
		::=  { cellMeasure  4 }


	eventA3Entry		 OBJECT-TYPE
		SYNTAX					 EventA3Entry
		MAX-ACCESS			 not-accessible
		STATUS					 current
		DESCRIPTION			 " -- "
		INDEX						{ a3LcId,a3CfgId }
		::=  { eventA3Table  1 }


	EventA3Entry		 ::=  SEQUENCE {
		a3LcId					Integer32,
		a3CfgId					Integer32,
		a3RowStatus					RowStatus,
		a3TrigQuantity					INTEGER,
		a3RptQuantity					INTEGER,
		a3Hysteresis					INTEGER,
		a3TimetoTrig					INTEGER,
		a3MaxReportCell					Integer32,
		a3RptInterval					INTEGER,
		a3RptAmount					INTEGER,
		a3Offset					INTEGER,
		a3MeasPurpose					INTEGER,
		a3MeasAlgoType					INTEGER
		}


	a3LcId		 OBJECT-TYPE
		SYNTAX					 Integer32( 0 .. 23 )
		MAX-ACCESS			 not-accessible
		STATUS					 current
		DESCRIPTION			 " -- "
		::=  { eventA3Entry  1 }


	a3CfgId		 OBJECT-TYPE
		SYNTAX					 Integer32( 0 .. 15 )
		MAX-ACCESS			 not-accessible
		STATUS					 current
		DESCRIPTION			 " -- "
		::=  { eventA3Entry  2 }


	a3RowStatus		 OBJECT-TYPE
		SYNTAX					 RowStatus
		MAX-ACCESS			 read-create
		STATUS					 current
		DESCRIPTION			 " -- "
		::=  { eventA3Entry  3 }


	a3TrigQuantity		 OBJECT-TYPE
		SYNTAX					 INTEGER{ rsrp(0),rsrq(1)  }
		MAX-ACCESS			 read-create
		STATUS					 current
		DESCRIPTION			 " -- "
		::=  { eventA3Entry  4 }


	a3RptQuantity		 OBJECT-TYPE
		SYNTAX					 INTEGER{ trigQuant(0),both(1)  }
		MAX-ACCESS			 read-create
		STATUS					 current
		DESCRIPTION			 " -- "
		::=  { eventA3Entry  5 }


	a3Hysteresis		 OBJECT-TYPE
		SYNTAX					 INTEGER{ hysteresis0(0),hysteresisPoint5(1),hysteresis1(2),hysteresis1point5(3),hysteresis2(4),hysteresis2point5(5),hysteresis3(6),hysteresis3point5(7),hysteresis4(8),hysteresis4point5(9),hysteresis5(10),hysteresis5point5(11),hysteresis6(12),hysteresis6point5(13),hysteresis7(14),hysteresis7point5(15),hysteresis8(16),hysteresis8point5(17),hysteresis9(18),hysteresis9point5(19),hysteresis10(20),hysteresis10point5(21),hysteresis11(22),hysteresis11point5(23),hysteresis12(24),hysteresis12point5(25),hysteresis13(26),hysteresis13point5(27),hysteresis14(28),hysteresis14point5(29),hysteresis15(30)  }
		MAX-ACCESS			 read-create
		STATUS					 current
		DESCRIPTION			 " -- "
		::=  { eventA3Entry  6 }


	a3TimetoTrig		 OBJECT-TYPE
		SYNTAX					 INTEGER{ ms0(0),ms40(1),ms64(2),ms80(3),ms100(4),ms128(5),ms160(6),ms256(7),ms320(8),ms480(9),ms512(10),ms640(11),ms1024(12),ms1280(13),ms2560(14),ms5120(15)  }
		MAX-ACCESS			 read-create
		STATUS					 current
		DESCRIPTION			 " -- "
		::=  { eventA3Entry  7 }


	a3MaxReportCell		 OBJECT-TYPE
		SYNTAX					 Integer32( 1 .. 8 )
		MAX-ACCESS			 read-create
		STATUS					 current
		DESCRIPTION			 " -- "
		::=  { eventA3Entry  8 }


	a3RptInterval		 OBJECT-TYPE
		SYNTAX					 INTEGER{ ms120(0),ms240(1),ms480(2),ms640(3),ms1024(4),ms2048(5),ms5120(6),ms10240(7),min1(8),min6(9),min12(10),min30(11),min60(12)  }
		MAX-ACCESS			 read-create
		STATUS					 current
		DESCRIPTION			 " -- "
		::=  { eventA3Entry  9 }


	a3RptAmount		 OBJECT-TYPE
		SYNTAX					 INTEGER{ r1(0),r2(1),r4(2),r8(3),r16(4),r32(5),r64(6),infinity(7)  }
		MAX-ACCESS			 read-create
		STATUS					 current
		DESCRIPTION			 " -- "
		::=  { eventA3Entry  10 }


	a3Offset		 OBJECT-TYPE
		SYNTAX					 INTEGER{ a3OffsetMinus15(0),a3OffsetMinus14Point5(1),a3OffsetMinus14(2),a3OffsetMinus13Point5(3),a3OffsetMinus13(4),a3OffsetMinus12Point5(5),a3OffsetMinus12(6),a3OffsetMinus11Point5(7),a3OffsetMinus11(8),a3OffsetMinus10Point5(9),a3OffsetMinus10(10),a3OffsetMinus9Point5(11),a3OffsetMinus9(12),a3OffsetMinus8Point5(13),a3OffsetMinus8(14),a3OffsetMinus7Point5(15),a3OffsetMinus7(16),a3OffsetMinus6Point5(17),a3OffsetMinus6(18),a3OffsetMinus5Point5(19),a3OffsetMinus5(20),a3OffsetMinus4Point5(21),a3OffsetMinus4(22),a3OffsetMinus3Point5(23),a3OffsetMinus3(24),a3OffsetMinus2Point5(25),a3OffsetMinus2(26),a3OffsetMinus1Point5(27),a3OffsetMinus1(28),a3OffsetMinusPoint5(29),a3Offset0(30),a3OffsetPoint5(31),a3Offset1(32),a3Offset1Point5(33),a3Offset2(34),a3Offset2Point5(35),a3Offset3(36),a3Offset3Point5(37),a3Offset4(38),a3Offset4Point5(39),a3Offset5(40),a3Offset5Point5(41),a3Offset6(42),a3Offset6Point5(43),a3Offset7(44),a3Offset7Point5(45),a3Offset8(46),a3Offset8Point5(47),a3Offset9(48),a3Offset9Point5(49),a3Offset10(50),a3Offset10Point5(51),a3Offset11(52),a3Offset11Point5(53),a3Offset12(54),a3Offset12Point5(55),a3Offset13(56),a3Offset13Point5(57),a3Offset14(58),a3Offset14Point5(59),a3Offset15(60)  }
		MAX-ACCESS			 read-create
		STATUS					 current
		DESCRIPTION			 " -- "
		::=  { eventA3Entry  11 }


	a3MeasPurpose		 OBJECT-TYPE
		SYNTAX					 INTEGER{ intraFreqPriHc(0),volteHc(1),icic(3),sCellConfig(4),coMP(5),anrFindAdjCell(6),mLB(7),invalid(8)  }
		MAX-ACCESS			 read-create
		STATUS					 current
		DESCRIPTION			 " -- "
		::=  { eventA3Entry  12 }


	a3MeasAlgoType		 OBJECT-TYPE
		SYNTAX					 INTEGER{ handover(0),icic(1),coMP(2),anr(3),sCellConfig(4),invalid(5),mLB(6)  }
		MAX-ACCESS			 read-create
		STATUS					 current
		DESCRIPTION			 " -- "
		::=  { eventA3Entry  13 }


	eventA4Table		 OBJECT-TYPE
		SYNTAX					 SEQUENCE  OF	 EventA4Entry
		MAX-ACCESS			 not-accessible
		STATUS					 current
		DESCRIPTION			 " -- "
		::=  { cellMeasure  5 }


	eventA4Entry		 OBJECT-TYPE
		SYNTAX					 EventA4Entry
		MAX-ACCESS			 not-accessible
		STATUS					 current
		DESCRIPTION			 " -- "
		INDEX						{ a4LcId,a4CfgId }
		::=  { eventA4Table  1 }


	EventA4Entry		 ::=  SEQUENCE {
		a4LcId					Integer32,
		a4CfgId					Integer32,
		a4RowStatus					RowStatus,
		a4TrigQuantity					INTEGER,
		a4RptQuantity					INTEGER,
		a4Hysteresis					INTEGER,
		a4TimetoTrig					INTEGER,
		a4MaxReportCell					Integer32,
		a4RptInterval					INTEGER,
		a4RptAmount					INTEGER,
		a4RptThresholdRsrp					Integer32,
		a4RptThresholdRsrq					INTEGER,
		a4MeasPurpose					INTEGER,
		a4MeasAlgoType					INTEGER
		}


	a4LcId		 OBJECT-TYPE
		SYNTAX					 Integer32( 0 .. 23 )
		MAX-ACCESS			 not-accessible
		STATUS					 current
		DESCRIPTION			 " -- "
		::=  { eventA4Entry  1 }


	a4CfgId		 OBJECT-TYPE
		SYNTAX					 Integer32( 0 .. 15 )
		MAX-ACCESS			 not-accessible
		STATUS					 current
		DESCRIPTION			 " -- "
		::=  { eventA4Entry  2 }


	a4RowStatus		 OBJECT-TYPE
		SYNTAX					 RowStatus
		MAX-ACCESS			 read-create
		STATUS					 current
		DESCRIPTION			 " -- "
		::=  { eventA4Entry  3 }


	a4TrigQuantity		 OBJECT-TYPE
		SYNTAX					 INTEGER{ rsrp(0),rsrq(1)  }
		MAX-ACCESS			 read-create
		STATUS					 current
		DESCRIPTION			 " -- "
		::=  { eventA4Entry  4 }


	a4RptQuantity		 OBJECT-TYPE
		SYNTAX					 INTEGER{ trigQuant(0),both(1)  }
		MAX-ACCESS			 read-create
		STATUS					 current
		DESCRIPTION			 " -- "
		::=  { eventA4Entry  5 }


	a4Hysteresis		 OBJECT-TYPE
		SYNTAX					 INTEGER{ hysteresis0(0),hysteresisPoint5(1),hysteresis1(2),hysteresis1point5(3),hysteresis2(4),hysteresis2point5(5),hysteresis3(6),hysteresis3point5(7),hysteresis4(8),hysteresis4point5(9),hysteresis5(10),hysteresis5point5(11),hysteresis6(12),hysteresis6point5(13),hysteresis7(14),hysteresis7point5(15),hysteresis8(16),hysteresis8point5(17),hysteresis9(18),hysteresis9point5(19),hysteresis10(20),hysteresis10point5(21),hysteresis11(22),hysteresis11point5(23),hysteresis12(24),hysteresis12point5(25),hysteresis13(26),hysteresis13point5(27),hysteresis14(28),hysteresis14point5(29),hysteresis15(30)  }
		MAX-ACCESS			 read-create
		STATUS					 current
		DESCRIPTION			 " -- "
		::=  { eventA4Entry  6 }


	a4TimetoTrig		 OBJECT-TYPE
		SYNTAX					 INTEGER{ ms0(0),ms40(1),ms64(2),ms80(3),ms100(4),ms128(5),ms160(6),ms256(7),ms320(8),ms480(9),ms512(10),ms640(11),ms1024(12),ms1280(13),ms2560(14),ms5120(15)  }
		MAX-ACCESS			 read-create
		STATUS					 current
		DESCRIPTION			 " -- "
		::=  { eventA4Entry  7 }


	a4MaxReportCell		 OBJECT-TYPE
		SYNTAX					 Integer32( 1 .. 8 )
		MAX-ACCESS			 read-create
		STATUS					 current
		DESCRIPTION			 " -- "
		::=  { eventA4Entry  8 }


	a4RptInterval		 OBJECT-TYPE
		SYNTAX					 INTEGER{ ms120(0),ms240(1),ms480(2),ms640(3),ms1024(4),ms2048(5),ms5120(6),ms10240(7),min1(8),min6(9),min12(10),min30(11),min60(12)  }
		MAX-ACCESS			 read-create
		STATUS					 current
		DESCRIPTION			 " -- "
		::=  { eventA4Entry  9 }


	a4RptAmount		 OBJECT-TYPE
		SYNTAX					 INTEGER{ r1(0),r2(1),r4(2),r8(3),r16(4),r32(5),r64(6),infinity(7)  }
		MAX-ACCESS			 read-create
		STATUS					 current
		DESCRIPTION			 " -- "
		::=  { eventA4Entry  10 }


	a4RptThresholdRsrp		 OBJECT-TYPE
		SYNTAX					 Integer32( -140 .. -44 )
		MAX-ACCESS			 read-create
		STATUS					 current
		DESCRIPTION			 " -- "
		::=  { eventA4Entry  11 }


	a4RptThresholdRsrq		 OBJECT-TYPE
		SYNTAX					 INTEGER{ rsrqLessMinus19point5(0),rsrqMinus19point5(1),rsrqMinus19(2),rsrqMinus18point5(3),rsrqMinus18(4),rsrqMinus17point5(5),rsrqMinus17(6),rsrqMinus16point5(7),rsrqMinus16(8),rsrqMinus15point5(9),rsrqMinus15(10),rsrqMinus14point5(11),rsrqMinus14(12),rsrqMinus13point5(13),rsrqMinus13(14),rsrqMinus12point5(15),rsrqMinus12(16),rsrqMinus11point5(17),rsrqMinus11(18),rsrqMinus10poing5(19),rsrqMinus10(20),rsrqMinus9point5(21),rsrqMinus9(22),rsrqMinus8point5(23),rsrqMinus8(24),rsrqMinus7point5(25),rsrqMinus7(26),rsrqMinus6point5(27),rsrqMinus6(28),rsrqMinus5point5(29),rsrqMinus5(30),rsrqMinus4point5(31),rsrqMinus4(32),rsrqMinus3point5(33),rsrqMinus3(34)  }
		MAX-ACCESS			 read-create
		STATUS					 current
		DESCRIPTION			 " -- "
		::=  { eventA4Entry  12 }


	a4MeasPurpose		 OBJECT-TYPE
		SYNTAX					 INTEGER{ qciAppointFreHc(0),highFreqPriHc(1),shuttingdown(2),loadBalance(3),activeScell(4),hcBasedSpeed(5),anrFindAdjCell(6),volteAppointFreHc(7),invalid(8),volteHc(9),appointFreHc(10),goldUserAppointFreHc(11),hcBasedVoQuality(13)  }
		MAX-ACCESS			 read-create
		STATUS					 current
		DESCRIPTION			 " -- "
		::=  { eventA4Entry  13 }


	a4MeasAlgoType		 OBJECT-TYPE
		SYNTAX					 INTEGER{ handover(0),casCellConfig(1),hcBasedSpeed(2),anr(3),invalid(5)  }
		MAX-ACCESS			 read-create
		STATUS					 current
		DESCRIPTION			 " -- "
		::=  { eventA4Entry  14 }


	eventA5Table		 OBJECT-TYPE
		SYNTAX					 SEQUENCE  OF	 EventA5Entry
		MAX-ACCESS			 not-accessible
		STATUS					 current
		DESCRIPTION			 " -- "
		::=  { cellMeasure  6 }


	eventA5Entry		 OBJECT-TYPE
		SYNTAX					 EventA5Entry
		MAX-ACCESS			 not-accessible
		STATUS					 current
		DESCRIPTION			 " -- "
		INDEX						{ a5LcId,a5CfgId }
		::=  { eventA5Table  1 }


	EventA5Entry		 ::=  SEQUENCE {
		a5LcId					Integer32,
		a5CfgId					Integer32,
		a5RowStatus					RowStatus,
		a5TrigQuantity					INTEGER,
		a5RptQuantity					INTEGER,
		a5Hysteresis					INTEGER,
		a5TimetoTrig					INTEGER,
		a5MaxReportCell					Integer32,
		a5RptInterval					INTEGER,
		a5RptAmount					INTEGER,
		a5RptThreshold1Rsrp					Integer32,
		a5RptThreshold1Rsrq					INTEGER,
		a5RptThreshold2Rsrp					Integer32,
		a5RptThreshold2Rsrq					INTEGER,
		a5MeasPurpose					INTEGER,
		a5MeasAlgoType					INTEGER
		}


	a5LcId		 OBJECT-TYPE
		SYNTAX					 Integer32( 0 .. 23 )
		MAX-ACCESS			 not-accessible
		STATUS					 current
		DESCRIPTION			 " -- "
		::=  { eventA5Entry  1 }


	a5CfgId		 OBJECT-TYPE
		SYNTAX					 Integer32( 0 .. 15 )
		MAX-ACCESS			 not-accessible
		STATUS					 current
		DESCRIPTION			 " -- "
		::=  { eventA5Entry  2 }


	a5RowStatus		 OBJECT-TYPE
		SYNTAX					 RowStatus
		MAX-ACCESS			 read-create
		STATUS					 current
		DESCRIPTION			 " -- "
		::=  { eventA5Entry  3 }


	a5TrigQuantity		 OBJECT-TYPE
		SYNTAX					 INTEGER{ rsrp(0),rsrq(1)  }
		MAX-ACCESS			 read-create
		STATUS					 current
		DESCRIPTION			 " -- "
		::=  { eventA5Entry  4 }


	a5RptQuantity		 OBJECT-TYPE
		SYNTAX					 INTEGER{ trigQuant(0),both(1)  }
		MAX-ACCESS			 read-create
		STATUS					 current
		DESCRIPTION			 " -- "
		::=  { eventA5Entry  5 }


	a5Hysteresis		 OBJECT-TYPE
		SYNTAX					 INTEGER{ hysteresis0(0),hysteresisPoint5(1),hysteresis1(2),hysteresis1point5(3),hysteresis2(4),hysteresis2point5(5),hysteresis3(6),hysteresis3point5(7),hysteresis4(8),hysteresis4point5(9),hysteresis5(10),hysteresis5point5(11),hysteresis6(12),hysteresis6point5(13),hysteresis7(14),hysteresis7point5(15),hysteresis8(16),hysteresis8point5(17),hysteresis9(18),hysteresis9point5(19),hysteresis10(20),hysteresis10point5(21),hysteresis11(22),hysteresis11point5(23),hysteresis12(24),hysteresis12point5(25),hysteresis13(26),hysteresis13point5(27),hysteresis14(28),hysteresis14point5(29),hysteresis15(30)  }
		MAX-ACCESS			 read-create
		STATUS					 current
		DESCRIPTION			 " -- "
		::=  { eventA5Entry  6 }


	a5TimetoTrig		 OBJECT-TYPE
		SYNTAX					 INTEGER{ ms0(0),ms40(1),ms64(2),ms80(3),ms100(4),ms128(5),ms160(6),ms256(7),ms320(8),ms480(9),ms512(10),ms640(11),ms1024(12),ms1280(13),ms2560(14),ms5120(15)  }
		MAX-ACCESS			 read-create
		STATUS					 current
		DESCRIPTION			 " -- "
		::=  { eventA5Entry  7 }


	a5MaxReportCell		 OBJECT-TYPE
		SYNTAX					 Integer32( 1 .. 8 )
		MAX-ACCESS			 read-create
		STATUS					 current
		DESCRIPTION			 " -- "
		::=  { eventA5Entry  8 }


	a5RptInterval		 OBJECT-TYPE
		SYNTAX					 INTEGER{ ms120(0),ms240(1),ms480(2),ms640(3),ms1024(4),ms2048(5),ms5120(6),ms10240(7),min1(8),min6(9),min12(10),min30(11),min60(12)  }
		MAX-ACCESS			 read-create
		STATUS					 current
		DESCRIPTION			 " -- "
		::=  { eventA5Entry  9 }


	a5RptAmount		 OBJECT-TYPE
		SYNTAX					 INTEGER{ r1(0),r2(1),r4(2),r8(3),r16(4),r32(5),r64(6),infinity(7)  }
		MAX-ACCESS			 read-create
		STATUS					 current
		DESCRIPTION			 " -- "
		::=  { eventA5Entry  10 }


	a5RptThreshold1Rsrp		 OBJECT-TYPE
		SYNTAX					 Integer32( -140 .. -44 )
		MAX-ACCESS			 read-create
		STATUS					 current
		DESCRIPTION			 " -- "
		::=  { eventA5Entry  11 }


	a5RptThreshold1Rsrq		 OBJECT-TYPE
		SYNTAX					 INTEGER{ rsrqLessMinus19point5(0),rsrqMinus19point5(1),rsrqMinus19(2),rsrqMinus18point5(3),rsrqMinus18(4),rsrqMinus17point5(5),rsrqMinus17(6),rsrqMinus16point5(7),rsrqMinus16(8),rsrqMinus15point5(9),rsrqMinus15(10),rsrqMinus14point5(11),rsrqMinus14(12),rsrqMinus13point5(13),rsrqMinus13(14),rsrqMinus12point5(15),rsrqMinus12(16),rsrqMinus11point5(17),rsrqMinus11(18),rsrqMinus10poing5(19),rsrqMinus10(20),rsrqMinus9point5(21),rsrqMinus9(22),rsrqMinus8point5(23),rsrqMinus8(24),rsrqMinus7point5(25),rsrqMinus7(26),rsrqMinus6point5(27),rsrqMinus6(28),rsrqMinus5point5(29),rsrqMinus5(30),rsrqMinus4point5(31),rsrqMinus4(32),rsrqMinus3point5(33),rsrqMinus3(34)  }
		MAX-ACCESS			 read-create
		STATUS					 current
		DESCRIPTION			 " -- "
		::=  { eventA5Entry  12 }


	a5RptThreshold2Rsrp		 OBJECT-TYPE
		SYNTAX					 Integer32( -140 .. -44 )
		MAX-ACCESS			 read-create
		STATUS					 current
		DESCRIPTION			 " -- "
		::=  { eventA5Entry  13 }


	a5RptThreshold2Rsrq		 OBJECT-TYPE
		SYNTAX					 INTEGER{ rsrqLessMinus19point5(0),rsrqMinus19point5(1),rsrqMinus19(2),rsrqMinus18point5(3),rsrqMinus18(4),rsrqMinus17point5(5),rsrqMinus17(6),rsrqMinus16point5(7),rsrqMinus16(8),rsrqMinus15point5(9),rsrqMinus15(10),rsrqMinus14point5(11),rsrqMinus14(12),rsrqMinus13point5(13),rsrqMinus13(14),rsrqMinus12point5(15),rsrqMinus12(16),rsrqMinus11point5(17),rsrqMinus11(18),rsrqMinus10poing5(19),rsrqMinus10(20),rsrqMinus9point5(21),rsrqMinus9(22),rsrqMinus8point5(23),rsrqMinus8(24),rsrqMinus7point5(25),rsrqMinus7(26),rsrqMinus6point5(27),rsrqMinus6(28),rsrqMinus5point5(29),rsrqMinus5(30),rsrqMinus4point5(31),rsrqMinus4(32),rsrqMinus3point5(33),rsrqMinus3(34)  }
		MAX-ACCESS			 read-create
		STATUS					 current
		DESCRIPTION			 " -- "
		::=  { eventA5Entry  14 }


	a5MeasPurpose		 OBJECT-TYPE
		SYNTAX					 INTEGER{ qciAppointFrePPsuppression(0),lowFreqPriHc(2),loadBlancePPsuppression(3),frePPsuppression(4),volteHc(5),anrFindAdjCell(6),volteFrePPsuppression(7),invalid(8),goldUserFrePPsuppression(9),hcBasedVoQualityPPsuppression(10)  }
		MAX-ACCESS			 read-create
		STATUS					 current
		DESCRIPTION			 " -- "
		::=  { eventA5Entry  15 }


	a5MeasAlgoType		 OBJECT-TYPE
		SYNTAX					 INTEGER{ handover(0),anr(3),invalid(5)  }
		MAX-ACCESS			 read-create
		STATUS					 current
		DESCRIPTION			 " -- "
		::=  { eventA5Entry  16 }


	euePeriodReportTable		 OBJECT-TYPE
		SYNTAX					 SEQUENCE  OF	 EuePeriodReportEntry
		MAX-ACCESS			 not-accessible
		STATUS					 current
		DESCRIPTION			 " -- "
		::=  { cellMeasure  7 }


	euePeriodReportEntry		 OBJECT-TYPE
		SYNTAX					 EuePeriodReportEntry
		MAX-ACCESS			 not-accessible
		STATUS					 current
		DESCRIPTION			 " -- "
		INDEX						{ euePeriodRptLcId,euePeriodRptCfgId }
		::=  { euePeriodReportTable  1 }


	EuePeriodReportEntry		 ::=  SEQUENCE {
		euePeriodRptLcId					Integer32,
		euePeriodRptCfgId					Integer32,
		euePeriodRptRowStatus					RowStatus,
		euePeriodRptNetworkType					INTEGER,
		euePeriodRptType					INTEGER,
		euePeriodRptMaxReportCell					Integer32,
		euePeriodRptRptQuantity					INTEGER,
		euePeriodRptRptInterval					INTEGER,
		euePeriodRptTrigQuantity					INTEGER,
		euePeriodRptRptAmount					INTEGER,
		euePeriodRptPurpose					INTEGER,
		euePeriodRptAlgoType					INTEGER
		}


	euePeriodRptLcId		 OBJECT-TYPE
		SYNTAX					 Integer32( 0 .. 23 )
		MAX-ACCESS			 not-accessible
		STATUS					 current
		DESCRIPTION			 " -- "
		::=  { euePeriodReportEntry  1 }


	euePeriodRptCfgId		 OBJECT-TYPE
		SYNTAX					 Integer32( 0 .. 15 )
		MAX-ACCESS			 not-accessible
		STATUS					 current
		DESCRIPTION			 " -- "
		::=  { euePeriodReportEntry  2 }


	euePeriodRptRowStatus		 OBJECT-TYPE
		SYNTAX					 RowStatus
		MAX-ACCESS			 read-create
		STATUS					 current
		DESCRIPTION			 " -- "
		::=  { euePeriodReportEntry  3 }


	euePeriodRptNetworkType		 OBJECT-TYPE
		SYNTAX					 INTEGER{ measNetworkEutra(0),measNetworkUtra(1),measNetworkGeran(2),measNetworkCdma2000(3)  }
		MAX-ACCESS			 read-create
		STATUS					 current
		DESCRIPTION			 " -- "
		::=  { euePeriodReportEntry  4 }


	euePeriodRptType		 OBJECT-TYPE
		SYNTAX					 INTEGER{ reportstrongestcell(0),reportCGI(1),reportstrongestcellforSon(2)  }
		MAX-ACCESS			 read-create
		STATUS					 current
		DESCRIPTION			 " -- "
		::=  { euePeriodReportEntry  5 }


	euePeriodRptMaxReportCell		 OBJECT-TYPE
		SYNTAX					 Integer32( 1 .. 8 )
		MAX-ACCESS			 read-create
		STATUS					 current
		DESCRIPTION			 " -- "
		::=  { euePeriodReportEntry  6 }


	euePeriodRptRptQuantity		 OBJECT-TYPE
		SYNTAX					 INTEGER{ trigQuant(0),both(1),invalid(65535)  }
		MAX-ACCESS			 read-create
		STATUS					 current
		DESCRIPTION			 " -- "
		::=  { euePeriodReportEntry  7 }


	euePeriodRptRptInterval		 OBJECT-TYPE
		SYNTAX					 INTEGER{ ms120(0),ms240(1),ms480(2),ms640(3),ms1024(4),ms2048(5),ms5120(6),ms10240(7),min1(8),min6(9),min12(10),min30(11),min60(12)  }
		MAX-ACCESS			 read-create
		STATUS					 current
		DESCRIPTION			 " -- "
		::=  { euePeriodReportEntry  8 }


	euePeriodRptTrigQuantity		 OBJECT-TYPE
		SYNTAX					 INTEGER{ rsrp(0),rsrq(1)  }
		MAX-ACCESS			 read-create
		STATUS					 current
		DESCRIPTION			 " -- "
		::=  { euePeriodReportEntry  9 }


	euePeriodRptRptAmount		 OBJECT-TYPE
		SYNTAX					 INTEGER{ r1(0),r2(1),r4(2),r8(3),r16(4),r32(5),r64(6),infinity(7)  }
		MAX-ACCESS			 read-create
		STATUS					 current
		DESCRIPTION			 " -- "
		::=  { euePeriodReportEntry  10 }


	euePeriodRptPurpose		 OBJECT-TYPE
		SYNTAX					 INTEGER{ strongestCell(0),ueRxTxTimeDiff(2),anr(4),anrFindAdjCell(5),invalid(8),reduceAdjCellPower(9)  }
		MAX-ACCESS			 read-create
		STATUS					 current
		DESCRIPTION			 " -- "
		::=  { euePeriodReportEntry  11 }


	euePeriodRptAlgoType		 OBJECT-TYPE
		SYNTAX					 INTEGER{ handover(0),mr(1),anr(2),mdt(3),reducePower(4),invalid(5)  }
		MAX-ACCESS			 read-create
		STATUS					 current
		DESCRIPTION			 " -- "
		::=  { euePeriodReportEntry  12 }


	measGapTable		 OBJECT-TYPE
		SYNTAX					 SEQUENCE  OF	 MeasGapEntry
		MAX-ACCESS			 not-accessible
		STATUS					 current
		DESCRIPTION			 " -- "
		::=  { cellMeasure  8 }


	measGapEntry		 OBJECT-TYPE
		SYNTAX					 MeasGapEntry
		MAX-ACCESS			 not-accessible
		STATUS					 current
		DESCRIPTION			 " -- "
		INDEX						{ measGapLcId }
		::=  { measGapTable  1 }


	MeasGapEntry		 ::=  SEQUENCE {
		measGapLcId					Integer32,
		measGapRowStatus					RowStatus,
		measGapCfgFlagForRrcConnect					INTEGER,
		measGapPattern					Integer32,
		measGapOffset					Integer32
		}


	measGapLcId		 OBJECT-TYPE
		SYNTAX					 Integer32( 0 .. 23 )
		MAX-ACCESS			 not-accessible
		STATUS					 current
		DESCRIPTION			 " -- "
		::=  { measGapEntry  1 }


	measGapRowStatus		 OBJECT-TYPE
		SYNTAX					 RowStatus
		MAX-ACCESS			 read-create
		STATUS					 current
		DESCRIPTION			 " -- "
		::=  { measGapEntry  2 }


	measGapCfgFlagForRrcConnect		 OBJECT-TYPE
		SYNTAX					 INTEGER{ measGapInfoOff(0),measGapInfoOn(1)  }
		MAX-ACCESS			 read-create
		STATUS					 current
		DESCRIPTION			 " -- "
		::=  { measGapEntry  3 }


	measGapPattern		 OBJECT-TYPE
		SYNTAX					 Integer32( 0 .. 1 )
		MAX-ACCESS			 read-create
		STATUS					 current
		DESCRIPTION			 " -- "
		::=  { measGapEntry  4 }


	measGapOffset		 OBJECT-TYPE
		SYNTAX					 Integer32( 0 .. 79 )
		MAX-ACCESS			 read-create
		STATUS					 current
		DESCRIPTION			 " -- "
		::=  { measGapEntry  5 }


	eventB1Table		 OBJECT-TYPE
		SYNTAX					 SEQUENCE  OF	 EventB1Entry
		MAX-ACCESS			 not-accessible
		STATUS					 current
		DESCRIPTION			 " -- "
		::=  { cellMeasure  12 }


	eventB1Entry		 OBJECT-TYPE
		SYNTAX					 EventB1Entry
		MAX-ACCESS			 not-accessible
		STATUS					 current
		DESCRIPTION			 " -- "
		INDEX						{ b1LcId,b1CfgId }
		::=  { eventB1Table  1 }


	EventB1Entry		 ::=  SEQUENCE {
		b1LcId					Integer32,
		b1CfgId					Integer32,
		b1RowStatus					RowStatus,
		b1NetworkType					INTEGER,
		b1MeasQuantityUtraFdd					INTEGER,
		b1MeasQuantityUtraTdd					INTEGER,
		b1MeasFilterCoeffUtra					INTEGER,
		b1MeasQuantityGeran					INTEGER,
		b1MeasFilterCoeffGeran					INTEGER,
		b1Hysteresis					INTEGER,
		b1TimetoTrig					INTEGER,
		b1MaxReportCell					Integer32,
		b1RptInterval					INTEGER,
		b1RptAmount					INTEGER,
		b1ThresholdRscpUtra					Integer32,
		b1ThresholdEcnoUtra					INTEGER,
		b1ThresholdRssiGeran					Integer32,
		b1MeasPurpose					INTEGER,
		b1MeasAlgoType					INTEGER
		}


	b1LcId		 OBJECT-TYPE
		SYNTAX					 Integer32( 0 .. 23 )
		MAX-ACCESS			 not-accessible
		STATUS					 current
		DESCRIPTION			 " -- "
		::=  { eventB1Entry  1 }


	b1CfgId		 OBJECT-TYPE
		SYNTAX					 Integer32( 0 .. 15 )
		MAX-ACCESS			 not-accessible
		STATUS					 current
		DESCRIPTION			 " -- "
		::=  { eventB1Entry  2 }


	b1RowStatus		 OBJECT-TYPE
		SYNTAX					 RowStatus
		MAX-ACCESS			 read-create
		STATUS					 current
		DESCRIPTION			 " -- "
		::=  { eventB1Entry  3 }


	b1NetworkType		 OBJECT-TYPE
		SYNTAX					 INTEGER{ utraFdd(0),utraTdd(1),geran(2)  }
		MAX-ACCESS			 read-create
		STATUS					 current
		DESCRIPTION			 " -- "
		::=  { eventB1Entry  4 }


	b1MeasQuantityUtraFdd		 OBJECT-TYPE
		SYNTAX					 INTEGER{ cpichRSCP(0),cpichEcN0(1)  }
		MAX-ACCESS			 read-create
		STATUS					 current
		DESCRIPTION			 " -- "
		::=  { eventB1Entry  5 }


	b1MeasQuantityUtraTdd		 OBJECT-TYPE
		SYNTAX					 INTEGER{ pccpchRSCP(0)  }
		MAX-ACCESS			 read-create
		STATUS					 current
		DESCRIPTION			 " -- "
		::=  { eventB1Entry  6 }


	b1MeasFilterCoeffUtra		 OBJECT-TYPE
		SYNTAX					 INTEGER{ k0(0),k1(1),k2(2),k3(3),k4(4),k5(5),k6(6),k7(7),k8(8),k9(9),k11(10),k13(11),k15(12),k17(13),k19(14)  }
		MAX-ACCESS			 read-create
		STATUS					 current
		DESCRIPTION			 " -- "
		::=  { eventB1Entry  7 }


	b1MeasQuantityGeran		 OBJECT-TYPE
		SYNTAX					 INTEGER{ rssi(0)  }
		MAX-ACCESS			 read-create
		STATUS					 current
		DESCRIPTION			 " -- "
		::=  { eventB1Entry  8 }


	b1MeasFilterCoeffGeran		 OBJECT-TYPE
		SYNTAX					 INTEGER{ k0(0),k1(1),k2(2),k3(3),k4(4),k5(5),k6(6),k7(7),k8(8),k9(9),k11(10),k13(11),k15(12),k17(13),k19(14)  }
		MAX-ACCESS			 read-create
		STATUS					 current
		DESCRIPTION			 " -- "
		::=  { eventB1Entry  9 }


	b1Hysteresis		 OBJECT-TYPE
		SYNTAX					 INTEGER{ hysteresis0(0),hysteresisPoint5(1),hysteresis1(2),hysteresis1point5(3),hysteresis2(4),hysteresis2point5(5),hysteresis3(6),hysteresis3point5(7),hysteresis4(8),hysteresis4point5(9),hysteresis5(10),hysteresis5point5(11),hysteresis6(12),hysteresis6point5(13),hysteresis7(14),hysteresis7point5(15),hysteresis8(16),hysteresis8point5(17),hysteresis9(18),hysteresis9point5(19),hysteresis10(20),hysteresis10point5(21),hysteresis11(22),hysteresis11point5(23),hysteresis12(24),hysteresis12point5(25),hysteresis13(26),hysteresis13point5(27),hysteresis14(28),hysteresis14point5(29),hysteresis15(30)  }
		MAX-ACCESS			 read-create
		STATUS					 current
		DESCRIPTION			 " -- "
		::=  { eventB1Entry  10 }


	b1TimetoTrig		 OBJECT-TYPE
		SYNTAX					 INTEGER{ ms0(0),ms40(1),ms64(2),ms80(3),ms100(4),ms128(5),ms160(6),ms256(7),ms320(8),ms480(9),ms512(10),ms640(11),ms1024(12),ms1280(13),ms2560(14),ms5120(15)  }
		MAX-ACCESS			 read-create
		STATUS					 current
		DESCRIPTION			 " -- "
		::=  { eventB1Entry  11 }


	b1MaxReportCell		 OBJECT-TYPE
		SYNTAX					 Integer32( 1 .. 8 )
		MAX-ACCESS			 read-create
		STATUS					 current
		DESCRIPTION			 " -- "
		::=  { eventB1Entry  12 }


	b1RptInterval		 OBJECT-TYPE
		SYNTAX					 INTEGER{ ms120(0),ms240(1),ms480(2),ms640(3),ms1024(4),ms2048(5),ms5120(6),ms10240(7),min1(8),min6(9),min12(10),min30(11),min60(12)  }
		MAX-ACCESS			 read-create
		STATUS					 current
		DESCRIPTION			 " -- "
		::=  { eventB1Entry  13 }


	b1RptAmount		 OBJECT-TYPE
		SYNTAX					 INTEGER{ r1(0),r2(1),r4(2),r8(3),r16(4),r32(5),r64(6),infinity(7)  }
		MAX-ACCESS			 read-create
		STATUS					 current
		DESCRIPTION			 " -- "
		::=  { eventB1Entry  14 }


	b1ThresholdRscpUtra		 OBJECT-TYPE
		SYNTAX					 Integer32( -120 .. -24 )
		MAX-ACCESS			 read-create
		STATUS					 current
		DESCRIPTION			 " -- "
		::=  { eventB1Entry  15 }


	b1ThresholdEcnoUtra		 OBJECT-TYPE
		SYNTAX					 INTEGER{ ecnoMinus24point5(0),ecnoMinus24(1),ecnoMinus23point5(2),ecnoMinus23(3),ecnoMinus22point5(4),ecnoMinus22(5),ecnoMinus21point5(6),ecnoMinus21(7),ecnoMinus20point5(8),ecnoMinus20(9),ecnoMinus19point5(10),ecnoMinus19(11),ecnoMinus18point5(12),ecnoMinus18(13),ecnoMinus17point5(14),ecnoMinus17(15),ecnoMinus16point5(16),ecnoMinus16(17),ecnoMinus15point5(18),ecnoMinus15(19),ecnoMinus14point5(20),ecnoMinus14(21),ecnoMinus13point5(22),ecnoMinus13(23),ecnoMinus12point5(24),ecnoMinus12(25),ecnoMinus11point5(26),ecnoMinus11(27),ecnoMinus10point5(28),ecnoMinus10(29),ecnoMinus9point5(30),ecnoMinus9(31),ecnoMinus8point5(32),ecnoMinus8(33),ecnoMinus7point5(34),ecnoMinus7(35),ecnoMinus6point5(36),ecnoMinus6(37),ecnoMinus5point5(38),ecnoMinus5(39),ecnoMinus4point5(40),ecnoMinus4(41),ecnoMinus3point5(42),ecnoMinus3(43),ecnoMinus2point5(44),ecnoMinus2(45),ecnoMinus1point5(46),ecnoMinus1(47),ecnoMinuspoint5(48),ecnoMinus0(49)  }
		MAX-ACCESS			 read-create
		STATUS					 current
		DESCRIPTION			 " -- "
		::=  { eventB1Entry  16 }


	b1ThresholdRssiGeran		 OBJECT-TYPE
		SYNTAX					 Integer32( -110 .. -47 )
		MAX-ACCESS			 read-create
		STATUS					 current
		DESCRIPTION			 " -- "
		::=  { eventB1Entry  17 }


	b1MeasPurpose		 OBJECT-TYPE
		SYNTAX					 INTEGER{ interRatHc(0),csfb(1),loadBlance(2),invalid(8)  }
		MAX-ACCESS			 read-create
		STATUS					 current
		DESCRIPTION			 " -- "
		::=  { eventB1Entry  18 }


	b1MeasAlgoType		 OBJECT-TYPE
		SYNTAX					 INTEGER{ handover(0),invalid(5)  }
		MAX-ACCESS			 read-create
		STATUS					 current
		DESCRIPTION			 " -- "
		::=  { eventB1Entry  19 }


	eventB2Table		 OBJECT-TYPE
		SYNTAX					 SEQUENCE  OF	 EventB2Entry
		MAX-ACCESS			 not-accessible
		STATUS					 current
		DESCRIPTION			 " -- "
		::=  { cellMeasure  13 }


	eventB2Entry		 OBJECT-TYPE
		SYNTAX					 EventB2Entry
		MAX-ACCESS			 not-accessible
		STATUS					 current
		DESCRIPTION			 " -- "
		INDEX						{ b2LcId,b2CfgId }
		::=  { eventB2Table  1 }


	EventB2Entry		 ::=  SEQUENCE {
		b2LcId					Integer32,
		b2CfgId					Integer32,
		b2RowStatus					RowStatus,
		b2NetworkType					INTEGER,
		b2MeasQuantityUtraFdd					INTEGER,
		b2MeasQuantityUtraTdd					INTEGER,
		b2MeasFilterCoeffUtra					INTEGER,
		b2MeasQuantityGeran					INTEGER,
		b2MeasFilterCoeffGeran					INTEGER,
		b2Hysteresis					INTEGER,
		b2TimetoTrig					INTEGER,
		b2MaxReportCell					Integer32,
		b2RptInterval					INTEGER,
		b2RptAmount					INTEGER,
		b2Threshold1Quantity					INTEGER,
		b2ThresholdRsrp					Integer32,
		b2ThresholdRsrq					INTEGER,
		b2Threshold2RscpUtra					Integer32,
		b2Threshold2EcnoUtra					INTEGER,
		b2Threshold2RssiGeran					Integer32,
		b2MeasPurpose					INTEGER,
		b2MeasAlgoType					INTEGER,
		b2MeasQuantityCdma2000					INTEGER,
		b2MeasFilterCoeffCdma2000					INTEGER,
		b2ThresholdpilotStrengthCdma2000					Integer32
		}


	b2LcId		 OBJECT-TYPE
		SYNTAX					 Integer32( 0 .. 23 )
		MAX-ACCESS			 not-accessible
		STATUS					 current
		DESCRIPTION			 " -- "
		::=  { eventB2Entry  1 }


	b2CfgId		 OBJECT-TYPE
		SYNTAX					 Integer32( 0 .. 15 )
		MAX-ACCESS			 not-accessible
		STATUS					 current
		DESCRIPTION			 " -- "
		::=  { eventB2Entry  2 }


	b2RowStatus		 OBJECT-TYPE
		SYNTAX					 RowStatus
		MAX-ACCESS			 read-create
		STATUS					 current
		DESCRIPTION			 " -- "
		::=  { eventB2Entry  3 }


	b2NetworkType		 OBJECT-TYPE
		SYNTAX					 INTEGER{ utraFdd(0),utraTdd(1),geran(2),cdma2000(3)  }
		MAX-ACCESS			 read-create
		STATUS					 current
		DESCRIPTION			 " -- "
		::=  { eventB2Entry  4 }


	b2MeasQuantityUtraFdd		 OBJECT-TYPE
		SYNTAX					 INTEGER{ cpichRSCP(0),cpichEcN0(1)  }
		MAX-ACCESS			 read-create
		STATUS					 current
		DESCRIPTION			 " -- "
		::=  { eventB2Entry  5 }


	b2MeasQuantityUtraTdd		 OBJECT-TYPE
		SYNTAX					 INTEGER{ pccpchRSCP(0)  }
		MAX-ACCESS			 read-create
		STATUS					 current
		DESCRIPTION			 " -- "
		::=  { eventB2Entry  6 }


	b2MeasFilterCoeffUtra		 OBJECT-TYPE
		SYNTAX					 INTEGER{ k0(0),k1(1),k2(2),k3(3),k4(4),k5(5),k6(6),k7(7),k8(8),k9(9),k11(10),k13(11),k15(12),k17(13),k19(14)  }
		MAX-ACCESS			 read-create
		STATUS					 current
		DESCRIPTION			 " -- "
		::=  { eventB2Entry  7 }


	b2MeasQuantityGeran		 OBJECT-TYPE
		SYNTAX					 INTEGER{ rssi(0)  }
		MAX-ACCESS			 read-create
		STATUS					 current
		DESCRIPTION			 " -- "
		::=  { eventB2Entry  8 }


	b2MeasFilterCoeffGeran		 OBJECT-TYPE
		SYNTAX					 INTEGER{ k0(0),k1(1),k2(2),k3(3),k4(4),k5(5),k6(6),k7(7),k8(8),k9(9),k11(10),k13(11),k15(12),k17(13),k19(14)  }
		MAX-ACCESS			 read-create
		STATUS					 current
		DESCRIPTION			 " -- "
		::=  { eventB2Entry  9 }


	b2Hysteresis		 OBJECT-TYPE
		SYNTAX					 INTEGER{ hysteresis0(0),hysteresisPoint5(1),hysteresis1(2),hysteresis1point5(3),hysteresis2(4),hysteresis2point5(5),hysteresis3(6),hysteresis3point5(7),hysteresis4(8),hysteresis4point5(9),hysteresis5(10),hysteresis5point5(11),hysteresis6(12),hysteresis6point5(13),hysteresis7(14),hysteresis7point5(15),hysteresis8(16),hysteresis8point5(17),hysteresis9(18),hysteresis9point5(19),hysteresis10(20),hysteresis10point5(21),hysteresis11(22),hysteresis11point5(23),hysteresis12(24),hysteresis12point5(25),hysteresis13(26),hysteresis13point5(27),hysteresis14(28),hysteresis14point5(29),hysteresis15(30)  }
		MAX-ACCESS			 read-create
		STATUS					 current
		DESCRIPTION			 " -- "
		::=  { eventB2Entry  10 }


	b2TimetoTrig		 OBJECT-TYPE
		SYNTAX					 INTEGER{ ms0(0),ms40(1),ms64(2),ms80(3),ms100(4),ms128(5),ms160(6),ms256(7),ms320(8),ms480(9),ms512(10),ms640(11),ms1024(12),ms1280(13),ms2560(14),ms5120(15)  }
		MAX-ACCESS			 read-create
		STATUS					 current
		DESCRIPTION			 " -- "
		::=  { eventB2Entry  11 }


	b2MaxReportCell		 OBJECT-TYPE
		SYNTAX					 Integer32( 1 .. 8 )
		MAX-ACCESS			 read-create
		STATUS					 current
		DESCRIPTION			 " -- "
		::=  { eventB2Entry  12 }


	b2RptInterval		 OBJECT-TYPE
		SYNTAX					 INTEGER{ ms120(0),ms240(1),ms480(2),ms640(3),ms1024(4),ms2048(5),ms5120(6),ms10240(7),min1(8),min6(9),min12(10),min30(11),min60(12)  }
		MAX-ACCESS			 read-create
		STATUS					 current
		DESCRIPTION			 " -- "
		::=  { eventB2Entry  13 }


	b2RptAmount		 OBJECT-TYPE
		SYNTAX					 INTEGER{ r1(0),r2(1),r4(2),r8(3),r16(4),r32(5),r64(6),infinity(7)  }
		MAX-ACCESS			 read-create
		STATUS					 current
		DESCRIPTION			 " -- "
		::=  { eventB2Entry  14 }


	b2Threshold1Quantity		 OBJECT-TYPE
		SYNTAX					 INTEGER{ rsrp(0),rsrq(1)  }
		MAX-ACCESS			 read-create
		STATUS					 current
		DESCRIPTION			 " -- "
		::=  { eventB2Entry  15 }


	b2ThresholdRsrp		 OBJECT-TYPE
		SYNTAX					 Integer32( -140 .. -44 )
		MAX-ACCESS			 read-create
		STATUS					 current
		DESCRIPTION			 " -- "
		::=  { eventB2Entry  16 }


	b2ThresholdRsrq		 OBJECT-TYPE
		SYNTAX					 INTEGER{ rsrqLessMinus19point5(0),rsrqMinus19point5(1),rsrqMinus19(2),rsrqMinus18point5(3),rsrqMinus18(4),rsrqMinus17point5(5),rsrqMinus17(6),rsrqMinus16point5(7),rsrqMinus16(8),rsrqMinus15point5(9),rsrqMinus15(10),rsrqMinus14point5(11),rsrqMinus14(12),rsrqMinus13point5(13),rsrqMinus13(14),rsrqMinus12point5(15),rsrqMinus12(16),rsrqMinus11point5(17),rsrqMinus11(18),rsrqMinus10poing5(19),rsrqMinus10(20),rsrqMinus9point5(21),rsrqMinus9(22),rsrqMinus8point5(23),rsrqMinus8(24),rsrqMinus7point5(25),rsrqMinus7(26),rsrqMinus6point5(27),rsrqMinus6(28),rsrqMinus5point5(29),rsrqMinus5(30),rsrqMinus4point5(31),rsrqMinus4(32),rsrqMinus3point5(33),rsrqMinus3(34)  }
		MAX-ACCESS			 read-create
		STATUS					 current
		DESCRIPTION			 " -- "
		::=  { eventB2Entry  17 }


	b2Threshold2RscpUtra		 OBJECT-TYPE
		SYNTAX					 Integer32( -120 .. -24 )
		MAX-ACCESS			 read-create
		STATUS					 current
		DESCRIPTION			 " -- "
		::=  { eventB2Entry  18 }


	b2Threshold2EcnoUtra		 OBJECT-TYPE
		SYNTAX					 INTEGER{ ecnoMinus24point5(0),ecnoMinus24(1),ecnoMinus23point5(2),ecnoMinus23(3),ecnoMinus22point5(4),ecnoMinus22(5),ecnoMinus21point5(6),ecnoMinus21(7),ecnoMinus20point5(8),ecnoMinus20(9),ecnoMinus19point5(10),ecnoMinus19(11),ecnoMinus18point5(12),ecnoMinus18(13),ecnoMinus17point5(14),ecnoMinus17(15),ecnoMinus16point5(16),ecnoMinus16(17),ecnoMinus15point5(18),ecnoMinus15(19),ecnoMinus14point5(20),ecnoMinus14(21),ecnoMinus13point5(22),ecnoMinus13(23),ecnoMinus12point5(24),ecnoMinus12(25),ecnoMinus11point5(26),ecnoMinus11(27),ecnoMinus10point5(28),ecnoMinus10(29),ecnoMinus9point5(30),ecnoMinus9(31),ecnoMinus8point5(32),ecnoMinus8(33),ecnoMinus7point5(34),ecnoMinus7(35),ecnoMinus6point5(36),ecnoMinus6(37),ecnoMinus5point5(38),ecnoMinus5(39),ecnoMinus4point5(40),ecnoMinus4(41),ecnoMinus3point5(42),ecnoMinus3(43),ecnoMinus2point5(44),ecnoMinus2(45),ecnoMinus1point5(46),ecnoMinus1(47),ecnoMinuspoint5(48),ecnoMinus0(49)  }
		MAX-ACCESS			 read-create
		STATUS					 current
		DESCRIPTION			 " -- "
		::=  { eventB2Entry  19 }


	b2Threshold2RssiGeran		 OBJECT-TYPE
		SYNTAX					 Integer32( -110 .. -47 )
		MAX-ACCESS			 read-create
		STATUS					 current
		DESCRIPTION			 " -- "
		::=  { eventB2Entry  20 }


	b2MeasPurpose		 OBJECT-TYPE
		SYNTAX					 INTEGER{ interRatCsHc(0),interRatPsHc(1),invalid(8)  }
		MAX-ACCESS			 read-create
		STATUS					 current
		DESCRIPTION			 " -- "
		::=  { eventB2Entry  21 }


	b2MeasAlgoType		 OBJECT-TYPE
		SYNTAX					 INTEGER{ handover(0),invalid(5)  }
		MAX-ACCESS			 read-create
		STATUS					 current
		DESCRIPTION			 " -- "
		::=  { eventB2Entry  22 }


	b2MeasQuantityCdma2000		 OBJECT-TYPE
		SYNTAX					 INTEGER{ pipilotStrength(0)  }
		MAX-ACCESS			 read-create
		STATUS					 current
		DESCRIPTION			 " -- "
		::=  { eventB2Entry  23 }


	b2MeasFilterCoeffCdma2000		 OBJECT-TYPE
		SYNTAX					 INTEGER{ k0(0),k1(1),k2(2),k3(3),k4(4),k5(5),k6(6),k7(7),k8(8),k9(9),k11(10),k13(11),k15(12),k17(13),k19(14)  }
		MAX-ACCESS			 read-create
		STATUS					 current
		DESCRIPTION			 " -- "
		::=  { eventB2Entry  24 }


	b2ThresholdpilotStrengthCdma2000		 OBJECT-TYPE
		SYNTAX					 Integer32( -110 .. -47 )
		MAX-ACCESS			 read-create
		STATUS					 current
		DESCRIPTION			 " -- "
		::=  { eventB2Entry  25 }


	eventA6Table		 OBJECT-TYPE
		SYNTAX					 SEQUENCE  OF	 EventA6Entry
		MAX-ACCESS			 not-accessible
		STATUS					 current
		DESCRIPTION			 " -- "
		::=  { cellMeasure  14 }


	eventA6Entry		 OBJECT-TYPE
		SYNTAX					 EventA6Entry
		MAX-ACCESS			 not-accessible
		STATUS					 current
		DESCRIPTION			 " -- "
		INDEX						{ a6LcId,a6CfgId }
		::=  { eventA6Table  1 }


	EventA6Entry		 ::=  SEQUENCE {
		a6LcId					Integer32,
		a6CfgId					Integer32,
		a6RowStatus					RowStatus,
		a6TrigQuantity					INTEGER,
		a6RptQuantity					INTEGER,
		a6Hysteresis					INTEGER,
		a6TimetoTrig					INTEGER,
		a6MaxReportCell					Integer32,
		a6RptInterval					INTEGER,
		a6RptAmount					INTEGER,
		a6Offset					INTEGER,
		a6MeasPurpose					INTEGER,
		a6MeasAlgoType					INTEGER
		}


	a6LcId		 OBJECT-TYPE
		SYNTAX					 Integer32( 0 .. 23 )
		MAX-ACCESS			 not-accessible
		STATUS					 current
		DESCRIPTION			 " -- "
		::=  { eventA6Entry  1 }


	a6CfgId		 OBJECT-TYPE
		SYNTAX					 Integer32( 0 .. 15 )
		MAX-ACCESS			 not-accessible
		STATUS					 current
		DESCRIPTION			 " -- "
		::=  { eventA6Entry  2 }


	a6RowStatus		 OBJECT-TYPE
		SYNTAX					 RowStatus
		MAX-ACCESS			 read-create
		STATUS					 current
		DESCRIPTION			 " -- "
		::=  { eventA6Entry  3 }


	a6TrigQuantity		 OBJECT-TYPE
		SYNTAX					 INTEGER{ rsrp(0),rsrq(1)  }
		MAX-ACCESS			 read-create
		STATUS					 current
		DESCRIPTION			 " -- "
		::=  { eventA6Entry  4 }


	a6RptQuantity		 OBJECT-TYPE
		SYNTAX					 INTEGER{ trigQuant(0),both(1)  }
		MAX-ACCESS			 read-create
		STATUS					 current
		DESCRIPTION			 " -- "
		::=  { eventA6Entry  5 }


	a6Hysteresis		 OBJECT-TYPE
		SYNTAX					 INTEGER{ hysteresis0(0),hysteresisPoint5(1),hysteresis1(2),hysteresis1point5(3),hysteresis2(4),hysteresis2point5(5),hysteresis3(6),hysteresis3point5(7),hysteresis4(8),hysteresis4point5(9),hysteresis5(10),hysteresis5point5(11),hysteresis6(12),hysteresis6point5(13),hysteresis7(14),hysteresis7point5(15),hysteresis8(16),hysteresis8point5(17),hysteresis9(18),hysteresis9point5(19),hysteresis10(20),hysteresis10point5(21),hysteresis11(22),hysteresis11point5(23),hysteresis12(24),hysteresis12point5(25),hysteresis13(26),hysteresis13point5(27),hysteresis14(28),hysteresis14point5(29),hysteresis15(30)  }
		MAX-ACCESS			 read-create
		STATUS					 current
		DESCRIPTION			 " -- "
		::=  { eventA6Entry  6 }


	a6TimetoTrig		 OBJECT-TYPE
		SYNTAX					 INTEGER{ ms0(0),ms40(1),ms64(2),ms80(3),ms100(4),ms128(5),ms160(6),ms256(7),ms320(8),ms480(9),ms512(10),ms640(11),ms1024(12),ms1280(13),ms2560(14),ms5120(15)  }
		MAX-ACCESS			 read-create
		STATUS					 current
		DESCRIPTION			 " -- "
		::=  { eventA6Entry  7 }


	a6MaxReportCell		 OBJECT-TYPE
		SYNTAX					 Integer32( 1 .. 8 )
		MAX-ACCESS			 read-create
		STATUS					 current
		DESCRIPTION			 " -- "
		::=  { eventA6Entry  8 }


	a6RptInterval		 OBJECT-TYPE
		SYNTAX					 INTEGER{ ms120(0),ms240(1),ms480(2),ms640(3),ms1024(4),ms2048(5),ms5120(6),ms10240(7),min1(8),min6(9),min12(10),min30(11),min60(12)  }
		MAX-ACCESS			 read-create
		STATUS					 current
		DESCRIPTION			 " -- "
		::=  { eventA6Entry  9 }


	a6RptAmount		 OBJECT-TYPE
		SYNTAX					 INTEGER{ r1(0),r2(1),r4(2),r8(3),r16(4),r32(5),r64(6),infinity(7)  }
		MAX-ACCESS			 read-create
		STATUS					 current
		DESCRIPTION			 " -- "
		::=  { eventA6Entry  10 }


	a6Offset		 OBJECT-TYPE
		SYNTAX					 INTEGER{ a6OffsetMinus15(0),a6OffsetMinus14Point5(1),a6OffsetMinus14(2),a6OffsetMinus13Point5(3),a6OffsetMinus13(4),a6OffsetMinus12Point5(5),a6OffsetMinus12(6),a6OffsetMinus11Point5(7),a6OffsetMinus11(8),a6OffsetMinus10Point5(9),a6OffsetMinus10(10),a6OffsetMinus9Point5(11),a6OffsetMinus9(12),a6OffsetMinus8Point5(13),a6OffsetMinus8(14),a6OffsetMinus7Point5(15),a6OffsetMinus7(16),a6OffsetMinus6Point5(17),a6OffsetMinus6(18),a6OffsetMinus5Point5(19),a6OffsetMinus5(20),a6OffsetMinus4Point5(21),a6OffsetMinus4(22),a6OffsetMinus3Point5(23),a6OffsetMinus3(24),a6OffsetMinus2Point5(25),a6OffsetMinus2(26),a6OffsetMinus1Point5(27),a6OffsetMinus1(28),a6OffsetMinusPoint5(29),a6Offset0(30),a6OffsetPoint5(31),a6Offset1(32),a6Offset1Point5(33),a6Offset2(34),a6Offset2Point5(35),a6Offset3(36),a6Offset3Point5(37),a6Offset4(38),a6Offset4Point5(39),a6Offset5(40),a6Offset5Point5(41),a6Offset6(42),a6Offset6Point5(43),a6Offset7(44),a6Offset7Point5(45),a6Offset8(46),a6Offset8Point5(47),a6Offset9(48),a6Offset9Point5(49),a6Offset10(50),a6Offset10Point5(51),a6Offset11(52),a6Offset11Point5(53),a6Offset12(54),a6Offset12Point5(55),a6Offset13(56),a6Offset13Point5(57),a6Offset14(58),a6Offset14Point5(59),a6Offset15(60)  }
		MAX-ACCESS			 read-create
		STATUS					 current
		DESCRIPTION			 " -- "
		::=  { eventA6Entry  11 }


	a6MeasPurpose		 OBJECT-TYPE
		SYNTAX					 INTEGER{ sCellSubstitution(0),invalid(8)  }
		MAX-ACCESS			 read-create
		STATUS					 current
		DESCRIPTION			 " -- "
		::=  { eventA6Entry  12 }


	a6MeasAlgoType		 OBJECT-TYPE
		SYNTAX					 INTEGER{ ca(0),invalid(5)  }
		MAX-ACCESS			 read-create
		STATUS					 current
		DESCRIPTION			 " -- "
		::=  { eventA6Entry  13 }


	ueTimerConstants		 OBJECT IDENTIFIER
		::=  { networkElementPlanCell  10 }


	eueTimerConstantsTable		 OBJECT-TYPE
		SYNTAX					 SEQUENCE  OF	 EueTimerConstantsEntry
		MAX-ACCESS			 not-accessible
		STATUS					 current
		DESCRIPTION			 " -- "
		::=  { ueTimerConstants  1 }


	eueTimerConstantsEntry		 OBJECT-TYPE
		SYNTAX					 EueTimerConstantsEntry
		MAX-ACCESS			 not-accessible
		STATUS					 current
		DESCRIPTION			 " -- "
		INDEX						{ eueTimerLcId }
		::=  { eueTimerConstantsTable  1 }


	EueTimerConstantsEntry		 ::=  SEQUENCE {
		eueTimerLcId					Integer32,
		eueTimerRowStatus					RowStatus,
		eueTimerT300					INTEGER,
		eueTimerT301					INTEGER,
		eueTimerT310					INTEGER,
		eueTimerT311					INTEGER,
		eueTimerN310					INTEGER,
		eueTimerN311					INTEGER,
		eueTimerT304					INTEGER,
		eueTimerT320					INTEGER,
		eueTimerT304ForCco					INTEGER,
		eueTimerT302					Unsigned32
		}


	eueTimerLcId		 OBJECT-TYPE
		SYNTAX					 Integer32( 0 .. 23 )
		MAX-ACCESS			 not-accessible
		STATUS					 current
		DESCRIPTION			 " -- "
		::=  { eueTimerConstantsEntry  1 }


	eueTimerRowStatus		 OBJECT-TYPE
		SYNTAX					 RowStatus
		MAX-ACCESS			 read-create
		STATUS					 current
		DESCRIPTION			 " -- "
		::=  { eueTimerConstantsEntry  2 }


	eueTimerT300		 OBJECT-TYPE
		SYNTAX					 INTEGER{ ms100(0),ms200(1),ms300(2),ms400(3),ms600(4),ms1000(5),ms1500(6),ms2000(7)  }
		MAX-ACCESS			 read-create
		STATUS					 current
		DESCRIPTION			 " -- "
		::=  { eueTimerConstantsEntry  3 }


	eueTimerT301		 OBJECT-TYPE
		SYNTAX					 INTEGER{ ms100(0),ms200(1),ms300(2),ms400(3),ms600(4),ms1000(5),ms1500(6),ms2000(7)  }
		MAX-ACCESS			 read-create
		STATUS					 current
		DESCRIPTION			 " -- "
		::=  { eueTimerConstantsEntry  4 }


	eueTimerT310		 OBJECT-TYPE
		SYNTAX					 INTEGER{ ms0(0),ms50(1),ms100(2),ms200(3),ms500(4),ms1000(5),ms2000(6)  }
		MAX-ACCESS			 read-create
		STATUS					 current
		DESCRIPTION			 " -- "
		::=  { eueTimerConstantsEntry  5 }


	eueTimerT311		 OBJECT-TYPE
		SYNTAX					 INTEGER{ ms1000(0),ms3000(1),ms5000(2),ms10000(3),ms15000(4),ms20000(5),ms30000(6)  }
		MAX-ACCESS			 read-create
		STATUS					 current
		DESCRIPTION			 " -- "
		::=  { eueTimerConstantsEntry  6 }


	eueTimerN310		 OBJECT-TYPE
		SYNTAX					 INTEGER{ n1(0),n2(1),n3(2),n4(3),n6(4),n8(5),n10(6),n20(7)  }
		MAX-ACCESS			 read-create
		STATUS					 current
		DESCRIPTION			 " -- "
		::=  { eueTimerConstantsEntry  7 }


	eueTimerN311		 OBJECT-TYPE
		SYNTAX					 INTEGER{ n1(0),n2(1),n3(2),n4(3),n5(4),n6(5),n8(6),n10(7)  }
		MAX-ACCESS			 read-create
		STATUS					 current
		DESCRIPTION			 " -- "
		::=  { eueTimerConstantsEntry  8 }


	eueTimerT304		 OBJECT-TYPE
		SYNTAX					 INTEGER{ ms50(0),ms100(1),ms150(2),ms200(3),ms500(4),ms1000(5),ms2000(6)  }
		MAX-ACCESS			 read-create
		STATUS					 current
		DESCRIPTION			 " -- "
		::=  { eueTimerConstantsEntry  9 }


	eueTimerT320		 OBJECT-TYPE
		SYNTAX					 INTEGER{ min5(0),min10(1),min20(2),min30(3),min60(4),min120(5),min180(6)  }
		MAX-ACCESS			 read-create
		STATUS					 current
		DESCRIPTION			 " -- "
		::=  { eueTimerConstantsEntry  10 }


	eueTimerT304ForCco		 OBJECT-TYPE
		SYNTAX					 INTEGER{ ms100(0),ms200(1),ms500(2),ms1000(3),ms2000(4),ms4000(5),ms8000(6)  }
		MAX-ACCESS			 read-create
		STATUS					 current
		DESCRIPTION			 " -- "
		::=  { eueTimerConstantsEntry  11 }


	eueTimerT302		 OBJECT-TYPE
		SYNTAX					 Unsigned32( 1 .. 16 )
		MAX-ACCESS			 read-create
		STATUS					 current
		DESCRIPTION			 " -- "
		::=  { eueTimerConstantsEntry  12 }


	cellRelation		 OBJECT IDENTIFIER
		::=  { networkElementPlanCell  11 }


	cellAdjRelationTable		 OBJECT-TYPE
		SYNTAX					 SEQUENCE  OF	 CellAdjRelationEntry
		MAX-ACCESS			 not-accessible
		STATUS					 current
		DESCRIPTION			 " -- "
		::=  { cellRelation  1 }


	cellAdjRelationEntry		 OBJECT-TYPE
		SYNTAX					 CellAdjRelationEntry
		MAX-ACCESS			 not-accessible
		STATUS					 current
		DESCRIPTION			 " -- "
		INDEX						{ cellAdjCellLcId,cellAdjCellIndex }
		::=  { cellAdjRelationTable  1 }


	CellAdjRelationEntry		 ::=  SEQUENCE {
		cellAdjCellLcId					Integer32,
		cellAdjCellIndex					Integer32,
		cellAdjCellRowStatus					RowStatus,
		cellAdjCellEnbGlobalId					Unsigned32,
		cellAdjCellLocalId					Integer32,
		cellAdjCellX2Flag					INTEGER,
		cellAdjCellHCFlag					INTEGER,
		cellAdjCellRemoveFlag					INTEGER,
		cellAdjCellQOffset					INTEGER,
		cellAdjCellNetworkType					INTEGER,
		cellAdjCellCdma2000Bandclass					INTEGER,
		cellAdjCellPlmnMcc					MncMccType,
		cellAdjCellPlmnMnc					MncMccType,
		cellAdjCellRncIdUtra					Integer32,
		cellAdjCellIdUtra					Unsigned32,
		cellAdjCellLac					Integer32,
		cellAdjCellIdGeran					Integer32,
		cellAdjCell40MLayeredFrameWorkCfg					INTEGER,
		cellAdjCellCdmaPhyCellId					Integer32,
		cellAdjCellCdmaFreq					Integer32,
		cellAdjCellIndividualOffset					INTEGER,
		cellAdjCellSpeedType					INTEGER
		}


	cellAdjCellLcId		 OBJECT-TYPE
		SYNTAX					 Integer32( 0 .. 23 )
		MAX-ACCESS			 not-accessible
		STATUS					 current
		DESCRIPTION			 " -- "
		::=  { cellAdjRelationEntry  1 }


	cellAdjCellIndex		 OBJECT-TYPE
		SYNTAX					 Integer32( 1 .. 256 )
		MAX-ACCESS			 not-accessible
		STATUS					 current
		DESCRIPTION			 " -- "
		::=  { cellAdjRelationEntry  2 }


	cellAdjCellRowStatus		 OBJECT-TYPE
		SYNTAX					 RowStatus
		MAX-ACCESS			 read-create
		STATUS					 current
		DESCRIPTION			 " -- "
		::=  { cellAdjRelationEntry  3 }


	cellAdjCellEnbGlobalId		 OBJECT-TYPE
		SYNTAX					 Unsigned32( 0 .. 1048575 )
		MAX-ACCESS			 read-create
		STATUS					 current
		DESCRIPTION			 " -- "
		::=  { cellAdjRelationEntry  4 }


	cellAdjCellLocalId		 OBJECT-TYPE
		SYNTAX					 Integer32( 0 .. 255 )
		MAX-ACCESS			 read-create
		STATUS					 current
		DESCRIPTION			 " -- "
		::=  { cellAdjRelationEntry  5 }


	cellAdjCellX2Flag		 OBJECT-TYPE
		SYNTAX					 INTEGER{ false(0),true(1)  }
		MAX-ACCESS			 read-create
		STATUS					 current
		DESCRIPTION			 " -- "
		::=  { cellAdjRelationEntry  6 }


	cellAdjCellHCFlag		 OBJECT-TYPE
		SYNTAX					 INTEGER{ false(0),true(1)  }
		MAX-ACCESS			 read-create
		STATUS					 current
		DESCRIPTION			 " -- "
		::=  { cellAdjRelationEntry  7 }


	cellAdjCellRemoveFlag		 OBJECT-TYPE
		SYNTAX					 INTEGER{ false(0),true(1)  }
		MAX-ACCESS			 read-create
		STATUS					 current
		DESCRIPTION			 " -- "
		::=  { cellAdjRelationEntry  8 }


	cellAdjCellQOffset		 OBJECT-TYPE
		SYNTAX					 INTEGER{ n24dB(0),n22dB(1),n20dB(2),n18dB(3),n16dB(4),n14dB(5),n12dB(6),n10dB(7),n8dB(8),n6dB(9),n5dB(10),n4dB(11),n3dB(12),n2dB(13),n1dB(14),p0dB(15),p1dB(16),p2dB(17),p3dB(18),p4dB(19),p5dB(20),p6dB(21),p8dB(22),p10dB(23),p12dB(24),p14dB(25),p16dB(26),p18dB(27),p20dB(28),p22dB(29),p24dB(30)  }
		MAX-ACCESS			 read-create
		STATUS					 current
		DESCRIPTION			 " -- "
		::=  { cellAdjRelationEntry  9 }


	cellAdjCellNetworkType		 OBJECT-TYPE
		SYNTAX					 INTEGER{ eutra(0),utraFdd(1),utraTdd(2),geran(3),cdma2000(4)  }
		MAX-ACCESS			 read-create
		STATUS					 current
		DESCRIPTION			 " -- "
		::=  { cellAdjRelationEntry  10 }


	cellAdjCellCdma2000Bandclass		 OBJECT-TYPE
		SYNTAX					 INTEGER{ bc0(0),bc1(1),bc2(2),bc3(3),bc4(4),bc5(5),bc6(6),bc7(7),bc8(8),bc9(9),bc10(10),bc11(11),bc12(12),bc13(13),bc14(14),bc15(15),bc16(16),bc17(17),invalid(-1)  }
		MAX-ACCESS			 read-create
		STATUS					 current
		DESCRIPTION			 " -- "
		::=  { cellAdjRelationEntry  17 }


	cellAdjCellPlmnMcc		 OBJECT-TYPE
		SYNTAX					 MncMccType
		MAX-ACCESS			 read-create
		STATUS					 current
		DESCRIPTION			 " -- "
		::=  { cellAdjRelationEntry  18 }


	cellAdjCellPlmnMnc		 OBJECT-TYPE
		SYNTAX					 MncMccType
		MAX-ACCESS			 read-create
		STATUS					 current
		DESCRIPTION			 " -- "
		::=  { cellAdjRelationEntry  19 }


	cellAdjCellRncIdUtra		 OBJECT-TYPE
		SYNTAX					 Integer32( 0 .. 65535 )
		MAX-ACCESS			 read-create
		STATUS					 current
		DESCRIPTION			 " -- "
		::=  { cellAdjRelationEntry  20 }


	cellAdjCellIdUtra		 OBJECT-TYPE
		SYNTAX					 Unsigned32( 0 .. 65535 )
		MAX-ACCESS			 read-create
		STATUS					 current
		DESCRIPTION			 " -- "
		::=  { cellAdjRelationEntry  21 }


	cellAdjCellLac		 OBJECT-TYPE
		SYNTAX					 Integer32( 0 .. 65535 )
		MAX-ACCESS			 read-create
		STATUS					 current
		DESCRIPTION			 " -- "
		::=  { cellAdjRelationEntry  22 }


	cellAdjCellIdGeran		 OBJECT-TYPE
		SYNTAX					 Integer32( 0 .. 65535 )
		MAX-ACCESS			 read-create
		STATUS					 current
		DESCRIPTION			 " -- "
		::=  { cellAdjRelationEntry  23 }


	cellAdjCell40MLayeredFrameWorkCfg		 OBJECT-TYPE
		SYNTAX					 INTEGER{ noLayerOver(0),wholeLayerOver(1),partLayerOver(2),invalid(-1)  }
		MAX-ACCESS			 read-create
		STATUS					 current
		DESCRIPTION			 " -- "
		::=  { cellAdjRelationEntry  26 }


	cellAdjCellCdmaPhyCellId		 OBJECT-TYPE
		SYNTAX					 Integer32( 0 .. 511 )
		MAX-ACCESS			 read-create
		STATUS					 current
		DESCRIPTION			 " -- "
		::=  { cellAdjRelationEntry  29 }


	cellAdjCellCdmaFreq		 OBJECT-TYPE
		SYNTAX					 Integer32( 0 .. 2047 )
		MAX-ACCESS			 read-create
		STATUS					 current
		DESCRIPTION			 " -- "
		::=  { cellAdjRelationEntry  30 }


	cellAdjCellIndividualOffset		 OBJECT-TYPE
		SYNTAX					 INTEGER{ n24dB(0),n22dB(1),n20dB(2),n18dB(3),n16dB(4),n14dB(5),n12dB(6),n10dB(7),n8dB(8),n6dB(9),n5dB(10),n4dB(11),n3dB(12),n2dB(13),n1dB(14),p0dB(15),p1dB(16),p2dB(17),p3dB(18),p4dB(19),p5dB(20),p6dB(21),p8dB(22),p10dB(23),p12dB(24),p14dB(25),p16dB(26),p18dB(27),p20dB(28),p22dB(29),p24dB(30)  }
		MAX-ACCESS			 read-create
		STATUS					 current
		DESCRIPTION			 " -- "
		::=  { cellAdjRelationEntry  31 }


	cellAdjCellSpeedType		 OBJECT-TYPE
		SYNTAX					 INTEGER{ highSpeedCell(0),lowSpeedCell(1)  }
		MAX-ACCESS			 read-create
		STATUS					 current
		DESCRIPTION			 " -- "
		::=  { cellAdjRelationEntry  32 }


	cellAdjRelationDelInfo		 OBJECT IDENTIFIER
		::=  { cellRelation  2 }


	cellAdjDelLcId		 OBJECT-TYPE
		SYNTAX					 Integer32( 0 .. 23 )
		MAX-ACCESS			 read-write
		STATUS					 current
		DESCRIPTION			 " -- "
		::=  { cellAdjRelationDelInfo  1 }


	cellAdjDelCellNetworkType		 OBJECT-TYPE
		SYNTAX					 INTEGER{ eutra(0),utraFdd(1),utraTdd(2),geran(3),cdma2000(4)  }
		MAX-ACCESS			 read-write
		STATUS					 current
		DESCRIPTION			 " -- "
		::=  { cellAdjRelationDelInfo  2 }


	cellAdjDelCellPlmnMcc		 OBJECT-TYPE
		SYNTAX					 MncMccType
		MAX-ACCESS			 read-write
		STATUS					 current
		DESCRIPTION			 " -- "
		::=  { cellAdjRelationDelInfo  3 }


	cellAdjDelCellPlmnMnc		 OBJECT-TYPE
		SYNTAX					 MncMccType
		MAX-ACCESS			 read-write
		STATUS					 current
		DESCRIPTION			 " -- "
		::=  { cellAdjRelationDelInfo  4 }


	cellAdjDelEnbGlobalId		 OBJECT-TYPE
		SYNTAX					 Unsigned32( 0 .. 1048575 )
		MAX-ACCESS			 read-write
		STATUS					 current
		DESCRIPTION			 " -- "
		::=  { cellAdjRelationDelInfo  5 }


	cellAdjDelAdjCellLocalId		 OBJECT-TYPE
		SYNTAX					 Integer32( 0 .. 255 )
		MAX-ACCESS			 read-write
		STATUS					 current
		DESCRIPTION			 " -- "
		::=  { cellAdjRelationDelInfo  6 }


	cellAdjDelCellRncIdUtra		 OBJECT-TYPE
		SYNTAX					 Integer32( 0 .. 65535 )
		MAX-ACCESS			 read-write
		STATUS					 current
		DESCRIPTION			 " -- "
		::=  { cellAdjRelationDelInfo  7 }


	cellAdjDelCellIdUtra		 OBJECT-TYPE
		SYNTAX					 Unsigned32( 0 .. 65535 )
		MAX-ACCESS			 read-write
		STATUS					 current
		DESCRIPTION			 " -- "
		::=  { cellAdjRelationDelInfo  8 }


	cellAdjDelCellLac		 OBJECT-TYPE
		SYNTAX					 Integer32( 0 .. 65535 )
		MAX-ACCESS			 read-write
		STATUS					 current
		DESCRIPTION			 " -- "
		::=  { cellAdjRelationDelInfo  9 }


	cellAdjDelCellIdGeran		 OBJECT-TYPE
		SYNTAX					 Integer32( 0 .. 65535 )
		MAX-ACCESS			 read-write
		STATUS					 current
		DESCRIPTION			 " -- "
		::=  { cellAdjRelationDelInfo  10 }


	cellAdjDelCellCdma2000Bandclass		 OBJECT-TYPE
		SYNTAX					 INTEGER{ bc0(0),bc1(1),bc2(2),bc3(3),bc4(4),bc5(5),bc6(6),bc7(7),bc8(8),bc9(9),bc10(10),bc11(11),bc12(12),bc13(13),bc14(14),bc15(15),bc16(16),bc17(17),invalid(-1)  }
		MAX-ACCESS			 read-write
		STATUS					 current
		DESCRIPTION			 " -- "
		::=  { cellAdjRelationDelInfo  11 }


	cellAdjDelCellCdmaPhyCellId		 OBJECT-TYPE
		SYNTAX					 Integer32( 0 .. 511 )
		MAX-ACCESS			 read-write
		STATUS					 current
		DESCRIPTION			 " -- "
		::=  { cellAdjRelationDelInfo  12 }


	cellAdjDelCellCdmaFreq		 OBJECT-TYPE
		SYNTAX					 Integer32( 0 .. 2047 )
		MAX-ACCESS			 read-write
		STATUS					 current
		DESCRIPTION			 " -- "
		::=  { cellAdjRelationDelInfo  13 }


	pl		 OBJECT IDENTIFIER
		::=  { networkElementPlanCell  12 }


	sdCfgTable		 OBJECT-TYPE
		SYNTAX					 SEQUENCE  OF	 SdCfgEntry
		MAX-ACCESS			 not-accessible
		STATUS					 current
		DESCRIPTION			 " -- "
		::=  { pl  1 }


	sdCfgEntry		 OBJECT-TYPE
		SYNTAX					 SdCfgEntry
		MAX-ACCESS			 not-accessible
		STATUS					 current
		DESCRIPTION			 " -- "
		INDEX						{ sdCfgLcId }
		::=  { sdCfgTable  1 }


	SdCfgEntry		 ::=  SEQUENCE {
		sdCfgLcId					Integer32,
		sdCfgRowStatus					RowStatus,
		sdCfgThresholdDetection					Integer32,
		sdCfgThresholdCollision					Integer32
		}


	sdCfgLcId		 OBJECT-TYPE
		SYNTAX					 Integer32( 0 .. 23 )
		MAX-ACCESS			 not-accessible
		STATUS					 current
		DESCRIPTION			 " -- "
		::=  { sdCfgEntry  1 }


	sdCfgRowStatus		 OBJECT-TYPE
		SYNTAX					 RowStatus
		MAX-ACCESS			 read-create
		STATUS					 current
		DESCRIPTION			 " -- "
		::=  { sdCfgEntry  2 }


	sdCfgThresholdDetection		 OBJECT-TYPE
		SYNTAX					 Integer32( 0 .. 32767 )
		MAX-ACCESS			 read-create
		STATUS					 current
		DESCRIPTION			 " -- "
		::=  { sdCfgEntry  3 }


	sdCfgThresholdCollision		 OBJECT-TYPE
		SYNTAX					 Integer32( 0 .. 65535 )
		MAX-ACCESS			 read-create
		STATUS					 current
		DESCRIPTION			 " -- "
		::=  { sdCfgEntry  4 }


	phyCfgTable		 OBJECT-TYPE
		SYNTAX					 SEQUENCE  OF	 PhyCfgEntry
		MAX-ACCESS			 not-accessible
		STATUS					 current
		DESCRIPTION			 " -- "
		::=  { pl  2 }


	phyCfgEntry		 OBJECT-TYPE
		SYNTAX					 PhyCfgEntry
		MAX-ACCESS			 not-accessible
		STATUS					 current
		DESCRIPTION			 " -- "
		INDEX						{ phyCfgLcId }
		::=  { phyCfgTable  1 }


	PhyCfgEntry		 ::=  SEQUENCE {
		phyCfgLcId					Integer32,
		phyCfgRowStatus					RowStatus,
		phyCfgBFGranuleSinglePort					Integer32,
		phyCfgBFGranuleDoublePort					Integer32,
		phyCfgTimeValidThreshold					Integer32,
		phyCfgFreqValidThreshold					Integer32,
		phyCfgIterStopThreshold					Integer32,
		phyCfgIterMaxNum					Integer32,
		phyCfgRxxFactor					Integer32,
		phyCfgSRSSamplePerPrb					Integer32,
		phyCfgWBFCalFlag					INTEGER,
		phyCfgAoaWeightFactor					Integer32,
		phyCfgBFInterleaveFlag					INTEGER,
		phyCfgBFOnSwitch					INTEGER,
		phyCfgPVSPeriod					INTEGER,
		phyCfgBFScramPeriod					INTEGER,
		phyCfgBFAngleNum					Integer32,
		phyCfgScramUePower					Integer32,
		phyCfgIrcSwitch					INTEGER,
		phyCfgMultiBeamFlag					INTEGER,
		phyCfgIrcAdaptiveThreshold					Integer32,
		phyCfgMmseSwitch					INTEGER,
		phyCfgSrsCqiMeasType					INTEGER,
		phyCfgPuschAckActiveSwitch					INTEGER,
		phyCfgRxChanDelayCfg					Integer32,
		phyCfgIotScSmartAlarmThresholdL					Integer32,
		phyCfgIotScSmartAlarmThresholdH					Integer32,
		phyCfgIotScSmartAlarmPRBnumR					Integer32,
		phyCfgIotScNotSmartAlarmThresholdL					Integer32,
		phyCfgIotScNotSmartAlarmThresholdH					Integer32,
		phyCfgIotScNotSmartAlarmPRBnumR					Integer32,
		phyCfgDlTestMode					Integer32,
		phyCfgDlTestOfdm					Integer32,
		phyCfgDlTestAmp1					Integer32,
		phyCfgDlTestAmp2					Integer32,
		phyCfgDlTestAmp3					Integer32,
		phyCfgContinIotMeasPeriod					Integer32,
		phyCfgContinIotMeasTimes					Integer32,
		phyCfgContinIotManualMeasSubfnTrigger					INTEGER,
		phyCfgContinIotAlarmRelateSwitch					INTEGER,
		phyCfgIotRalativeHighAlarmThreshold					Integer32,
		phyCfgIotRelativeHighAlarmPRBnumR					Integer32,
		phyCfgIotChanAlarmRate					Integer32,
		phyCfgIotChanNormalRate					Integer32,
		phyCfgTm9BfType					INTEGER,
		phyCfgIotSmartAlarmPartLowRate					Integer32,
		phyCfgIotSmartAlarmPartHighRate					Integer32,
		phyCfgIotNotSmartAlarmPartLowRate					Integer32,
		phyCfgIotNotSmartAlarmPartHighRate					Integer32,
		phyCfgRipPMReportDelta					Integer32,
		phyCfgUlIterSwitch					INTEGER,
		phyCfgUlIterNum					Integer32,
		phyCfgCrsStepupSwitch					INTEGER,
		phyCfgCrsStepupPeriod					Integer32,
		phyCfgPucchSrStubSwitch					INTEGER,
		phyCfgPucchSrStubPeriod					Integer32,
		phyCfgPucchFilterFactor					Integer32,
		phyCfgUncertainCQISwitch					INTEGER,
		phyCfgUncertainCQIUeIndex					Integer32,
		phyCfgSpeedDetectSwitch					INTEGER,
		phyCfgSpeedDetectShortT					INTEGER,
		phyCfgSpeedDetectP					INTEGER,
		phyCfgSpeedDetectLowThreshold					Integer32,
		phyCfgSpeedDetectHighThreshold					Integer32,
		phyCfgSpeedDetectLowTimes					Integer32,
		phyCfgSpeedDetectHighTimes					Integer32,
		phyCfgHighSpeedFreqShiftThr					Integer32,
		phyCfgHighSpeedDlModifyFreqShiftPeriod					Integer32,
		phyCfgPucchDataSrStubSwitch					INTEGER,
		phyCfgPucchDataSrStubPeriod					Integer32,
		phyCfgPucchNormalCpFmt1ActiveThred1Ant					Integer32,
		phyCfgPucchNormalCpFmt1ActiveThred2Ant					Integer32,
		phyCfgPucchNormalCpFmt1ActiveThred3Ant					Integer32,
		phyCfgPucchNormalCpFmt1ActiveThred4Ant					Integer32,
		phyCfgPucchNormalCpFmt1ActiveThred5Ant					Integer32,
		phyCfgPucchNormalCpFmt1ActiveThred6Ant					Integer32,
		phyCfgPucchNormalCpFmt1ActiveThred7Ant					Integer32,
		phyCfgPucchNormalCpFmt1ActiveThred8Ant					Integer32,
		phyCfgPucchExTendCpFmt1ActiveThred1Ant					Integer32,
		phyCfgPucchExTendCpFmt1ActiveThred2Ant					Integer32,
		phyCfgPucchExTendCpFmt1ActiveThred3Ant					Integer32,
		phyCfgPucchExTendCpFmt1ActiveThred4Ant					Integer32,
		phyCfgPucchExTendCpFmt1ActiveThred5Ant					Integer32,
		phyCfgPucchExTendCpFmt1ActiveThred6Ant					Integer32,
		phyCfgPucchExTendCpFmt1ActiveThred7Ant					Integer32,
		phyCfgPucchExTendCpFmt1ActiveThred8Ant					Integer32,
		phyCfgPucchSrAckCollideSelectFlag					INTEGER,
		phyCfgPucchSrThrePara					Integer32,
		phyCfgPucchAckThrePara					Integer32,
		phyCfgPucchSingleAntAlgorithmFlag					INTEGER,
		phyCfgPucchNormalCpFmt1ActiveThredSingleAnt					Integer32,
		phyCfgRipPMReportDeltaSSF					Integer32,
		phyCfgPlTestPara					Unsigned32,
		phyCfgPucchVolteSrStubPeriod					Integer32,
		phyCfgRipPMReportDeltaSwitch					INTEGER,
		phyCfgCrsStepupStep					Integer32,
		phyCfgCrsStepdownStep					Integer32,
		phyCfgSrsUePowerCqiThre					Integer32,
		phyCfgSrsUePowerBfThre					Integer32,
		phyCfgSrsUePowerTaThre					Integer32,
		phyCfgSrsUePowerAnteSelectThre					Integer32,
		phyCfgSrsSnrCqiThre					Integer32,
		phyCfgSrsSnrBfThre					Integer32,
		phyCfgSrsSnrTaThre					Integer32,
		phyCfgSrsSnrAnteSelectThre					Integer32,
		phyPuschPowerControlSnrThre					Integer32,
		phyCfgRipIotShifter					Integer32
		}


	phyCfgLcId		 OBJECT-TYPE
		SYNTAX					 Integer32( 0 .. 23 )
		MAX-ACCESS			 not-accessible
		STATUS					 current
		DESCRIPTION			 " -- "
		::=  { phyCfgEntry  1 }


	phyCfgRowStatus		 OBJECT-TYPE
		SYNTAX					 RowStatus
		MAX-ACCESS			 read-create
		STATUS					 current
		DESCRIPTION			 " -- "
		::=  { phyCfgEntry  2 }


	phyCfgBFGranuleSinglePort		 OBJECT-TYPE
		SYNTAX					 Integer32( 1 .. 100 )
		MAX-ACCESS			 read-create
		STATUS					 current
		DESCRIPTION			 " -- "
		::=  { phyCfgEntry  3 }


	phyCfgBFGranuleDoublePort		 OBJECT-TYPE
		SYNTAX					 Integer32( 1 .. 100 )
		MAX-ACCESS			 read-create
		STATUS					 current
		DESCRIPTION			 " -- "
		::=  { phyCfgEntry  4 }


	phyCfgTimeValidThreshold		 OBJECT-TYPE
		SYNTAX					 Integer32( 1 .. 32 )
		MAX-ACCESS			 read-create
		STATUS					 current
		DESCRIPTION			 " -- "
		::=  { phyCfgEntry  5 }


	phyCfgFreqValidThreshold		 OBJECT-TYPE
		SYNTAX					 Integer32( 1 .. 100 )
		MAX-ACCESS			 read-create
		STATUS					 current
		DESCRIPTION			 " -- "
		::=  { phyCfgEntry  6 }


	phyCfgIterStopThreshold		 OBJECT-TYPE
		SYNTAX					 Integer32( 0 .. 65535 )
		MAX-ACCESS			 read-create
		STATUS					 current
		DESCRIPTION			 " -- "
		::=  { phyCfgEntry  7 }


	phyCfgIterMaxNum		 OBJECT-TYPE
		SYNTAX					 Integer32( 1 .. 64 )
		MAX-ACCESS			 read-create
		STATUS					 current
		DESCRIPTION			 " -- "
		::=  { phyCfgEntry  8 }


	phyCfgRxxFactor		 OBJECT-TYPE
		SYNTAX					 Integer32( 0 .. 255 )
		MAX-ACCESS			 read-create
		STATUS					 current
		DESCRIPTION			 " -- "
		::=  { phyCfgEntry  9 }


	phyCfgSRSSamplePerPrb		 OBJECT-TYPE
		SYNTAX					 Integer32( 32 .. 192 )
		MAX-ACCESS			 read-create
		STATUS					 current
		DESCRIPTION			 " -- "
		::=  { phyCfgEntry  10 }


	phyCfgWBFCalFlag		 OBJECT-TYPE
		SYNTAX					 INTEGER{ noBandWeight(0),gobAlg(1),ebbAlg(2),autoSelecAlg(3)  }
		MAX-ACCESS			 read-create
		STATUS					 current
		DESCRIPTION			 " -- "
		::=  { phyCfgEntry  11 }


	phyCfgAoaWeightFactor		 OBJECT-TYPE
		SYNTAX					 Integer32( 0 .. 255 )
		MAX-ACCESS			 read-create
		STATUS					 current
		DESCRIPTION			 " -- "
		::=  { phyCfgEntry  12 }


	phyCfgBFInterleaveFlag		 OBJECT-TYPE
		SYNTAX					 INTEGER{ off(0),on(1)  }
		MAX-ACCESS			 read-create
		STATUS					 current
		DESCRIPTION			 " -- "
		::=  { phyCfgEntry  13 }


	phyCfgBFOnSwitch		 OBJECT-TYPE
		SYNTAX					 INTEGER{ off(0),on(1)  }
		MAX-ACCESS			 read-create
		STATUS					 current
		DESCRIPTION			 " -- "
		::=  { phyCfgEntry  14 }


	phyCfgPVSPeriod		 OBJECT-TYPE
		SYNTAX					 INTEGER{ val2(2),val4(4),val6(6),val8(8)  }
		MAX-ACCESS			 read-create
		STATUS					 current
		DESCRIPTION			 " -- "
		::=  { phyCfgEntry  15 }


	phyCfgBFScramPeriod		 OBJECT-TYPE
		SYNTAX					 INTEGER{ val1(1),val2(2),val3(3)  }
		MAX-ACCESS			 read-create
		STATUS					 current
		DESCRIPTION			 " -- "
		::=  { phyCfgEntry  16 }


	phyCfgBFAngleNum		 OBJECT-TYPE
		SYNTAX					 Integer32( 1 .. 7 )
		MAX-ACCESS			 read-create
		STATUS					 current
		DESCRIPTION			 " -- "
		::=  { phyCfgEntry  17 }


	phyCfgScramUePower		 OBJECT-TYPE
		SYNTAX					 Integer32( -6 .. 6 )
		MAX-ACCESS			 read-create
		STATUS					 current
		DESCRIPTION			 " -- "
		::=  { phyCfgEntry  18 }


	phyCfgIrcSwitch		 OBJECT-TYPE
		SYNTAX					 INTEGER{ mrc(0),irc(1),autoSele(2),enhancedIRC(3),enhancedAutoSele(4)  }
		MAX-ACCESS			 read-create
		STATUS					 current
		DESCRIPTION			 " -- "
		::=  { phyCfgEntry  19 }


	phyCfgMultiBeamFlag		 OBJECT-TYPE
		SYNTAX					 INTEGER{ singleBeam(0),sultiBeam(1)  }
		MAX-ACCESS			 read-create
		STATUS					 current
		DESCRIPTION			 " -- "
		::=  { phyCfgEntry  21 }


	phyCfgIrcAdaptiveThreshold		 OBJECT-TYPE
		SYNTAX					 Integer32( 8192 .. 40960 )
		MAX-ACCESS			 read-create
		STATUS					 current
		DESCRIPTION			 " -- "
		::=  { phyCfgEntry  22 }


	phyCfgMmseSwitch		 OBJECT-TYPE
		SYNTAX					 INTEGER{ zf(0),mmse(1),zfAndMmse(2)  }
		MAX-ACCESS			 read-create
		STATUS					 current
		DESCRIPTION			 " -- "
		::=  { phyCfgEntry  23 }


	phyCfgSrsCqiMeasType		 OBJECT-TYPE
		SYNTAX					 INTEGER{ nofreqSel(0),ulfreqSel(1),dlfreqSel(2)  }
		MAX-ACCESS			 read-create
		STATUS					 current
		DESCRIPTION			 " -- "
		::=  { phyCfgEntry  24 }


	phyCfgPuschAckActiveSwitch		 OBJECT-TYPE
		SYNTAX					 INTEGER{ off(0),on(1)  }
		MAX-ACCESS			 read-create
		STATUS					 current
		DESCRIPTION			 " -- "
		::=  { phyCfgEntry  25 }


	phyCfgRxChanDelayCfg		 OBJECT-TYPE
		SYNTAX					 Integer32( -160 .. 160 )
		MAX-ACCESS			 read-create
		STATUS					 current
		DESCRIPTION			 " -- "
		::=  { phyCfgEntry  26 }


	phyCfgIotScSmartAlarmThresholdL		 OBJECT-TYPE
		SYNTAX					 Integer32( -16 .. 77 )
		MAX-ACCESS			 read-create
		STATUS					 current
		DESCRIPTION			 " -- "
		::=  { phyCfgEntry  27 }


	phyCfgIotScSmartAlarmThresholdH		 OBJECT-TYPE
		SYNTAX					 Integer32( -16 .. 77 )
		MAX-ACCESS			 read-create
		STATUS					 current
		DESCRIPTION			 " -- "
		::=  { phyCfgEntry  28 }


	phyCfgIotScSmartAlarmPRBnumR		 OBJECT-TYPE
		SYNTAX					 Integer32( 1 .. 100 )
		MAX-ACCESS			 read-create
		STATUS					 current
		DESCRIPTION			 " -- "
		::=  { phyCfgEntry  29 }


	phyCfgIotScNotSmartAlarmThresholdL		 OBJECT-TYPE
		SYNTAX					 Integer32( -16 .. 77 )
		MAX-ACCESS			 read-create
		STATUS					 current
		DESCRIPTION			 " -- "
		::=  { phyCfgEntry  30 }


	phyCfgIotScNotSmartAlarmThresholdH		 OBJECT-TYPE
		SYNTAX					 Integer32( -16 .. 77 )
		MAX-ACCESS			 read-create
		STATUS					 current
		DESCRIPTION			 " -- "
		::=  { phyCfgEntry  31 }


	phyCfgIotScNotSmartAlarmPRBnumR		 OBJECT-TYPE
		SYNTAX					 Integer32( 1 .. 100 )
		MAX-ACCESS			 read-create
		STATUS					 current
		DESCRIPTION			 " -- "
		::=  { phyCfgEntry  32 }


	phyCfgDlTestMode		 OBJECT-TYPE
		SYNTAX					 Integer32( 0 .. 255 )
		MAX-ACCESS			 read-create
		STATUS					 current
		DESCRIPTION			 " -- "
		::=  { phyCfgEntry  33 }


	phyCfgDlTestOfdm		 OBJECT-TYPE
		SYNTAX					 Integer32( 0 .. 127 )
		MAX-ACCESS			 read-create
		STATUS					 current
		DESCRIPTION			 " -- "
		::=  { phyCfgEntry  34 }


	phyCfgDlTestAmp1		 OBJECT-TYPE
		SYNTAX					 Integer32( 0 .. 32768 )
		MAX-ACCESS			 read-create
		STATUS					 current
		DESCRIPTION			 " -- "
		::=  { phyCfgEntry  35 }


	phyCfgDlTestAmp2		 OBJECT-TYPE
		SYNTAX					 Integer32( 0 .. 32768 )
		MAX-ACCESS			 read-create
		STATUS					 current
		DESCRIPTION			 " -- "
		::=  { phyCfgEntry  36 }


	phyCfgDlTestAmp3		 OBJECT-TYPE
		SYNTAX					 Integer32( 0 .. 32768 )
		MAX-ACCESS			 read-create
		STATUS					 current
		DESCRIPTION			 " -- "
		::=  { phyCfgEntry  37 }


	phyCfgContinIotMeasPeriod		 OBJECT-TYPE
		SYNTAX					 Integer32( 1 .. 3600 )
		MAX-ACCESS			 read-create
		STATUS					 current
		DESCRIPTION			 " -- "
		::=  { phyCfgEntry  38 }


	phyCfgContinIotMeasTimes		 OBJECT-TYPE
		SYNTAX					 Integer32( 300 .. 3000 )
		MAX-ACCESS			 read-create
		STATUS					 current
		DESCRIPTION			 " -- "
		::=  { phyCfgEntry  39 }


	phyCfgContinIotManualMeasSubfnTrigger		 OBJECT-TYPE
		SYNTAX					 INTEGER{ off(0),on(1)  }
		MAX-ACCESS			 read-create
		STATUS					 current
		DESCRIPTION			 " -- "
		::=  { phyCfgEntry  40 }


	phyCfgContinIotAlarmRelateSwitch		 OBJECT-TYPE
		SYNTAX					 INTEGER{ off(0),on(1)  }
		MAX-ACCESS			 read-create
		STATUS					 current
		DESCRIPTION			 " -- "
		::=  { phyCfgEntry  41 }


	phyCfgIotRalativeHighAlarmThreshold		 OBJECT-TYPE
		SYNTAX					 Integer32( 0 .. 47 )
		MAX-ACCESS			 read-create
		STATUS					 current
		DESCRIPTION			 " -- "
		::=  { phyCfgEntry  42 }


	phyCfgIotRelativeHighAlarmPRBnumR		 OBJECT-TYPE
		SYNTAX					 Integer32( 1 .. 100 )
		MAX-ACCESS			 read-create
		STATUS					 current
		DESCRIPTION			 " -- "
		::=  { phyCfgEntry  43 }


	phyCfgIotChanAlarmRate		 OBJECT-TYPE
		SYNTAX					 Integer32( 1 .. 100 )
		MAX-ACCESS			 read-create
		STATUS					 current
		DESCRIPTION			 " -- "
		::=  { phyCfgEntry  44 }


	phyCfgIotChanNormalRate		 OBJECT-TYPE
		SYNTAX					 Integer32( 1 .. 100 )
		MAX-ACCESS			 read-create
		STATUS					 current
		DESCRIPTION			 " -- "
		::=  { phyCfgEntry  45 }


	phyCfgTm9BfType		 OBJECT-TYPE
		SYNTAX					 INTEGER{ pm(0),bf(1),pmAndBf(2)  }
		MAX-ACCESS			 read-create
		STATUS					 current
		DESCRIPTION			 " -- "
		::=  { phyCfgEntry  46 }


	phyCfgIotSmartAlarmPartLowRate		 OBJECT-TYPE
		SYNTAX					 Integer32( 0 .. 100 )
		MAX-ACCESS			 read-create
		STATUS					 current
		DESCRIPTION			 " -- "
		::=  { phyCfgEntry  47 }


	phyCfgIotSmartAlarmPartHighRate		 OBJECT-TYPE
		SYNTAX					 Integer32( 0 .. 100 )
		MAX-ACCESS			 read-create
		STATUS					 current
		DESCRIPTION			 " -- "
		::=  { phyCfgEntry  48 }


	phyCfgIotNotSmartAlarmPartLowRate		 OBJECT-TYPE
		SYNTAX					 Integer32( 0 .. 100 )
		MAX-ACCESS			 read-create
		STATUS					 current
		DESCRIPTION			 " -- "
		::=  { phyCfgEntry  49 }


	phyCfgIotNotSmartAlarmPartHighRate		 OBJECT-TYPE
		SYNTAX					 Integer32( 0 .. 100 )
		MAX-ACCESS			 read-create
		STATUS					 current
		DESCRIPTION			 " -- "
		::=  { phyCfgEntry  50 }


	phyCfgRipPMReportDelta		 OBJECT-TYPE
		SYNTAX					 Integer32( -20 .. 20 )
		MAX-ACCESS			 read-create
		STATUS					 current
		DESCRIPTION			 " -- "
		::=  { phyCfgEntry  51 }


	phyCfgUlIterSwitch		 OBJECT-TYPE
		SYNTAX					 INTEGER{ off(0),on(1)  }
		MAX-ACCESS			 read-create
		STATUS					 current
		DESCRIPTION			 " -- "
		::=  { phyCfgEntry  52 }


	phyCfgUlIterNum		 OBJECT-TYPE
		SYNTAX					 Integer32( 1 .. 16 )
		MAX-ACCESS			 read-create
		STATUS					 current
		DESCRIPTION			 " -- "
		::=  { phyCfgEntry  53 }


	phyCfgCrsStepupSwitch		 OBJECT-TYPE
		SYNTAX					 INTEGER{ off(0),on(1)  }
		MAX-ACCESS			 read-create
		STATUS					 current
		DESCRIPTION			 " -- "
		::=  { phyCfgEntry  54 }


	phyCfgCrsStepupPeriod		 OBJECT-TYPE
		SYNTAX					 Integer32( 1 .. 60 )
		MAX-ACCESS			 read-create
		STATUS					 current
		DESCRIPTION			 " -- "
		::=  { phyCfgEntry  55 }


	phyCfgPucchSrStubSwitch		 OBJECT-TYPE
		SYNTAX					 INTEGER{ off(0),on(1)  }
		MAX-ACCESS			 read-create
		STATUS					 current
		DESCRIPTION			 " -- "
		::=  { phyCfgEntry  56 }


	phyCfgPucchSrStubPeriod		 OBJECT-TYPE
		SYNTAX					 Integer32( 1 .. 60 )
		MAX-ACCESS			 read-create
		STATUS					 current
		DESCRIPTION			 " -- "
		::=  { phyCfgEntry  57 }


	phyCfgPucchFilterFactor		 OBJECT-TYPE
		SYNTAX					 Integer32( 1 .. 15 )
		MAX-ACCESS			 read-create
		STATUS					 current
		DESCRIPTION			 " -- "
		::=  { phyCfgEntry  58 }


	phyCfgUncertainCQISwitch		 OBJECT-TYPE
		SYNTAX					 INTEGER{ off(0),on(1)  }
		MAX-ACCESS			 read-create
		STATUS					 current
		DESCRIPTION			 " -- "
		::=  { phyCfgEntry  59 }


	phyCfgUncertainCQIUeIndex		 OBJECT-TYPE
		SYNTAX					 Integer32( 0 .. 1249|65535 )
		MAX-ACCESS			 read-create
		STATUS					 current
		DESCRIPTION			 " -- "
		::=  { phyCfgEntry  60 }


	phyCfgSpeedDetectSwitch		 OBJECT-TYPE
		SYNTAX					 INTEGER{ off(0),on(1)  }
		MAX-ACCESS			 read-create
		STATUS					 current
		DESCRIPTION			 " -- "
		::=  { phyCfgEntry  61 }


	phyCfgSpeedDetectShortT		 OBJECT-TYPE
		SYNTAX					 INTEGER{ time500(4),time600(5),time700(6),time800(7),time900(9),time1000(10),time2000(11),time3000(12),time4000(13),time5000(14),time6000(15)  }
		MAX-ACCESS			 read-create
		STATUS					 current
		DESCRIPTION			 " -- "
		::=  { phyCfgEntry  62 }


	phyCfgSpeedDetectP		 OBJECT-TYPE
		SYNTAX					 INTEGER{ p1(0),p2(1),p3(2),p4(3),p5(4),p6(5),p7(6),p8(7),p9(8),p10(9),p11(10),p12(11),p13(12),p14(13),p15(14),p16(15)  }
		MAX-ACCESS			 read-create
		STATUS					 current
		DESCRIPTION			 " -- "
		::=  { phyCfgEntry  63 }


	phyCfgSpeedDetectLowThreshold		 OBJECT-TYPE
		SYNTAX					 Integer32( 0 .. 500 )
		MAX-ACCESS			 read-create
		STATUS					 current
		DESCRIPTION			 " -- "
		::=  { phyCfgEntry  64 }


	phyCfgSpeedDetectHighThreshold		 OBJECT-TYPE
		SYNTAX					 Integer32( 0 .. 500 )
		MAX-ACCESS			 read-create
		STATUS					 current
		DESCRIPTION			 " -- "
		::=  { phyCfgEntry  65 }


	phyCfgSpeedDetectLowTimes		 OBJECT-TYPE
		SYNTAX					 Integer32( 1 .. 128 )
		MAX-ACCESS			 read-create
		STATUS					 current
		DESCRIPTION			 " -- "
		::=  { phyCfgEntry  66 }


	phyCfgSpeedDetectHighTimes		 OBJECT-TYPE
		SYNTAX					 Integer32( 1 .. 128 )
		MAX-ACCESS			 read-create
		STATUS					 current
		DESCRIPTION			 " -- "
		::=  { phyCfgEntry  67 }


	phyCfgHighSpeedFreqShiftThr		 OBJECT-TYPE
		SYNTAX					 Integer32( 1 .. 1000 )
		MAX-ACCESS			 read-create
		STATUS					 current
		DESCRIPTION			 " -- "
		::=  { phyCfgEntry  68 }


	phyCfgHighSpeedDlModifyFreqShiftPeriod		 OBJECT-TYPE
		SYNTAX					 Integer32( 1 .. 1000 )
		MAX-ACCESS			 read-create
		STATUS					 current
		DESCRIPTION			 " -- "
		::=  { phyCfgEntry  69 }


	phyCfgPucchDataSrStubSwitch		 OBJECT-TYPE
		SYNTAX					 INTEGER{ off(0),on(1)  }
		MAX-ACCESS			 read-create
		STATUS					 current
		DESCRIPTION			 " -- "
		::=  { phyCfgEntry  70 }


	phyCfgPucchDataSrStubPeriod		 OBJECT-TYPE
		SYNTAX					 Integer32( 1 .. 60 )
		MAX-ACCESS			 read-create
		STATUS					 current
		DESCRIPTION			 " -- "
		::=  { phyCfgEntry  71 }


	phyCfgPucchNormalCpFmt1ActiveThred1Ant		 OBJECT-TYPE
		SYNTAX					 Integer32( 0 .. 65535 )
		MAX-ACCESS			 read-create
		STATUS					 current
		DESCRIPTION			 " -- "
		::=  { phyCfgEntry  72 }


	phyCfgPucchNormalCpFmt1ActiveThred2Ant		 OBJECT-TYPE
		SYNTAX					 Integer32( 0 .. 65535 )
		MAX-ACCESS			 read-create
		STATUS					 current
		DESCRIPTION			 " -- "
		::=  { phyCfgEntry  73 }


	phyCfgPucchNormalCpFmt1ActiveThred3Ant		 OBJECT-TYPE
		SYNTAX					 Integer32( 0 .. 65535 )
		MAX-ACCESS			 read-create
		STATUS					 current
		DESCRIPTION			 " -- "
		::=  { phyCfgEntry  74 }


	phyCfgPucchNormalCpFmt1ActiveThred4Ant		 OBJECT-TYPE
		SYNTAX					 Integer32( 0 .. 65535 )
		MAX-ACCESS			 read-create
		STATUS					 current
		DESCRIPTION			 " -- "
		::=  { phyCfgEntry  75 }


	phyCfgPucchNormalCpFmt1ActiveThred5Ant		 OBJECT-TYPE
		SYNTAX					 Integer32( 0 .. 65535 )
		MAX-ACCESS			 read-create
		STATUS					 current
		DESCRIPTION			 " -- "
		::=  { phyCfgEntry  76 }


	phyCfgPucchNormalCpFmt1ActiveThred6Ant		 OBJECT-TYPE
		SYNTAX					 Integer32( 0 .. 65535 )
		MAX-ACCESS			 read-create
		STATUS					 current
		DESCRIPTION			 " -- "
		::=  { phyCfgEntry  77 }


	phyCfgPucchNormalCpFmt1ActiveThred7Ant		 OBJECT-TYPE
		SYNTAX					 Integer32( 0 .. 65535 )
		MAX-ACCESS			 read-create
		STATUS					 current
		DESCRIPTION			 " -- "
		::=  { phyCfgEntry  78 }


	phyCfgPucchNormalCpFmt1ActiveThred8Ant		 OBJECT-TYPE
		SYNTAX					 Integer32( 0 .. 65535 )
		MAX-ACCESS			 read-create
		STATUS					 current
		DESCRIPTION			 " -- "
		::=  { phyCfgEntry  79 }


	phyCfgPucchExTendCpFmt1ActiveThred1Ant		 OBJECT-TYPE
		SYNTAX					 Integer32( 0 .. 65535 )
		MAX-ACCESS			 read-create
		STATUS					 current
		DESCRIPTION			 " -- "
		::=  { phyCfgEntry  80 }


	phyCfgPucchExTendCpFmt1ActiveThred2Ant		 OBJECT-TYPE
		SYNTAX					 Integer32( 0 .. 65535 )
		MAX-ACCESS			 read-create
		STATUS					 current
		DESCRIPTION			 " -- "
		::=  { phyCfgEntry  81 }


	phyCfgPucchExTendCpFmt1ActiveThred3Ant		 OBJECT-TYPE
		SYNTAX					 Integer32( 0 .. 65535 )
		MAX-ACCESS			 read-create
		STATUS					 current
		DESCRIPTION			 " -- "
		::=  { phyCfgEntry  82 }


	phyCfgPucchExTendCpFmt1ActiveThred4Ant		 OBJECT-TYPE
		SYNTAX					 Integer32( 0 .. 65535 )
		MAX-ACCESS			 read-create
		STATUS					 current
		DESCRIPTION			 " -- "
		::=  { phyCfgEntry  83 }


	phyCfgPucchExTendCpFmt1ActiveThred5Ant		 OBJECT-TYPE
		SYNTAX					 Integer32( 0 .. 65535 )
		MAX-ACCESS			 read-create
		STATUS					 current
		DESCRIPTION			 " -- "
		::=  { phyCfgEntry  84 }


	phyCfgPucchExTendCpFmt1ActiveThred6Ant		 OBJECT-TYPE
		SYNTAX					 Integer32( 0 .. 65535 )
		MAX-ACCESS			 read-create
		STATUS					 current
		DESCRIPTION			 " -- "
		::=  { phyCfgEntry  85 }


	phyCfgPucchExTendCpFmt1ActiveThred7Ant		 OBJECT-TYPE
		SYNTAX					 Integer32( 0 .. 65535 )
		MAX-ACCESS			 read-create
		STATUS					 current
		DESCRIPTION			 " -- "
		::=  { phyCfgEntry  86 }


	phyCfgPucchExTendCpFmt1ActiveThred8Ant		 OBJECT-TYPE
		SYNTAX					 Integer32( 0 .. 65535 )
		MAX-ACCESS			 read-create
		STATUS					 current
		DESCRIPTION			 " -- "
		::=  { phyCfgEntry  87 }


	phyCfgPucchSrAckCollideSelectFlag		 OBJECT-TYPE
		SYNTAX					 INTEGER{ useSRthre(0),useACKthre(1)  }
		MAX-ACCESS			 read-create
		STATUS					 current
		DESCRIPTION			 " -- "
		::=  { phyCfgEntry  88 }


	phyCfgPucchSrThrePara		 OBJECT-TYPE
		SYNTAX					 Integer32( 0 .. 65535 )
		MAX-ACCESS			 read-create
		STATUS					 current
		DESCRIPTION			 " -- "
		::=  { phyCfgEntry  89 }


	phyCfgPucchAckThrePara		 OBJECT-TYPE
		SYNTAX					 Integer32( 0 .. 65535 )
		MAX-ACCESS			 read-create
		STATUS					 current
		DESCRIPTION			 " -- "
		::=  { phyCfgEntry  90 }


	phyCfgPucchSingleAntAlgorithmFlag		 OBJECT-TYPE
		SYNTAX					 INTEGER{ off(0),on(1)  }
		MAX-ACCESS			 read-create
		STATUS					 current
		DESCRIPTION			 " -- "
		::=  { phyCfgEntry  91 }


	phyCfgPucchNormalCpFmt1ActiveThredSingleAnt		 OBJECT-TYPE
		SYNTAX					 Integer32( 0 .. 65535 )
		MAX-ACCESS			 read-create
		STATUS					 current
		DESCRIPTION			 " -- "
		::=  { phyCfgEntry  92 }


	phyCfgRipPMReportDeltaSSF		 OBJECT-TYPE
		SYNTAX					 Integer32( 0 .. 20 )
		MAX-ACCESS			 read-create
		STATUS					 current
		DESCRIPTION			 " -- "
		::=  { phyCfgEntry  93 }


	phyCfgPlTestPara		 OBJECT-TYPE
		SYNTAX					 Unsigned32( 0 .. 4294967295 )
		MAX-ACCESS			 read-create
		STATUS					 current
		DESCRIPTION			 " -- "
		::=  { phyCfgEntry  94 }


	phyCfgPucchVolteSrStubPeriod		 OBJECT-TYPE
		SYNTAX					 Integer32( 1 .. 320 )
		MAX-ACCESS			 read-create
		STATUS					 current
		DESCRIPTION			 " -- "
		::=  { phyCfgEntry  95 }


	phyCfgRipPMReportDeltaSwitch		 OBJECT-TYPE
		SYNTAX					 INTEGER{ off(0),on(1)  }
		MAX-ACCESS			 read-create
		STATUS					 current
		DESCRIPTION			 " -- "
		::=  { phyCfgEntry  96 }


	phyCfgCrsStepupStep		 OBJECT-TYPE
		SYNTAX					 Integer32( 0 .. 6 )
		MAX-ACCESS			 read-create
		STATUS					 current
		DESCRIPTION			 " -- "
		::=  { phyCfgEntry  97 }


	phyCfgCrsStepdownStep		 OBJECT-TYPE
		SYNTAX					 Integer32( 0 .. 10 )
		MAX-ACCESS			 read-create
		STATUS					 current
		DESCRIPTION			 " -- "
		::=  { phyCfgEntry  98 }


	phyCfgSrsUePowerCqiThre		 OBJECT-TYPE
		SYNTAX					 Integer32( -150 .. -40 )
		MAX-ACCESS			 read-create
		STATUS					 current
		DESCRIPTION			 " -- "
		::=  { phyCfgEntry  99 }


	phyCfgSrsUePowerBfThre		 OBJECT-TYPE
		SYNTAX					 Integer32( -150 .. -40 )
		MAX-ACCESS			 read-create
		STATUS					 current
		DESCRIPTION			 " -- "
		::=  { phyCfgEntry  100 }


	phyCfgSrsUePowerTaThre		 OBJECT-TYPE
		SYNTAX					 Integer32( -150 .. -40 )
		MAX-ACCESS			 read-create
		STATUS					 current
		DESCRIPTION			 " -- "
		::=  { phyCfgEntry  101 }


	phyCfgSrsUePowerAnteSelectThre		 OBJECT-TYPE
		SYNTAX					 Integer32( -150 .. -40 )
		MAX-ACCESS			 read-create
		STATUS					 current
		DESCRIPTION			 " -- "
		::=  { phyCfgEntry  102 }


	phyCfgSrsSnrCqiThre		 OBJECT-TYPE
		SYNTAX					 Integer32( -20 .. 40 )
		MAX-ACCESS			 read-create
		STATUS					 current
		DESCRIPTION			 " -- "
		::=  { phyCfgEntry  103 }


	phyCfgSrsSnrBfThre		 OBJECT-TYPE
		SYNTAX					 Integer32( -20 .. 40 )
		MAX-ACCESS			 read-create
		STATUS					 current
		DESCRIPTION			 " -- "
		::=  { phyCfgEntry  104 }


	phyCfgSrsSnrTaThre		 OBJECT-TYPE
		SYNTAX					 Integer32( -20 .. 40 )
		MAX-ACCESS			 read-create
		STATUS					 current
		DESCRIPTION			 " -- "
		::=  { phyCfgEntry  105 }


	phyCfgSrsSnrAnteSelectThre		 OBJECT-TYPE
		SYNTAX					 Integer32( -20 .. 40 )
		MAX-ACCESS			 read-create
		STATUS					 current
		DESCRIPTION			 " -- "
		::=  { phyCfgEntry  106 }


	phyPuschPowerControlSnrThre		 OBJECT-TYPE
		SYNTAX					 Integer32( -30 .. 40 )
		MAX-ACCESS			 read-create
		STATUS					 current
		DESCRIPTION			 " -- "
		::=  { phyCfgEntry  107 }


	phyCfgRipIotShifter		 OBJECT-TYPE
		SYNTAX					 Integer32( 0 .. 8 )
		MAX-ACCESS			 read-create
		STATUS					 current
		DESCRIPTION			 " -- "
		::=  { phyCfgEntry  108 }


	acCfgTable		 OBJECT-TYPE
		SYNTAX					 SEQUENCE  OF	 AcCfgEntry
		MAX-ACCESS			 not-accessible
		STATUS					 current
		DESCRIPTION			 " -- "
		::=  { pl  3 }


	acCfgEntry		 OBJECT-TYPE
		SYNTAX					 AcCfgEntry
		MAX-ACCESS			 not-accessible
		STATUS					 current
		DESCRIPTION			 " -- "
		INDEX						{ acCfgLcId }
		::=  { acCfgTable  1 }


	AcCfgEntry		 ::=  SEQUENCE {
		acCfgLcId					Integer32,
		acCfgRowStatus					RowStatus,
		acCfgPowAttenuRange					Integer32,
		acCfgAvePowAttenuRange					Integer32,
		acCfgPeakposShiftThreshold					Integer32,
		acCfgAvePeakposShiftThreshold					Integer32,
		acCfgSNRCalThreshold					Integer32,
		acCfgAveSNRCalThreshold					Integer32,
		acCfgPowLowThresholdSwitch					INTEGER,
		acCfgPowLowThreshold					Integer32,
		acCfgInterferenceSwitch					INTEGER,
		acCfgInterferenceThreshold					Integer32
		}


	acCfgLcId		 OBJECT-TYPE
		SYNTAX					 Integer32( 0 .. 23 )
		MAX-ACCESS			 not-accessible
		STATUS					 current
		DESCRIPTION			 " -- "
		::=  { acCfgEntry  1 }


	acCfgRowStatus		 OBJECT-TYPE
		SYNTAX					 RowStatus
		MAX-ACCESS			 read-create
		STATUS					 current
		DESCRIPTION			 " -- "
		::=  { acCfgEntry  2 }


	acCfgPowAttenuRange		 OBJECT-TYPE
		SYNTAX					 Integer32( -100 .. 100 )
		MAX-ACCESS			 read-create
		STATUS					 current
		DESCRIPTION			 " -- "
		::=  { acCfgEntry  3 }


	acCfgAvePowAttenuRange		 OBJECT-TYPE
		SYNTAX					 Integer32( -100 .. 100 )
		MAX-ACCESS			 read-create
		STATUS					 current
		DESCRIPTION			 " -- "
		::=  { acCfgEntry  4 }


	acCfgPeakposShiftThreshold		 OBJECT-TYPE
		SYNTAX					 Integer32( -100 .. 100 )
		MAX-ACCESS			 read-create
		STATUS					 current
		DESCRIPTION			 " -- "
		::=  { acCfgEntry  5 }


	acCfgAvePeakposShiftThreshold		 OBJECT-TYPE
		SYNTAX					 Integer32( -100 .. 100 )
		MAX-ACCESS			 read-create
		STATUS					 current
		DESCRIPTION			 " -- "
		::=  { acCfgEntry  6 }


	acCfgSNRCalThreshold		 OBJECT-TYPE
		SYNTAX					 Integer32( -100 .. 100 )
		MAX-ACCESS			 read-create
		STATUS					 current
		DESCRIPTION			 " -- "
		::=  { acCfgEntry  7 }


	acCfgAveSNRCalThreshold		 OBJECT-TYPE
		SYNTAX					 Integer32( -100 .. 100 )
		MAX-ACCESS			 read-create
		STATUS					 current
		DESCRIPTION			 " -- "
		::=  { acCfgEntry  8 }


	acCfgPowLowThresholdSwitch		 OBJECT-TYPE
		SYNTAX					 INTEGER{ off(0),on(1)  }
		MAX-ACCESS			 read-create
		STATUS					 current
		DESCRIPTION			 " -- "
		::=  { acCfgEntry  9 }


	acCfgPowLowThreshold		 OBJECT-TYPE
		SYNTAX					 Integer32( -50 .. -25 )
		MAX-ACCESS			 read-create
		STATUS					 current
		DESCRIPTION			 " -- "
		::=  { acCfgEntry  10 }


	acCfgInterferenceSwitch		 OBJECT-TYPE
		SYNTAX					 INTEGER{ off(0),on(1)  }
		MAX-ACCESS			 read-create
		STATUS					 current
		DESCRIPTION			 " -- "
		::=  { acCfgEntry  11 }


	acCfgInterferenceThreshold		 OBJECT-TYPE
		SYNTAX					 Integer32( -100 .. -50 )
		MAX-ACCESS			 read-create
		STATUS					 current
		DESCRIPTION			 " -- "
		::=  { acCfgEntry  12 }


	plSwitchNode		 OBJECT IDENTIFIER
		::=  { pl  4 }


	plUsrLogCfgTable		 OBJECT-TYPE
		SYNTAX					 SEQUENCE  OF	 PlUsrLogCfgEntry
		MAX-ACCESS			 not-accessible
		STATUS					 current
		DESCRIPTION			 " -- "
		::=  { plSwitchNode  1 }


	plUsrLogCfgEntry		 OBJECT-TYPE
		SYNTAX					 PlUsrLogCfgEntry
		MAX-ACCESS			 not-accessible
		STATUS					 current
		DESCRIPTION			 " -- "
		INDEX						{ plUsrLogLcId }
		::=  { plUsrLogCfgTable  1 }


	PlUsrLogCfgEntry		 ::=  SEQUENCE {
		plUsrLogLcId					Integer32,
		plUsrLogRowStatus					RowStatus,
		plUsrLogFlag					INTEGER,
		plUsrLogReportType					INTEGER,
		plUsrLogUlReportUeId					Integer32,
		plUsrLogUlReportDuration					Integer32,
		plUsrLogUlBlerThreshlod					Integer32,
		plUsrLogUlDataLargePeriod					Integer32,
		plUsrLogUlDataSmallPeriod					Integer32,
		plUsrLogUlDataSaveTimes					Integer32,
		plUsrLogUlInstanInfoPeriod					Integer32,
		plUsrLogDlReportType					INTEGER,
		plUsrLogDlReportUeId					Integer32,
		plUsrLogDlReportDuration					Integer32,
		plUsrLogDlBlerThreshlod					Integer32,
		plUsrLogDlDataLargePeriod					Integer32,
		plUsrLogDlDataSmallPeriod					Integer32,
		plUsrLogDlDataSaveTimes					Integer32,
		plUsrLogDlLogLevel					Integer32,
		plUsrLogPucchCatchDataType					INTEGER,
		plUsrLogPucchCatchDataUeindex					Integer32,
		plUsrLogPucchCatchDataSfn					Integer32,
		plUsrLogPucchCatchDataAckValue					Integer32,
		plUsrLogPucchCatchDataResourceIndex					Integer32,
		plUsrLogPucchCatchDataCqiValue					Integer32,
		plUsrLogPucchSnrOrRsrp					Unsigned32,
		plUsrLogMsg5CatchSwitch					INTEGER,
		plUsrLogPucchCatchDataHarqProcNum					Integer32,
		plUsrLogPucchCatchDataServiceType					INTEGER,
		plUsrLogPucchCatchDataVolteActiveFlag					INTEGER,
		plUsrLogPucchCatchDataCQIorRI					INTEGER,
		plUsrLogPucchPlLogFlag					INTEGER,
		plReportFlag					INTEGER,
		plReportUeType					INTEGER,
		plReportUeId					Integer32,
		plReportType					BITS
		}


	plUsrLogLcId		 OBJECT-TYPE
		SYNTAX					 Integer32( 0 .. 23 )
		MAX-ACCESS			 not-accessible
		STATUS					 current
		DESCRIPTION			 " -- "
		::=  { plUsrLogCfgEntry  1 }


	plUsrLogRowStatus		 OBJECT-TYPE
		SYNTAX					 RowStatus
		MAX-ACCESS			 read-create
		STATUS					 current
		DESCRIPTION			 " -- "
		::=  { plUsrLogCfgEntry  2 }


	plUsrLogFlag		 OBJECT-TYPE
		SYNTAX					 INTEGER{ off(0),on(1)  }
		MAX-ACCESS			 read-create
		STATUS					 current
		DESCRIPTION			 " -- "
		::=  { plUsrLogCfgEntry  3 }


	plUsrLogReportType		 OBJECT-TYPE
		SYNTAX					 INTEGER{ designteRNTI(0),designteUsrIndex(1),alternation(2)  }
		MAX-ACCESS			 read-create
		STATUS					 current
		DESCRIPTION			 " -- "
		::=  { plUsrLogCfgEntry  4 }


	plUsrLogUlReportUeId		 OBJECT-TYPE
		SYNTAX					 Integer32( 0 .. 65535 )
		MAX-ACCESS			 read-create
		STATUS					 current
		DESCRIPTION			 " -- "
		::=  { plUsrLogCfgEntry  5 }


	plUsrLogUlReportDuration		 OBJECT-TYPE
		SYNTAX					 Integer32( 1 .. 60 )
		MAX-ACCESS			 read-create
		STATUS					 current
		DESCRIPTION			 " -- "
		::=  { plUsrLogCfgEntry  6 }


	plUsrLogUlBlerThreshlod		 OBJECT-TYPE
		SYNTAX					 Integer32( 0 .. 100 )
		MAX-ACCESS			 read-create
		STATUS					 current
		DESCRIPTION			 " -- "
		::=  { plUsrLogCfgEntry  7 }


	plUsrLogUlDataLargePeriod		 OBJECT-TYPE
		SYNTAX					 Integer32( 1 .. 60 )
		MAX-ACCESS			 read-create
		STATUS					 current
		DESCRIPTION			 " -- "
		::=  { plUsrLogCfgEntry  8 }


	plUsrLogUlDataSmallPeriod		 OBJECT-TYPE
		SYNTAX					 Integer32( 1 .. 100 )
		MAX-ACCESS			 read-create
		STATUS					 current
		DESCRIPTION			 " -- "
		::=  { plUsrLogCfgEntry  9 }


	plUsrLogUlDataSaveTimes		 OBJECT-TYPE
		SYNTAX					 Integer32( 1 .. 6 )
		MAX-ACCESS			 read-create
		STATUS					 current
		DESCRIPTION			 " -- "
		::=  { plUsrLogCfgEntry  10 }


	plUsrLogUlInstanInfoPeriod		 OBJECT-TYPE
		SYNTAX					 Integer32( 1 .. 100 )
		MAX-ACCESS			 read-create
		STATUS					 current
		DESCRIPTION			 " -- "
		::=  { plUsrLogCfgEntry  11 }


	plUsrLogDlReportType		 OBJECT-TYPE
		SYNTAX					 INTEGER{ designteRNTI(0),designteUsrIndex(1),alternation(2)  }
		MAX-ACCESS			 read-create
		STATUS					 current
		DESCRIPTION			 " -- "
		::=  { plUsrLogCfgEntry  12 }


	plUsrLogDlReportUeId		 OBJECT-TYPE
		SYNTAX					 Integer32( 0 .. 65535 )
		MAX-ACCESS			 read-create
		STATUS					 current
		DESCRIPTION			 " -- "
		::=  { plUsrLogCfgEntry  13 }


	plUsrLogDlReportDuration		 OBJECT-TYPE
		SYNTAX					 Integer32( 1 .. 60 )
		MAX-ACCESS			 read-create
		STATUS					 current
		DESCRIPTION			 " -- "
		::=  { plUsrLogCfgEntry  14 }


	plUsrLogDlBlerThreshlod		 OBJECT-TYPE
		SYNTAX					 Integer32( 1 .. 100 )
		MAX-ACCESS			 read-create
		STATUS					 current
		DESCRIPTION			 " -- "
		::=  { plUsrLogCfgEntry  15 }


	plUsrLogDlDataLargePeriod		 OBJECT-TYPE
		SYNTAX					 Integer32( 1 .. 60 )
		MAX-ACCESS			 read-create
		STATUS					 current
		DESCRIPTION			 " -- "
		::=  { plUsrLogCfgEntry  16 }


	plUsrLogDlDataSmallPeriod		 OBJECT-TYPE
		SYNTAX					 Integer32( 1 .. 100 )
		MAX-ACCESS			 read-create
		STATUS					 current
		DESCRIPTION			 " -- "
		::=  { plUsrLogCfgEntry  17 }


	plUsrLogDlDataSaveTimes		 OBJECT-TYPE
		SYNTAX					 Integer32( 1 .. 64 )
		MAX-ACCESS			 read-create
		STATUS					 current
		DESCRIPTION			 " -- "
		::=  { plUsrLogCfgEntry  18 }


	plUsrLogDlLogLevel		 OBJECT-TYPE
		SYNTAX					 Integer32( 0 .. 7 )
		MAX-ACCESS			 read-create
		STATUS					 current
		DESCRIPTION			 " -- "
		::=  { plUsrLogCfgEntry  19 }


	plUsrLogPucchCatchDataType		 OBJECT-TYPE
		SYNTAX					 INTEGER{ bler(0),ackunactive(1),ackactive(2),ackequal(3),ackunequal(4),cqiequal(5),cqiunequal(6),fmt2ackequal(7),fmt2ackunequal(8),snrlower(9),snrhigher(10),rsrplower(11),rsrphigher(12),fmt3ackequal(13),fmt3ackunequal(14),srstubsrmiss(15)  }
		MAX-ACCESS			 read-create
		STATUS					 current
		DESCRIPTION			 " -- "
		::=  { plUsrLogCfgEntry  20 }


	plUsrLogPucchCatchDataUeindex		 OBJECT-TYPE
		SYNTAX					 Integer32( 0 .. 65535 )
		MAX-ACCESS			 read-create
		STATUS					 current
		DESCRIPTION			 " -- "
		::=  { plUsrLogCfgEntry  21 }


	plUsrLogPucchCatchDataSfn		 OBJECT-TYPE
		SYNTAX					 Integer32( 0 .. 9|255 )
		MAX-ACCESS			 read-create
		STATUS					 current
		DESCRIPTION			 " -- "
		::=  { plUsrLogCfgEntry  22 }


	plUsrLogPucchCatchDataAckValue		 OBJECT-TYPE
		SYNTAX					 Integer32( 0 .. 1048575 )
		MAX-ACCESS			 read-create
		STATUS					 current
		DESCRIPTION			 " -- "
		::=  { plUsrLogCfgEntry  23 }


	plUsrLogPucchCatchDataResourceIndex		 OBJECT-TYPE
		SYNTAX					 Integer32( 0 .. 15 )
		MAX-ACCESS			 read-create
		STATUS					 current
		DESCRIPTION			 " -- "
		::=  { plUsrLogCfgEntry  24 }


	plUsrLogPucchCatchDataCqiValue		 OBJECT-TYPE
		SYNTAX					 Integer32( 0 .. 65535 )
		MAX-ACCESS			 read-create
		STATUS					 current
		DESCRIPTION			 " -- "
		::=  { plUsrLogCfgEntry  25 }


	plUsrLogPucchSnrOrRsrp		 OBJECT-TYPE
		SYNTAX					 Unsigned32( 0 .. 4294967295 )
		MAX-ACCESS			 read-create
		STATUS					 current
		DESCRIPTION			 " -- "
		::=  { plUsrLogCfgEntry  26 }


	plUsrLogMsg5CatchSwitch		 OBJECT-TYPE
		SYNTAX					 INTEGER{ off(0),on(1)  }
		MAX-ACCESS			 read-create
		STATUS					 current
		DESCRIPTION			 " -- "
		::=  { plUsrLogCfgEntry  27 }


	plUsrLogPucchCatchDataHarqProcNum		 OBJECT-TYPE
		SYNTAX					 Integer32( 0 .. 255 )
		MAX-ACCESS			 read-create
		STATUS					 current
		DESCRIPTION			 " -- "
		::=  { plUsrLogCfgEntry  28 }


	plUsrLogPucchCatchDataServiceType		 OBJECT-TYPE
		SYNTAX					 INTEGER{ servicetypedata(0),servicetypevolte(1)  }
		MAX-ACCESS			 read-create
		STATUS					 current
		DESCRIPTION			 " -- "
		::=  { plUsrLogCfgEntry  29 }


	plUsrLogPucchCatchDataVolteActiveFlag		 OBJECT-TYPE
		SYNTAX					 INTEGER{ volteunactive(0),volteactive(1)  }
		MAX-ACCESS			 read-create
		STATUS					 current
		DESCRIPTION			 " -- "
		::=  { plUsrLogCfgEntry  30 }


	plUsrLogPucchCatchDataCQIorRI		 OBJECT-TYPE
		SYNTAX					 INTEGER{ catchri(0),catchcqi(1)  }
		MAX-ACCESS			 read-create
		STATUS					 current
		DESCRIPTION			 " -- "
		::=  { plUsrLogCfgEntry  31 }


	plUsrLogPucchPlLogFlag		 OBJECT-TYPE
		SYNTAX					 INTEGER{ off(0),on(1)  }
		MAX-ACCESS			 read-create
		STATUS					 current
		DESCRIPTION			 " -- "
		::=  { plUsrLogCfgEntry  32 }


	plReportFlag		 OBJECT-TYPE
		SYNTAX					 INTEGER{ off(0),on(1)  }
		MAX-ACCESS			 read-create
		STATUS					 current
		DESCRIPTION			 " -- "
		::=  { plUsrLogCfgEntry  33 }


	plReportUeType		 OBJECT-TYPE
		SYNTAX					 INTEGER{ off(0),on(1)  }
		MAX-ACCESS			 read-create
		STATUS					 current
		DESCRIPTION			 " -- "
		::=  { plUsrLogCfgEntry  34 }


	plReportUeId		 OBJECT-TYPE
		SYNTAX					 Integer32( 0 .. 1199 )
		MAX-ACCESS			 read-create
		STATUS					 current
		DESCRIPTION			 " -- "
		::=  { plUsrLogCfgEntry  35 }


	plReportType		 OBJECT-TYPE
		SYNTAX					 BITS{ iotlogflag(0),bflogflag(1),sdlogflag(2),pucchccmacpowerlogflag(3),pucchccmacacklogflag(4),pucchmacdelogflag(5),srslogflag(6),puschackcqilogflag(7),puschcrclogflag(8)  }
		MAX-ACCESS			 read-create
		STATUS					 current
		DESCRIPTION			 " -- "
		::=  { plUsrLogCfgEntry  36 }


	plIotLogServerConfig		 OBJECT IDENTIFIER
		::=  { plSwitchNode  2 }


	plIotLogServerInetAddrType		 OBJECT-TYPE
		SYNTAX					 InetAddressType
		MAX-ACCESS			 read-write
		STATUS					 current
		DESCRIPTION			 " -- "
		::=  { plIotLogServerConfig  1 }


	plIotLogServerInetAddr		 OBJECT-TYPE
		SYNTAX					 InetAddress
		MAX-ACCESS			 read-write
		STATUS					 current
		DESCRIPTION			 " -- "
		::=  { plIotLogServerConfig  2 }


	plIotLogFileDirectory		 OBJECT-TYPE
		SYNTAX					 DisplayString( SIZE ( 1 .. 199 ) )
		MAX-ACCESS			 read-write
		STATUS					 current
		DESCRIPTION			 " -- "
		::=  { plIotLogServerConfig  3 }


	plIotLogFtpServerLoginName		 OBJECT-TYPE
		SYNTAX					 DisplayString( SIZE ( 1 .. 255 ) )
		MAX-ACCESS			 read-write
		STATUS					 current
		DESCRIPTION			 " -- "
		::=  { plIotLogServerConfig  4 }


	plIotLogFtpServerPassword		 OBJECT-TYPE
		SYNTAX					 DisplayString( SIZE ( 1 .. 255 ) )
		MAX-ACCESS			 read-write
		STATUS					 current
		DESCRIPTION			 " -- "
		::=  { plIotLogServerConfig  5 }


	plRipCellCfgTable		 OBJECT-TYPE
		SYNTAX					 SEQUENCE  OF	 PlRipCellCfgEntry
		MAX-ACCESS			 not-accessible
		STATUS					 current
		DESCRIPTION			 " -- "
		::=  { plSwitchNode  3 }


	plRipCellCfgEntry		 OBJECT-TYPE
		SYNTAX					 PlRipCellCfgEntry
		MAX-ACCESS			 not-accessible
		STATUS					 current
		DESCRIPTION			 " -- "
		INDEX						{ plRipCellLcId }
		::=  { plRipCellCfgTable  1 }


	PlRipCellCfgEntry		 ::=  SEQUENCE {
		plRipCellLcId					Integer32,
		plRipCellRowStatus					RowStatus,
		plRipCellUpIotSwitch					INTEGER,
		plRipCellGranularity					INTEGER,
		plRipCellSchedSilentPeriod					INTEGER
		}


	plRipCellLcId		 OBJECT-TYPE
		SYNTAX					 Integer32( 0 .. 23 )
		MAX-ACCESS			 not-accessible
		STATUS					 current
		DESCRIPTION			 " -- "
		::=  { plRipCellCfgEntry  1 }


	plRipCellRowStatus		 OBJECT-TYPE
		SYNTAX					 RowStatus
		MAX-ACCESS			 read-create
		STATUS					 current
		DESCRIPTION			 " -- "
		::=  { plRipCellCfgEntry  2 }


	plRipCellUpIotSwitch		 OBJECT-TYPE
		SYNTAX					 INTEGER{ off(0),ripIot(1),prbIot(2),prbIotAndschedSilent(3),schedSilent(4)  }
		MAX-ACCESS			 read-create
		STATUS					 current
		DESCRIPTION			 " -- "
		::=  { plRipCellCfgEntry  3 }


	plRipCellGranularity		 OBJECT-TYPE
		SYNTAX					 INTEGER{ slot(0),symbol(1)  }
		MAX-ACCESS			 read-create
		STATUS					 current
		DESCRIPTION			 " -- "
		::=  { plRipCellCfgEntry  4 }


	plRipCellSchedSilentPeriod		 OBJECT-TYPE
		SYNTAX					 INTEGER{ ms1280(0),ms2560(1),ms5120(2)  }
		MAX-ACCESS			 read-create
		STATUS					 current
		DESCRIPTION			 " -- "
		::=  { plRipCellCfgEntry  5 }


	plRipLogConfig		 OBJECT IDENTIFIER
		::=  { plSwitchNode  4 }


	plRipLogInetAddrType		 OBJECT-TYPE
		SYNTAX					 InetAddressType
		MAX-ACCESS			 read-write
		STATUS					 current
		DESCRIPTION			 " -- "
		::=  { plRipLogConfig  1 }


	plRipLogInetAddr		 OBJECT-TYPE
		SYNTAX					 InetAddress
		MAX-ACCESS			 read-write
		STATUS					 current
		DESCRIPTION			 " -- "
		::=  { plRipLogConfig  2 }


	plRipLogFileDirectory		 OBJECT-TYPE
		SYNTAX					 DisplayString( SIZE ( 1 .. 199 ) )
		MAX-ACCESS			 read-write
		STATUS					 current
		DESCRIPTION			 " -- "
		::=  { plRipLogConfig  3 }


	plRipLogFtpServerLoginName		 OBJECT-TYPE
		SYNTAX					 DisplayString( SIZE ( 1 .. 255 ) )
		MAX-ACCESS			 read-write
		STATUS					 current
		DESCRIPTION			 " -- "
		::=  { plRipLogConfig  4 }


	plRipLogFtpServerPassword		 OBJECT-TYPE
		SYNTAX					 DisplayString( SIZE ( 1 .. 255 ) )
		MAX-ACCESS			 read-write
		STATUS					 current
		DESCRIPTION			 " -- "
		::=  { plRipLogConfig  5 }


	plRipLogStatisticPeriod		 OBJECT-TYPE
		SYNTAX					 Integer32( 1 .. 15 )
		MAX-ACCESS			 read-create
		STATUS					 current
		DESCRIPTION			 " -- "
		::=  { plRipLogConfig  6 }


	plRipLogReportPeriod		 OBJECT-TYPE
		SYNTAX					 Integer32( 1 .. 1440 )
		MAX-ACCESS			 read-create
		STATUS					 current
		DESCRIPTION			 " -- "
		::=  { plRipLogConfig  7 }


	plADICfgTable		 OBJECT-TYPE
		SYNTAX					 SEQUENCE  OF	 PlADICfgEntry
		MAX-ACCESS			 not-accessible
		STATUS					 current
		DESCRIPTION			 " -- "
		::=  { plSwitchNode  5 }


	plADICfgEntry		 OBJECT-TYPE
		SYNTAX					 PlADICfgEntry
		MAX-ACCESS			 not-accessible
		STATUS					 current
		DESCRIPTION			 " -- "
		INDEX						{ plADILcId }
		::=  { plADICfgTable  1 }


	PlADICfgEntry		 ::=  SEQUENCE {
		plADILcId					Integer32,
		plADIRowStatus					RowStatus,
		plADIFeatureSwitch					INTEGER,
		plADIIoTThresh					Integer32,
		plADIIoThighThreshoffset					Integer32,
		plADIIoTLowThreshoffset					Integer32,
		plADIDetectPeriod					Integer32,
		plADIDetectNum					Integer32,
		plADIDetectRatio					Integer32,
		plADICurrentStatus					INTEGER,
		plADIUlPwrPuschPowerSwitch					INTEGER,
		plADIUlPwrAlpha					INTEGER,
		plADIUlPwrPucchPowerSwitch					INTEGER,
		plADIUlPwrP0NominalPucch					Integer32,
		plADIRaPreambleInitRcvTargetPow					INTEGER,
		plADICellSelectQRxlevMin					INTEGER,
		plADICellReselIntraFreqQrxLevMin					INTEGER,
		plADIUlPwrP0NominalPusch					Integer32,
		plADIRaPowerRampStep					INTEGER,
		plADIRaPreambleTrMax					INTEGER,
		plADIUlPwrMsg3PowerCtrlSwitch					INTEGER,
		plADIUlPwrDeltaPreambleMsg3					INTEGER,
		plADIMacTestSwitchInfoUlLimitSrbMcsSwitch					INTEGER,
		plADIMacTestSwitchInfoUlMaxSrbMcs					Integer32,
		plADIMacTestSwitchInfoMcslimitSwitch					INTEGER,
		plADIMacTestSwitchInfolimitUlMcs					Integer32,
		plADIMacTestSwitchInfolimitDlMcs					Integer32
		}


	plADILcId		 OBJECT-TYPE
		SYNTAX					 Integer32( 0 .. 23 )
		MAX-ACCESS			 not-accessible
		STATUS					 current
		DESCRIPTION			 " -- "
		::=  { plADICfgEntry  1 }


	plADIRowStatus		 OBJECT-TYPE
		SYNTAX					 RowStatus
		MAX-ACCESS			 read-create
		STATUS					 current
		DESCRIPTION			 " -- "
		::=  { plADICfgEntry  2 }


	plADIFeatureSwitch		 OBJECT-TYPE
		SYNTAX					 INTEGER{ off(0),on(1)  }
		MAX-ACCESS			 read-create
		STATUS					 current
		DESCRIPTION			 " -- "
		::=  { plADICfgEntry  3 }


	plADIIoTThresh		 OBJECT-TYPE
		SYNTAX					 Integer32( 0 .. 120 )
		MAX-ACCESS			 read-create
		STATUS					 current
		DESCRIPTION			 " -- "
		::=  { plADICfgEntry  4 }


	plADIIoThighThreshoffset		 OBJECT-TYPE
		SYNTAX					 Integer32( 0 .. 50 )
		MAX-ACCESS			 read-create
		STATUS					 current
		DESCRIPTION			 " -- "
		::=  { plADICfgEntry  5 }


	plADIIoTLowThreshoffset		 OBJECT-TYPE
		SYNTAX					 Integer32( 0 .. 20 )
		MAX-ACCESS			 read-create
		STATUS					 current
		DESCRIPTION			 " -- "
		::=  { plADICfgEntry  6 }


	plADIDetectPeriod		 OBJECT-TYPE
		SYNTAX					 Integer32( 1 .. 10 )
		MAX-ACCESS			 read-create
		STATUS					 current
		DESCRIPTION			 " -- "
		::=  { plADICfgEntry  7 }


	plADIDetectNum		 OBJECT-TYPE
		SYNTAX					 Integer32( 1 .. 255 )
		MAX-ACCESS			 read-create
		STATUS					 current
		DESCRIPTION			 " -- "
		::=  { plADICfgEntry  8 }


	plADIDetectRatio		 OBJECT-TYPE
		SYNTAX					 Integer32( 60 .. 100 )
		MAX-ACCESS			 read-create
		STATUS					 current
		DESCRIPTION			 " -- "
		::=  { plADICfgEntry  9 }


	plADICurrentStatus		 OBJECT-TYPE
		SYNTAX					 INTEGER{ normal(0),middle(1),high(2),higher(3),other(4)  }
		MAX-ACCESS			 read-only
		STATUS					 current
		DESCRIPTION			 " -- "
		::=  { plADICfgEntry  10 }


	plADIUlPwrPuschPowerSwitch		 OBJECT-TYPE
		SYNTAX					 INTEGER{ off(0),on(1)  }
		MAX-ACCESS			 read-create
		STATUS					 current
		DESCRIPTION			 " -- "
		::=  { plADICfgEntry  11 }


	plADIUlPwrAlpha		 OBJECT-TYPE
		SYNTAX					 INTEGER{ al0(0),al04(1),al05(2),al06(3),al07(4),al08(5),al09(6),al1(7)  }
		MAX-ACCESS			 read-create
		STATUS					 current
		DESCRIPTION			 " -- "
		::=  { plADICfgEntry  12 }


	plADIUlPwrPucchPowerSwitch		 OBJECT-TYPE
		SYNTAX					 INTEGER{ off(0),on(1)  }
		MAX-ACCESS			 read-create
		STATUS					 current
		DESCRIPTION			 " -- "
		::=  { plADICfgEntry  13 }


	plADIUlPwrP0NominalPucch		 OBJECT-TYPE
		SYNTAX					 Integer32( -127 .. -96 )
		MAX-ACCESS			 read-create
		STATUS					 current
		DESCRIPTION			 " -- "
		::=  { plADICfgEntry  14 }


	plADIRaPreambleInitRcvTargetPow		 OBJECT-TYPE
		SYNTAX					 INTEGER{ n120dBm(0),n118dBm(1),n116dBm(2),n114dBm(3),n112dBm(4),n110dBm(5),n108dBm(6),n106dBm(7),n104dBm(8),n102dBm(9),n100dBm(10),n98dBm(11),n96dBm(12),n94dBm(13),n92dBm(14),n90dBm(15)  }
		MAX-ACCESS			 read-create
		STATUS					 current
		DESCRIPTION			 " -- "
		::=  { plADICfgEntry  15 }


	plADICellSelectQRxlevMin		 OBJECT-TYPE
		SYNTAX					 INTEGER{ rxLevMinMinusDbm140(0),rxLevMinMinusDbm138(1),rxLevMinMinusDbm136(2),rxLevMinMinusDbm134(3),rxLevMinMinusDbm132(4),rxLevMinMinusDbm130(5),rxLevMinMinusDbm128(6),rxLevMinMinusDbm126(7),rxLevMinMinusDbm124(8),rxLevMinMinusDbm122(9),rxLevMinMinusDbm120(10),rxLevMinMinusDbm118(11),rxLevMinMinusDbm116(12),rxLevMinMinusDbm114(13),rxLevMinMinusDbm112(14),rxLevMinMinusDbm110(15),rxLevMinMinusDbm108(16),rxLevMinMinusDbm106(17),rxLevMinMinusDbm104(18),rxLevMinMinusDbm102(19),rxLevMinMinusDbm100(20),rxLevMinMinusDbm98(21),rxLevMinMinusDbm96(22),rxLevMinMinusDbm94(23),rxLevMinMinusDbm92(24),rxLevMinMinusDbm90(25),rxLevMinMinusDbm88(26),rxLevMinMinusDbm86(27),rxLevMinMinusDbm84(28),rxLevMinMinusDbm82(29),rxLevMinMinusDbm80(30),rxLevMinMinusDbm78(31),rxLevMinMinusDbm76(32),rxLevMinMinusDbm74(33),rxLevMinMinusDbm72(34),rxLevMinMinusDbm70(35),rxLevMinMinusDbm68(36),rxLevMinMinusDbm66(37),rxLevMinMinusDbm64(38),rxLevMinMinusDbm62(39),rxLevMinMinusDbm60(40),rxLevMinMinusDbm58(41),rxLevMinMinusDbm56(42),rxLevMinMinusDbm54(43),rxLevMinMinusDbm52(44),rxLevMinMinusDbm50(45),rxLevMinMinusDbm48(46),rxLevMinMinusDbm46(47),rxLevMinMinusDbm44(48)  }
		MAX-ACCESS			 read-create
		STATUS					 current
		DESCRIPTION			 " -- "
		::=  { plADICfgEntry  16 }


	plADICellReselIntraFreqQrxLevMin		 OBJECT-TYPE
		SYNTAX					 INTEGER{ rxLevMinMinusDbm140(0),rxLevMinMinusDbm138(1),rxLevMinMinusDbm136(2),rxLevMinMinusDbm134(3),rxLevMinMinusDbm132(4),rxLevMinMinusDbm130(5),rxLevMinMinusDbm128(6),rxLevMinMinusDbm126(7),rxLevMinMinusDbm124(8),rxLevMinMinusDbm122(9),rxLevMinMinusDbm120(10),rxLevMinMinusDbm118(11),rxLevMinMinusDbm116(12),rxLevMinMinusDbm114(13),rxLevMinMinusDbm112(14),rxLevMinMinusDbm110(15),rxLevMinMinusDbm108(16),rxLevMinMinusDbm106(17),rxLevMinMinusDbm104(18),rxLevMinMinusDbm102(19),rxLevMinMinusDbm100(20),rxLevMinMinusDbm98(21),rxLevMinMinusDbm96(22),rxLevMinMinusDbm94(23),rxLevMinMinusDbm92(24),rxLevMinMinusDbm90(25),rxLevMinMinusDbm88(26),rxLevMinMinusDbm86(27),rxLevMinMinusDbm84(28),rxLevMinMinusDbm82(29),rxLevMinMinusDbm80(30),rxLevMinMinusDbm78(31),rxLevMinMinusDbm76(32),rxLevMinMinusDbm74(33),rxLevMinMinusDbm72(34),rxLevMinMinusDbm70(35),rxLevMinMinusDbm68(36),rxLevMinMinusDbm66(37),rxLevMinMinusDbm64(38),rxLevMinMinusDbm62(39),rxLevMinMinusDbm60(40),rxLevMinMinusDbm58(41),rxLevMinMinusDbm56(42),rxLevMinMinusDbm54(43),rxLevMinMinusDbm52(44),rxLevMinMinusDbm50(45),rxLevMinMinusDbm48(46),rxLevMinMinusDbm46(47),rxLevMinMinusDbm44(48)  }
		MAX-ACCESS			 read-create
		STATUS					 current
		DESCRIPTION			 " -- "
		::=  { plADICfgEntry  17 }


	plADIUlPwrP0NominalPusch		 OBJECT-TYPE
		SYNTAX					 Integer32( -126 .. 24 )
		MAX-ACCESS			 read-create
		STATUS					 current
		DESCRIPTION			 " -- "
		::=  { plADICfgEntry  18 }


	plADIRaPowerRampStep		 OBJECT-TYPE
		SYNTAX					 INTEGER{ dB0(0),dB2(1),dB4(2),dB6(3)  }
		MAX-ACCESS			 read-create
		STATUS					 current
		DESCRIPTION			 " -- "
		::=  { plADICfgEntry  19 }


	plADIRaPreambleTrMax		 OBJECT-TYPE
		SYNTAX					 INTEGER{ n3(0),n4(1),n5(2),n6(3),n7(4),n8(5),n10(6),n20(7),n50(8),n100(9),n200(10)  }
		MAX-ACCESS			 read-create
		STATUS					 current
		DESCRIPTION			 " -- "
		::=  { plADICfgEntry  20 }


	plADIUlPwrMsg3PowerCtrlSwitch		 OBJECT-TYPE
		SYNTAX					 INTEGER{ off(0),on(1)  }
		MAX-ACCESS			 read-create
		STATUS					 current
		DESCRIPTION			 " -- "
		::=  { plADICfgEntry  21 }


	plADIUlPwrDeltaPreambleMsg3		 OBJECT-TYPE
		SYNTAX					 INTEGER{ deltaPreambleMsg3DbN2(0),deltaPreambleMsg3Db0(1),deltaPreambleMsg3Db2(2),deltaPreambleMsg3Db4(3),deltaPreambleMsg3Db6(4),deltaPreambleMsg3Db8(5),deltaPreambleMsg3Db10(6),deltaPreambleMsg3Db12(7)  }
		MAX-ACCESS			 read-create
		STATUS					 current
		DESCRIPTION			 " -- "
		::=  { plADICfgEntry  22 }


	plADIMacTestSwitchInfoUlLimitSrbMcsSwitch		 OBJECT-TYPE
		SYNTAX					 INTEGER{ off(0),on(1)  }
		MAX-ACCESS			 read-create
		STATUS					 current
		DESCRIPTION			 " -- "
		::=  { plADICfgEntry  23 }


	plADIMacTestSwitchInfoUlMaxSrbMcs		 OBJECT-TYPE
		SYNTAX					 Integer32( 0 .. 28 )
		MAX-ACCESS			 read-create
		STATUS					 current
		DESCRIPTION			 " -- "
		::=  { plADICfgEntry  24 }


	plADIMacTestSwitchInfoMcslimitSwitch		 OBJECT-TYPE
		SYNTAX					 INTEGER{ off(0),on(1)  }
		MAX-ACCESS			 read-create
		STATUS					 current
		DESCRIPTION			 " -- "
		::=  { plADICfgEntry  25 }


	plADIMacTestSwitchInfolimitUlMcs		 OBJECT-TYPE
		SYNTAX					 Integer32( 0 .. 28 )
		MAX-ACCESS			 read-create
		STATUS					 current
		DESCRIPTION			 " -- "
		::=  { plADICfgEntry  26 }


	plADIMacTestSwitchInfolimitDlMcs		 OBJECT-TYPE
		SYNTAX					 Integer32( 0 .. 28 )
		MAX-ACCESS			 read-create
		STATUS					 current
		DESCRIPTION			 " -- "
		::=  { plADICfgEntry  27 }


	plRiaCellCfgTable		 OBJECT-TYPE
		SYNTAX					 SEQUENCE  OF	 PlRiaCellCfgEntry
		MAX-ACCESS			 not-accessible
		STATUS					 current
		DESCRIPTION			 " -- "
		::=  { plSwitchNode  6 }


	plRiaCellCfgEntry		 OBJECT-TYPE
		SYNTAX					 PlRiaCellCfgEntry
		MAX-ACCESS			 not-accessible
		STATUS					 current
		DESCRIPTION			 " -- "
		INDEX						{ plRiaCellLcId }
		::=  { plRiaCellCfgTable  1 }


	PlRiaCellCfgEntry		 ::=  SEQUENCE {
		plRiaCellLcId					Integer32,
		plRiaCellRowStatus					RowStatus,
		plRiaCellFuncSwitch					INTEGER,
		plRiaCellSpecialTsCfgSwitch					INTEGER,
		plRiaCellState					INTEGER,
		plRiaCellStateReason					INTEGER,
		plRiaCharactSeqCheckPerNum					INTEGER,
		plRiaCharactSeqSendSwitch					INTEGER,
		plRiaNormalStaCheckPeriod					Integer32
		}


	plRiaCellLcId		 OBJECT-TYPE
		SYNTAX					 Integer32( 0 .. 11 )
		MAX-ACCESS			 not-accessible
		STATUS					 current
		DESCRIPTION			 " -- "
		::=  { plRiaCellCfgEntry  1 }


	plRiaCellRowStatus		 OBJECT-TYPE
		SYNTAX					 RowStatus
		MAX-ACCESS			 read-create
		STATUS					 current
		DESCRIPTION			 " -- "
		::=  { plRiaCellCfgEntry  2 }


	plRiaCellFuncSwitch		 OBJECT-TYPE
		SYNTAX					 INTEGER{ off(0),on(1)  }
		MAX-ACCESS			 read-create
		STATUS					 current
		DESCRIPTION			 " -- "
		::=  { plRiaCellCfgEntry  3 }


	plRiaCellSpecialTsCfgSwitch		 OBJECT-TYPE
		SYNTAX					 INTEGER{ off(0),on(1)  }
		MAX-ACCESS			 read-create
		STATUS					 current
		DESCRIPTION			 " -- "
		::=  { plRiaCellCfgEntry  4 }


	plRiaCellState		 OBJECT-TYPE
		SYNTAX					 INTEGER{ normal(0),aversion(1)  }
		MAX-ACCESS			 read-only
		STATUS					 current
		DESCRIPTION			 " -- "
		::=  { plRiaCellCfgEntry  5 }


	plRiaCellStateReason		 OBJECT-TYPE
		SYNTAX					 INTEGER{ ripLwerCharSeqLst(0),ripHgher(1),detectCharSeq(2)  }
		MAX-ACCESS			 read-only
		STATUS					 current
		DESCRIPTION			 " -- "
		::=  { plRiaCellCfgEntry  6 }


	plRiaCharactSeqCheckPerNum		 OBJECT-TYPE
		SYNTAX					 INTEGER{ n1(0),n2(1),n4(2)  }
		MAX-ACCESS			 read-write
		STATUS					 current
		DESCRIPTION			 " -- "
		::=  { plRiaCellCfgEntry  7 }


	plRiaCharactSeqSendSwitch		 OBJECT-TYPE
		SYNTAX					 INTEGER{ off(0),on(1)  }
		MAX-ACCESS			 read-write
		STATUS					 current
		DESCRIPTION			 " -- "
		::=  { plRiaCellCfgEntry  8 }


	plRiaNormalStaCheckPeriod		 OBJECT-TYPE
		SYNTAX					 Integer32( 0 .. 6 )
		MAX-ACCESS			 read-write
		STATUS					 current
		DESCRIPTION			 " -- "
		::=  { plRiaCellCfgEntry  9 }


	plRiaParaCfg		 OBJECT IDENTIFIER
		::=  { plSwitchNode  7 }


	plRiaPrbThresh		 OBJECT-TYPE
		SYNTAX					 Integer32( 0 .. 120 )
		MAX-ACCESS			 read-write
		STATUS					 current
		DESCRIPTION			 " -- "
		::=  { plRiaParaCfg  1 }


	plRiaPrbThreshOffset		 OBJECT-TYPE
		SYNTAX					 Integer32( 0 .. 20 )
		MAX-ACCESS			 read-write
		STATUS					 current
		DESCRIPTION			 " -- "
		::=  { plRiaParaCfg  2 }


	plRiaInterferenceCheckPeriod		 OBJECT-TYPE
		SYNTAX					 Integer32( 1 .. 10 )
		MAX-ACCESS			 read-write
		STATUS					 current
		DESCRIPTION			 " -- "
		::=  { plRiaParaCfg  3 }


	plRiaInterferenceCheckPeriodNum		 OBJECT-TYPE
		SYNTAX					 Integer32( 1 .. 255 )
		MAX-ACCESS			 read-write
		STATUS					 current
		DESCRIPTION			 " -- "
		::=  { plRiaParaCfg  4 }


	plRiaInterferenceCheckRateThresh		 OBJECT-TYPE
		SYNTAX					 Integer32( 60 .. 100 )
		MAX-ACCESS			 read-write
		STATUS					 current
		DESCRIPTION			 " -- "
		::=  { plRiaParaCfg  5 }


	plRiaCharactSeqCheckPeriod		 OBJECT-TYPE
		SYNTAX					 Integer32( 1 .. 100 )
		MAX-ACCESS			 read-write
		STATUS					 current
		DESCRIPTION			 " -- "
		::=  { plRiaParaCfg  6 }


	plRiaCharactSeqCheckNum		 OBJECT-TYPE
		SYNTAX					 Integer32( 1 .. 4096 )
		MAX-ACCESS			 read-write
		STATUS					 current
		DESCRIPTION			 " -- "
		::=  { plRiaParaCfg  7 }


	plRiaCharactSeqCheckNumUpThresh		 OBJECT-TYPE
		SYNTAX					 Integer32( 1 .. 100 )
		MAX-ACCESS			 read-write
		STATUS					 current
		DESCRIPTION			 " -- "
		::=  { plRiaParaCfg  8 }


	plRiaCharactSeqCheckNumDownThresh		 OBJECT-TYPE
		SYNTAX					 Integer32( 0 .. 100 )
		MAX-ACCESS			 read-write
		STATUS					 current
		DESCRIPTION			 " -- "
		::=  { plRiaParaCfg  9 }


	plRiaCharactSeqCheckThresh		 OBJECT-TYPE
		SYNTAX					 Integer32( 1 .. 100 )
		MAX-ACCESS			 read-write
		STATUS					 current
		DESCRIPTION			 " -- "
		::=  { plRiaParaCfg  10 }


	plRiaLogServerInetAddrType		 OBJECT-TYPE
		SYNTAX					 InetAddressType
		MAX-ACCESS			 read-write
		STATUS					 current
		DESCRIPTION			 " -- "
		::=  { plRiaParaCfg  11 }


	plRiaLogServerInetAddr		 OBJECT-TYPE
		SYNTAX					 InetAddress
		MAX-ACCESS			 read-write
		STATUS					 current
		DESCRIPTION			 " -- "
		::=  { plRiaParaCfg  12 }


	plRiaLogServerDirectory		 OBJECT-TYPE
		SYNTAX					 DisplayString( SIZE ( 1 .. 199 ) )
		MAX-ACCESS			 read-write
		STATUS					 current
		DESCRIPTION			 " -- "
		::=  { plRiaParaCfg  13 }


	plRiaLogServerLoginName		 OBJECT-TYPE
		SYNTAX					 DisplayString( SIZE ( 1 .. 255 ) )
		MAX-ACCESS			 read-write
		STATUS					 current
		DESCRIPTION			 " -- "
		::=  { plRiaParaCfg  14 }


	plRiaLogServerPassward		 OBJECT-TYPE
		SYNTAX					 DisplayString( SIZE ( 1 .. 255 ) )
		MAX-ACCESS			 read-write
		STATUS					 current
		DESCRIPTION			 " -- "
		::=  { plRiaParaCfg  15 }


	plRiaLogRptPeriod		 OBJECT-TYPE
		SYNTAX					 INTEGER{ min15(0),min30(1),min60(2)  }
		MAX-ACCESS			 read-write
		STATUS					 current
		DESCRIPTION			 " -- "
		::=  { plRiaParaCfg  16 }


	plRiaCharactSeqRptSwitch		 OBJECT-TYPE
		SYNTAX					 INTEGER{ off(0),on(1)  }
		MAX-ACCESS			 read-write
		STATUS					 current
		DESCRIPTION			 " -- "
		::=  { plRiaParaCfg  17 }


	plRiaCellRptDataTable		 OBJECT-TYPE
		SYNTAX					 SEQUENCE  OF	 PlRiaCellRptDataEntry
		MAX-ACCESS			 not-accessible
		STATUS					 current
		DESCRIPTION			 " -- "
		::=  { plSwitchNode  8 }


	plRiaCellRptDataEntry		 OBJECT-TYPE
		SYNTAX					 PlRiaCellRptDataEntry
		MAX-ACCESS			 not-accessible
		STATUS					 current
		DESCRIPTION			 " -- "
		INDEX						{ plRiaCellRptLcId,plRiaCharactSeqIDNo }
		::=  { plRiaCellRptDataTable  1 }


	PlRiaCellRptDataEntry		 ::=  SEQUENCE {
		plRiaCellRptLcId					Integer32,
		plRiaCharactSeqIDNo					Integer32,
		plRiaCellRptRowStatus					RowStatus,
		plRiaCharactSeqID					Unsigned32,
		plRiaRptCharactSeqCheckNum					Unsigned32
		}


	plRiaCellRptLcId		 OBJECT-TYPE
		SYNTAX					 Integer32( 0 .. 11 )
		MAX-ACCESS			 not-accessible
		STATUS					 current
		DESCRIPTION			 " -- "
		::=  { plRiaCellRptDataEntry  1 }


	plRiaCharactSeqIDNo		 OBJECT-TYPE
		SYNTAX					 Integer32( 1 .. 4096 )
		MAX-ACCESS			 not-accessible
		STATUS					 current
		DESCRIPTION			 " -- "
		::=  { plRiaCellRptDataEntry  2 }


	plRiaCellRptRowStatus		 OBJECT-TYPE
		SYNTAX					 RowStatus
		MAX-ACCESS			 read-only
		STATUS					 current
		DESCRIPTION			 " -- "
		::=  { plRiaCellRptDataEntry  3 }


	plRiaCharactSeqID		 OBJECT-TYPE
		SYNTAX					 Unsigned32( 0 .. 4294967295 )
		MAX-ACCESS			 read-only
		STATUS					 current
		DESCRIPTION			 " -- "
		::=  { plRiaCellRptDataEntry  4 }


	plRiaRptCharactSeqCheckNum		 OBJECT-TYPE
		SYNTAX					 Unsigned32( 0 .. 4294967295 )
		MAX-ACCESS			 read-only
		STATUS					 current
		DESCRIPTION			 " -- "
		::=  { plRiaCellRptDataEntry  5 }


	anrNotificationNode		 OBJECT IDENTIFIER
		::=  { networkElementPlanCell  13 }


	anrNotifications		 OBJECT IDENTIFIER
		::=  { anrNotificationNode  1 }


	anrNotification		 NOTIFICATION-TYPE
		OBJECTS					 { anrNotiNEType,anrNotiNEID,anrNotiType,anrNotiResult,anrNotiFailReason,anrNotiLcIdx,anrNotiAdjRelationIdx,anrNotiAdjCellNetType,anrNotiAdjCellPlmnMcc,anrNotiAdjCellPlmnMnc,anrNotiAdjCellId,anrNotiTime,anrNotiMmeUeS1apId,anrNotiLocalCellRsrp,anrNotiAdjCellRsrp,anrNotiMeasType,anrNotiMeasEventType }
		STATUS					 current
		DESCRIPTION			 " -- "
		::=  { anrNotifications  1 }


	anrObjects		 OBJECT IDENTIFIER
		::=  { anrNotificationNode  2 }


	anrNotiNEType		 OBJECT-TYPE
		SYNTAX					 INTEGER{ unknown(0),tlb60a(2),emb5116tdlte(3),emb5132tdlte(4),emb5116(5),epc(21),ims(41)  }
		MAX-ACCESS			 accessible-for-notify
		STATUS					 current
		DESCRIPTION			 " -- "
		::=  { anrObjects  1 }


	anrNotiNEID		 OBJECT-TYPE
		SYNTAX					 Unsigned32( 0 .. 4294967295 )
		MAX-ACCESS			 accessible-for-notify
		STATUS					 current
		DESCRIPTION			 " -- "
		::=  { anrObjects  2 }


	anrNotiType		 OBJECT-TYPE
		SYNTAX					 INTEGER{ nrAddReq(0),nrDelReq(1),nrAddDone(2)  }
		MAX-ACCESS			 accessible-for-notify
		STATUS					 current
		DESCRIPTION			 " -- "
		::=  { anrObjects  3 }


	anrNotiResult		 OBJECT-TYPE
		SYNTAX					 INTEGER{ success(0),failure(1)  }
		MAX-ACCESS			 accessible-for-notify
		STATUS					 current
		DESCRIPTION			 " -- "
		::=  { anrObjects  4 }


	anrNotiFailReason		 OBJECT-TYPE
		SYNTAX					 INTEGER{ fullRec(0),invalid(1)  }
		MAX-ACCESS			 accessible-for-notify
		STATUS					 current
		DESCRIPTION			 " -- "
		::=  { anrObjects  5 }


	anrNotiLcIdx		 OBJECT-TYPE
		SYNTAX					 Integer32( 0 .. 23 )
		MAX-ACCESS			 accessible-for-notify
		STATUS					 current
		DESCRIPTION			 " -- "
		::=  { anrObjects  6 }


	anrNotiAdjRelationIdx		 OBJECT-TYPE
		SYNTAX					 Integer32( 0 .. 50 )
		MAX-ACCESS			 accessible-for-notify
		STATUS					 current
		DESCRIPTION			 " -- "
		::=  { anrObjects  7 }


	anrNotiAdjCellNetType		 OBJECT-TYPE
		SYNTAX					 INTEGER{ eutra(0),utraFdd(1),utraTdd(2),geran(3),cdma2000(4)  }
		MAX-ACCESS			 accessible-for-notify
		STATUS					 current
		DESCRIPTION			 " -- "
		::=  { anrObjects  8 }


	anrNotiAdjCellPlmnMcc		 OBJECT-TYPE
		SYNTAX					 MncMccType
		MAX-ACCESS			 accessible-for-notify
		STATUS					 current
		DESCRIPTION			 " -- "
		::=  { anrObjects  9 }


	anrNotiAdjCellPlmnMnc		 OBJECT-TYPE
		SYNTAX					 MncMccType
		MAX-ACCESS			 accessible-for-notify
		STATUS					 current
		DESCRIPTION			 " -- "
		::=  { anrObjects  10 }


	anrNotiAdjCellId		 OBJECT-TYPE
		SYNTAX					 Unsigned32Array
		MAX-ACCESS			 accessible-for-notify
		STATUS					 current
		DESCRIPTION			 " -- "
		::=  { anrObjects  11 }


	anrNotiTime		 OBJECT-TYPE
		SYNTAX					 DateAndTime
		MAX-ACCESS			 accessible-for-notify
		STATUS					 current
		DESCRIPTION			 " -- "
		::=  { anrObjects  12 }


	anrNotiMmeUeS1apId		 OBJECT-TYPE
		SYNTAX					 Unsigned32( 0 .. 4294967295 )
		MAX-ACCESS			 accessible-for-notify
		STATUS					 current
		DESCRIPTION			 " -- "
		::=  { anrObjects  13 }


	anrNotiLocalCellRsrp		 OBJECT-TYPE
		SYNTAX					 Unsigned32( 0 .. 97 )
		MAX-ACCESS			 accessible-for-notify
		STATUS					 current
		DESCRIPTION			 " -- "
		::=  { anrObjects  14 }


	anrNotiAdjCellRsrp		 OBJECT-TYPE
		SYNTAX					 Unsigned32( 0 .. 97 )
		MAX-ACCESS			 accessible-for-notify
		STATUS					 current
		DESCRIPTION			 " -- "
		::=  { anrObjects  15 }


	anrNotiMeasType		 OBJECT-TYPE
		SYNTAX					 INTEGER{ period(1),event(2)  }
		MAX-ACCESS			 accessible-for-notify
		STATUS					 current
		DESCRIPTION			 " -- "
		::=  { anrObjects  16 }


	anrNotiMeasEventType		 OBJECT-TYPE
		SYNTAX					 INTEGER{ a3(3),a4(4),a5(5)  }
		MAX-ACCESS			 accessible-for-notify
		STATUS					 current
		DESCRIPTION			 " -- "
		::=  { anrObjects  17 }


	mroNotificationNode		 OBJECT IDENTIFIER
		::=  { networkElementPlanCell  14 }


	mroNotifications		 OBJECT IDENTIFIER
		::=  { mroNotificationNode  1 }


	mroNotification		 NOTIFICATION-TYPE
		OBJECTS					 { mroNotiNEType,mroNotiNEID,mroNotiType,mroNotiCellId,mroNotiAdjCellPlmnMcc,mroNotiAdjCellPlmnMnc,mroNotiAdjCellId,mroNotiTime,mroNotiAdjCellPhyId,mroNotiAdjCellCenterFreq }
		STATUS					 current
		DESCRIPTION			 " -- "
		::=  { mroNotifications  1 }


	mroObjects		 OBJECT IDENTIFIER
		::=  { mroNotificationNode  2 }


	mroNotiNEType		 OBJECT-TYPE
		SYNTAX					 INTEGER{ unknown(0),tlb60a(2),emb5116tdlte(3),emb5132tdlte(4),emb5116(5),epc(21),ims(41)  }
		MAX-ACCESS			 accessible-for-notify
		STATUS					 current
		DESCRIPTION			 " -- "
		::=  { mroObjects  1 }


	mroNotiNEID		 OBJECT-TYPE
		SYNTAX					 Unsigned32( 0 .. 4294967295 )
		MAX-ACCESS			 accessible-for-notify
		STATUS					 current
		DESCRIPTION			 " -- "
		::=  { mroObjects  2 }


	mroNotiType		 OBJECT-TYPE
		SYNTAX					 INTEGER{ hoTooEarly(0),hoTooLate(1),hoToWrong(2),hoPingPang(3)  }
		MAX-ACCESS			 accessible-for-notify
		STATUS					 current
		DESCRIPTION			 " -- "
		::=  { mroObjects  3 }


	mroNotiCellId		 OBJECT-TYPE
		SYNTAX					 Integer32( 0 .. 23 )
		MAX-ACCESS			 accessible-for-notify
		STATUS					 current
		DESCRIPTION			 " -- "
		::=  { mroObjects  4 }


	mroNotiAdjCellPlmnMcc		 OBJECT-TYPE
		SYNTAX					 MncMccType
		MAX-ACCESS			 accessible-for-notify
		STATUS					 current
		DESCRIPTION			 " -- "
		::=  { mroObjects  5 }


	mroNotiAdjCellPlmnMnc		 OBJECT-TYPE
		SYNTAX					 MncMccType
		MAX-ACCESS			 accessible-for-notify
		STATUS					 current
		DESCRIPTION			 " -- "
		::=  { mroObjects  6 }


	mroNotiAdjCellId		 OBJECT-TYPE
		SYNTAX					 Unsigned32Array
		MAX-ACCESS			 accessible-for-notify
		STATUS					 current
		DESCRIPTION			 " -- "
		::=  { mroObjects  7 }


	mroNotiTime		 OBJECT-TYPE
		SYNTAX					 DateAndTime
		MAX-ACCESS			 accessible-for-notify
		STATUS					 current
		DESCRIPTION			 " -- "
		::=  { mroObjects  8 }


	mroNotiAdjCellPhyId		 OBJECT-TYPE
		SYNTAX					 Unsigned32Array
		MAX-ACCESS			 accessible-for-notify
		STATUS					 current
		DESCRIPTION			 " -- "
		::=  { mroObjects  9 }


	mroNotiAdjCellCenterFreq		 OBJECT-TYPE
		SYNTAX					 Unsigned32Array
		MAX-ACCESS			 accessible-for-notify
		STATUS					 current
		DESCRIPTION			 " -- "
		::=  { mroObjects  10 }


	fcNotificationNode		 OBJECT IDENTIFIER
		::=  { networkElementPlanCell  15 }


	fcNotifications		 OBJECT IDENTIFIER
		::=  { fcNotificationNode  1 }


	fcNotification		 NOTIFICATION-TYPE
		OBJECTS					 { fcNotiNEType,fcNotiNEID,fcNotiType,fcNotiCellId,fcNotiAdjCellPlmnMcc,fcNotiAdjCellPlmnMnc,fcNotiAdjCellId,fcNotiAdjEnbGlobalId,fcNotiTime }
		STATUS					 current
		DESCRIPTION			 " -- "
		::=  { fcNotifications  1 }


	fcObjects		 OBJECT IDENTIFIER
		::=  { fcNotificationNode  2 }


	fcNotiNEType		 OBJECT-TYPE
		SYNTAX					 INTEGER{ unknown(0),tlb60a(2),emb5116tdlte(3),emb5132tdlte(4),emb5116(5),epc(21),ims(41)  }
		MAX-ACCESS			 accessible-for-notify
		STATUS					 current
		DESCRIPTION			 " -- "
		::=  { fcObjects  1 }


	fcNotiNEID		 OBJECT-TYPE
		SYNTAX					 Unsigned32( 0 .. 4294967295 )
		MAX-ACCESS			 accessible-for-notify
		STATUS					 current
		DESCRIPTION			 " -- "
		::=  { fcObjects  2 }


	fcNotiType		 OBJECT-TYPE
		SYNTAX					 INTEGER{ lbc40fc(0)  }
		MAX-ACCESS			 accessible-for-notify
		STATUS					 current
		DESCRIPTION			 " -- "
		::=  { fcObjects  3 }


	fcNotiCellId		 OBJECT-TYPE
		SYNTAX					 Integer32( 0 .. 23 )
		MAX-ACCESS			 accessible-for-notify
		STATUS					 current
		DESCRIPTION			 " -- "
		::=  { fcObjects  4 }


	fcNotiAdjCellPlmnMcc		 OBJECT-TYPE
		SYNTAX					 MncMccType
		MAX-ACCESS			 accessible-for-notify
		STATUS					 current
		DESCRIPTION			 " -- "
		::=  { fcObjects  5 }


	fcNotiAdjCellPlmnMnc		 OBJECT-TYPE
		SYNTAX					 MncMccType
		MAX-ACCESS			 accessible-for-notify
		STATUS					 current
		DESCRIPTION			 " -- "
		::=  { fcObjects  6 }


	fcNotiAdjCellId		 OBJECT-TYPE
		SYNTAX					 Unsigned32Array
		MAX-ACCESS			 accessible-for-notify
		STATUS					 current
		DESCRIPTION			 " -- "
		::=  { fcObjects  7 }


	fcNotiAdjEnbGlobalId		 OBJECT-TYPE
		SYNTAX					 Unsigned32( 0 .. 1048575 )
		MAX-ACCESS			 accessible-for-notify
		STATUS					 current
		DESCRIPTION			 " -- "
		::=  { fcObjects  8 }


	fcNotiTime		 OBJECT-TYPE
		SYNTAX					 DateAndTime
		MAX-ACCESS			 accessible-for-notify
		STATUS					 current
		DESCRIPTION			 " -- "
		::=  { fcObjects  9 }


	cellCdma2000Para		 OBJECT IDENTIFIER
		::=  { networkElementPlanCell  16 }


	cellCdma2000ParaTable		 OBJECT-TYPE
		SYNTAX					 SEQUENCE  OF	 CellCdma2000ParaEntry
		MAX-ACCESS			 not-accessible
		STATUS					 current
		DESCRIPTION			 " -- "
		::=  { cellCdma2000Para  1 }


	cellCdma2000ParaEntry		 OBJECT-TYPE
		SYNTAX					 CellCdma2000ParaEntry
		MAX-ACCESS			 not-accessible
		STATUS					 current
		DESCRIPTION			 " -- "
		INDEX						{ cellCdma2000ParaLcId }
		::=  { cellCdma2000ParaTable  1 }


	CellCdma2000ParaEntry		 ::=  SEQUENCE {
		cellCdma2000ParaLcId					Integer32,
		cellCdma2000ParaRowStatus					RowStatus,
		cellCdma2000ParaSystemTimeInfoFlag					INTEGER,
		cellCdma2000ParaSystemTimeSynChr					INTEGER,
		cellCdma2000ParaSerWindowSize					Integer32,
		cellCdma2000ParaHRPDFlag					INTEGER,
		cellCdma2000ParaPreRegZoneId1					Integer32,
		cellCdma2000ParaSecondPreRegZoneIdFlag					INTEGER,
		cellCdma2000ParaPreRegZoneId2					Integer32,
		cellCdma2000ParaPreRegZoneId3					Integer32,
		cellCdma2000ParaPreRegAllowed					INTEGER,
		cellCdma2000ParaCdma1XrttCsfbRegCfgInd					INTEGER,
		cellCdma2000ParaCdma1XrttCsfbRegSid					Integer32,
		cellCdma2000ParaCdma1XrttCsfbRegNid					Integer32,
		cellCdma2000ParaCdma1XrttCsfbRegMultiSidInd					INTEGER,
		cellCdma2000ParaCdma1XrttCsfbRegMultiNidInd					INTEGER,
		cellCdma2000ParaCdma1XrttCsfbRegHomeRegInd					INTEGER,
		cellCdma2000ParaCdma1XrttCsfbRegFrgnSidRegInd					INTEGER,
		cellCdma2000ParaCdma1XrttCsfbRegFrgnNidRegInd					INTEGER,
		cellCdma2000ParaCdma1XrttCsfbRegParamRegInd					INTEGER,
		cellCdma2000ParaCdma1XrttCsfbRegPowerUpRegInd					INTEGER,
		cellCdma2000ParaCdma1XrttCsfbRegRegPeriod					Integer32,
		cellCdma2000ParaCdma1XrttCsfbRegRegZone					Integer32,
		cellCdma2000ParaCdma1XrttCsfbRegTotalZone					Integer32,
		cellCdma2000ParaCdma1XrttCsfbRegZoneTimer					Integer32,
		cellCdma2000ParaCsfbRegPwrDownRegCfgInd					INTEGER
		}


	cellCdma2000ParaLcId		 OBJECT-TYPE
		SYNTAX					 Integer32( 0 .. 23 )
		MAX-ACCESS			 not-accessible
		STATUS					 current
		DESCRIPTION			 " -- "
		::=  { cellCdma2000ParaEntry  1 }


	cellCdma2000ParaRowStatus		 OBJECT-TYPE
		SYNTAX					 RowStatus
		MAX-ACCESS			 read-create
		STATUS					 current
		DESCRIPTION			 " -- "
		::=  { cellCdma2000ParaEntry  2 }


	cellCdma2000ParaSystemTimeInfoFlag		 OBJECT-TYPE
		SYNTAX					 INTEGER{ false(0),true(1)  }
		MAX-ACCESS			 read-create
		STATUS					 current
		DESCRIPTION			 " -- "
		::=  { cellCdma2000ParaEntry  3 }


	cellCdma2000ParaSystemTimeSynChr		 OBJECT-TYPE
		SYNTAX					 INTEGER{ false(0),true(1)  }
		MAX-ACCESS			 read-create
		STATUS					 current
		DESCRIPTION			 " -- "
		::=  { cellCdma2000ParaEntry  4 }


	cellCdma2000ParaSerWindowSize		 OBJECT-TYPE
		SYNTAX					 Integer32( 0 .. 15|255 )
		MAX-ACCESS			 read-create
		STATUS					 current
		DESCRIPTION			 " -- "
		::=  { cellCdma2000ParaEntry  5 }


	cellCdma2000ParaHRPDFlag		 OBJECT-TYPE
		SYNTAX					 INTEGER{ false(0),true(1)  }
		MAX-ACCESS			 read-create
		STATUS					 current
		DESCRIPTION			 " -- "
		::=  { cellCdma2000ParaEntry  6 }


	cellCdma2000ParaPreRegZoneId1		 OBJECT-TYPE
		SYNTAX					 Integer32( 0 .. 255 )
		MAX-ACCESS			 read-create
		STATUS					 current
		DESCRIPTION			 " -- "
		::=  { cellCdma2000ParaEntry  7 }


	cellCdma2000ParaSecondPreRegZoneIdFlag		 OBJECT-TYPE
		SYNTAX					 INTEGER{ false(0),true(1)  }
		MAX-ACCESS			 read-create
		STATUS					 current
		DESCRIPTION			 " -- "
		::=  { cellCdma2000ParaEntry  8 }


	cellCdma2000ParaPreRegZoneId2		 OBJECT-TYPE
		SYNTAX					 Integer32( 0 .. 255|65535 )
		MAX-ACCESS			 read-create
		STATUS					 current
		DESCRIPTION			 " -- "
		::=  { cellCdma2000ParaEntry  9 }


	cellCdma2000ParaPreRegZoneId3		 OBJECT-TYPE
		SYNTAX					 Integer32( 0 .. 255|65535 )
		MAX-ACCESS			 read-create
		STATUS					 current
		DESCRIPTION			 " -- "
		::=  { cellCdma2000ParaEntry  10 }


	cellCdma2000ParaPreRegAllowed		 OBJECT-TYPE
		SYNTAX					 INTEGER{ false(0),true(1)  }
		MAX-ACCESS			 read-create
		STATUS					 current
		DESCRIPTION			 " -- "
		::=  { cellCdma2000ParaEntry  11 }


	cellCdma2000ParaCdma1XrttCsfbRegCfgInd		 OBJECT-TYPE
		SYNTAX					 INTEGER{ false(0),true(1)  }
		MAX-ACCESS			 read-create
		STATUS					 current
		DESCRIPTION			 " -- "
		::=  { cellCdma2000ParaEntry  12 }


	cellCdma2000ParaCdma1XrttCsfbRegSid		 OBJECT-TYPE
		SYNTAX					 Integer32( 0 .. 32767 )
		MAX-ACCESS			 read-create
		STATUS					 current
		DESCRIPTION			 " -- "
		::=  { cellCdma2000ParaEntry  13 }


	cellCdma2000ParaCdma1XrttCsfbRegNid		 OBJECT-TYPE
		SYNTAX					 Integer32( 0 .. 65535 )
		MAX-ACCESS			 read-create
		STATUS					 current
		DESCRIPTION			 " -- "
		::=  { cellCdma2000ParaEntry  14 }


	cellCdma2000ParaCdma1XrttCsfbRegMultiSidInd		 OBJECT-TYPE
		SYNTAX					 INTEGER{ false(0),true(1)  }
		MAX-ACCESS			 read-create
		STATUS					 current
		DESCRIPTION			 " -- "
		::=  { cellCdma2000ParaEntry  15 }


	cellCdma2000ParaCdma1XrttCsfbRegMultiNidInd		 OBJECT-TYPE
		SYNTAX					 INTEGER{ false(0),true(1)  }
		MAX-ACCESS			 read-create
		STATUS					 current
		DESCRIPTION			 " -- "
		::=  { cellCdma2000ParaEntry  16 }


	cellCdma2000ParaCdma1XrttCsfbRegHomeRegInd		 OBJECT-TYPE
		SYNTAX					 INTEGER{ false(0),true(1)  }
		MAX-ACCESS			 read-create
		STATUS					 current
		DESCRIPTION			 " -- "
		::=  { cellCdma2000ParaEntry  17 }


	cellCdma2000ParaCdma1XrttCsfbRegFrgnSidRegInd		 OBJECT-TYPE
		SYNTAX					 INTEGER{ false(0),true(1)  }
		MAX-ACCESS			 read-create
		STATUS					 current
		DESCRIPTION			 " -- "
		::=  { cellCdma2000ParaEntry  18 }


	cellCdma2000ParaCdma1XrttCsfbRegFrgnNidRegInd		 OBJECT-TYPE
		SYNTAX					 INTEGER{ false(0),true(1)  }
		MAX-ACCESS			 read-create
		STATUS					 current
		DESCRIPTION			 " -- "
		::=  { cellCdma2000ParaEntry  19 }


	cellCdma2000ParaCdma1XrttCsfbRegParamRegInd		 OBJECT-TYPE
		SYNTAX					 INTEGER{ false(0),true(1)  }
		MAX-ACCESS			 read-create
		STATUS					 current
		DESCRIPTION			 " -- "
		::=  { cellCdma2000ParaEntry  20 }


	cellCdma2000ParaCdma1XrttCsfbRegPowerUpRegInd		 OBJECT-TYPE
		SYNTAX					 INTEGER{ false(0),true(1)  }
		MAX-ACCESS			 read-create
		STATUS					 current
		DESCRIPTION			 " -- "
		::=  { cellCdma2000ParaEntry  21 }


	cellCdma2000ParaCdma1XrttCsfbRegRegPeriod		 OBJECT-TYPE
		SYNTAX					 Integer32( 0 .. 127 )
		MAX-ACCESS			 read-create
		STATUS					 current
		DESCRIPTION			 " -- "
		::=  { cellCdma2000ParaEntry  22 }


	cellCdma2000ParaCdma1XrttCsfbRegRegZone		 OBJECT-TYPE
		SYNTAX					 Integer32( 0 .. 4095 )
		MAX-ACCESS			 read-create
		STATUS					 current
		DESCRIPTION			 " -- "
		::=  { cellCdma2000ParaEntry  23 }


	cellCdma2000ParaCdma1XrttCsfbRegTotalZone		 OBJECT-TYPE
		SYNTAX					 Integer32( 0 .. 7 )
		MAX-ACCESS			 read-create
		STATUS					 current
		DESCRIPTION			 " -- "
		::=  { cellCdma2000ParaEntry  24 }


	cellCdma2000ParaCdma1XrttCsfbRegZoneTimer		 OBJECT-TYPE
		SYNTAX					 Integer32( 0 .. 7 )
		MAX-ACCESS			 read-create
		STATUS					 current
		DESCRIPTION			 " -- "
		::=  { cellCdma2000ParaEntry  25 }


	cellCdma2000ParaCsfbRegPwrDownRegCfgInd		 OBJECT-TYPE
		SYNTAX					 INTEGER{ false(0),true(1)  }
		MAX-ACCESS			 read-create
		STATUS					 current
		DESCRIPTION			 " -- "
		::=  { cellCdma2000ParaEntry  26 }


	multiBand		 OBJECT IDENTIFIER
		::=  { networkElementPlanCell  17 }


	multiBandTable		 OBJECT-TYPE
		SYNTAX					 SEQUENCE  OF	 MultiBandEntry
		MAX-ACCESS			 not-accessible
		STATUS					 current
		DESCRIPTION			 " -- "
		::=  { multiBand  1 }


	multiBandEntry		 OBJECT-TYPE
		SYNTAX					 MultiBandEntry
		MAX-ACCESS			 not-accessible
		STATUS					 current
		DESCRIPTION			 " -- "
		INDEX						{ multiBandLcId }
		::=  { multiBandTable  1 }


	MultiBandEntry		 ::=  SEQUENCE {
		multiBandLcId					Integer32,
		multiBandRowStatus					RowStatus,
		multiBandAddtionlSpecEmis1					Integer32,
		multiBandEnhanceSwitch					INTEGER
		}


	multiBandLcId		 OBJECT-TYPE
		SYNTAX					 Integer32( 0 .. 23 )
		MAX-ACCESS			 not-accessible
		STATUS					 current
		DESCRIPTION			 " -- "
		::=  { multiBandEntry  1 }


	multiBandRowStatus		 OBJECT-TYPE
		SYNTAX					 RowStatus
		MAX-ACCESS			 read-create
		STATUS					 current
		DESCRIPTION			 " -- "
		::=  { multiBandEntry  2 }


	multiBandAddtionlSpecEmis1		 OBJECT-TYPE
		SYNTAX					 Integer32( 1 .. 32 )
		MAX-ACCESS			 read-create
		STATUS					 current
		DESCRIPTION			 " -- "
		::=  { multiBandEntry  5 }


	multiBandEnhanceSwitch		 OBJECT-TYPE
		SYNTAX					 INTEGER{ off(0),on(1)  }
		MAX-ACCESS			 read-create
		STATUS					 current
		DESCRIPTION			 " -- "
		::=  { multiBandEntry  6 }


	adjCellECGI		 OBJECT IDENTIFIER
		::=  { networkElementPlanCell  18 }


	adjCellECGITable		 OBJECT-TYPE
		SYNTAX					 SEQUENCE  OF	 AdjCellECGIEntry
		MAX-ACCESS			 not-accessible
		STATUS					 current
		DESCRIPTION			 " -- "
		::=  { adjCellECGI  1 }


	adjCellECGIEntry		 OBJECT-TYPE
		SYNTAX					 AdjCellECGIEntry
		MAX-ACCESS			 not-accessible
		STATUS					 current
		DESCRIPTION			 " -- "
		INDEX						{ adjCellECGILcId }
		::=  { adjCellECGITable  1 }


	AdjCellECGIEntry		 ::=  SEQUENCE {
		adjCellECGILcId					Integer32,
		adjCellECGIRowStatus					RowStatus,
		adjCellECGIMeasSwitch					INTEGER,
		adjCellECGITimePerUE					Integer32,
		adjCellECGIUENum					Integer32
		}


	adjCellECGILcId		 OBJECT-TYPE
		SYNTAX					 Integer32( 0 .. 23 )
		MAX-ACCESS			 not-accessible
		STATUS					 current
		DESCRIPTION			 " -- "
		::=  { adjCellECGIEntry  1 }


	adjCellECGIRowStatus		 OBJECT-TYPE
		SYNTAX					 RowStatus
		MAX-ACCESS			 read-create
		STATUS					 current
		DESCRIPTION			 " -- "
		::=  { adjCellECGIEntry  2 }


	adjCellECGIMeasSwitch		 OBJECT-TYPE
		SYNTAX					 INTEGER{ off(0),on(1)  }
		MAX-ACCESS			 read-write
		STATUS					 current
		DESCRIPTION			 " -- "
		::=  { adjCellECGIEntry  3 }


	adjCellECGITimePerUE		 OBJECT-TYPE
		SYNTAX					 Integer32( 1 .. 10 )
		MAX-ACCESS			 read-write
		STATUS					 current
		DESCRIPTION			 " -- "
		::=  { adjCellECGIEntry  4 }


	adjCellECGIUENum		 OBJECT-TYPE
		SYNTAX					 Integer32( 1 .. 1200 )
		MAX-ACCESS			 read-write
		STATUS					 current
		DESCRIPTION			 " -- "
		::=  { adjCellECGIEntry  5 }


	mlbNotificationNode		 OBJECT IDENTIFIER
		::=  { networkElementPlanCell  19 }


	mlbNotifications		 OBJECT IDENTIFIER
		::=  { mlbNotificationNode  1 }


	mlbNotification		 NOTIFICATION-TYPE
		OBJECTS					 { mlbNotiNEType,mlbNotiNEID,mlbNotiType,mlbNotiCellType,mlbNotiCellId,mlbNotiAdjCellId,mlbNotiOcnAdjust,mlbEventNotiTime }
		STATUS					 current
		DESCRIPTION			 " -- "
		::=  { mlbNotifications  1 }


	mlbObjects		 OBJECT IDENTIFIER
		::=  { mlbNotificationNode  2 }


	mlbNotiNEType		 OBJECT-TYPE
		SYNTAX					 INTEGER{ unknown(0),tlb60a(2),emb5116tdlte(3),emb5132tdlte(4),emb5116(5),epc(21),ims(41)  }
		MAX-ACCESS			 accessible-for-notify
		STATUS					 current
		DESCRIPTION			 " -- "
		::=  { mlbObjects  1 }


	mlbNotiNEID		 OBJECT-TYPE
		SYNTAX					 Unsigned32( 0 .. 4294967295 )
		MAX-ACCESS			 accessible-for-notify
		STATUS					 current
		DESCRIPTION			 " -- "
		::=  { mlbObjects  2 }


	mlbNotiType		 OBJECT-TYPE
		SYNTAX					 INTEGER{ fail(0),reSelect(1),back(2),stop(3)  }
		MAX-ACCESS			 accessible-for-notify
		STATUS					 current
		DESCRIPTION			 " -- "
		::=  { mlbObjects  3 }


	mlbNotiCellType		 OBJECT-TYPE
		SYNTAX					 INTEGER{ srcCell(0),goalCell(1)  }
		MAX-ACCESS			 accessible-for-notify
		STATUS					 current
		DESCRIPTION			 " -- "
		::=  { mlbObjects  4 }


	mlbNotiCellId		 OBJECT-TYPE
		SYNTAX					 Integer32( 0 .. 11 )
		MAX-ACCESS			 accessible-for-notify
		STATUS					 current
		DESCRIPTION			 " -- "
		::=  { mlbObjects  5 }


	mlbNotiAdjCellId		 OBJECT-TYPE
		SYNTAX					 Integer32( 1 .. 256 )
		MAX-ACCESS			 accessible-for-notify
		STATUS					 current
		DESCRIPTION			 " -- "
		::=  { mlbObjects  6 }


	mlbNotiOcnAdjust		 OBJECT-TYPE
		SYNTAX					 Integer32( -20 .. 20 )
		MAX-ACCESS			 accessible-for-notify
		STATUS					 current
		DESCRIPTION			 " -- "
		::=  { mlbObjects  7 }


	mlbEventNotiTime		 OBJECT-TYPE
		SYNTAX					 DateAndTime
		MAX-ACCESS			 accessible-for-notify
		STATUS					 current
		DESCRIPTION			 " -- "
		::=  { mlbObjects  8 }


	staticMeasurement		 OBJECT IDENTIFIER
		::=  { networkElementLayoutPlan  6 }


	eNBMeasComCfg		 OBJECT IDENTIFIER
		::=  { staticMeasurement  1 }


	eNBMeasComPeriodicForPrbNum		 OBJECT-TYPE
		SYNTAX					 Unsigned32( 0 .. 65535 )
		MAX-ACCESS			 read-write
		STATUS					 current
		DESCRIPTION			 " -- "
		::=  { eNBMeasComCfg  1 }


	eNBMeasComFilterCoeffForPrbNum		 OBJECT-TYPE
		SYNTAX					 INTEGER{ val0(0),val1(1),val2(2),val3(3),val4(4),val5(5),val6(6),val7(7),val8(8),val9(9),val11(10),val13(11),val15(12),val17(13),val19(14)  }
		MAX-ACCESS			 read-write
		STATUS					 current
		DESCRIPTION			 " -- "
		::=  { eNBMeasComCfg  2 }


	eNBMeasComPeriodicForRate		 OBJECT-TYPE
		SYNTAX					 Unsigned32( 0 .. 65535 )
		MAX-ACCESS			 read-write
		STATUS					 current
		DESCRIPTION			 " -- "
		::=  { eNBMeasComCfg  3 }


	eNBMeasComFilterCoeffForRate		 OBJECT-TYPE
		SYNTAX					 INTEGER{ val0(0),val1(1),val2(2),val3(3),val4(4),val5(5),val6(6),val7(7),val8(8),val9(9),val11(10),val13(11),val15(12),val17(13),val19(14)  }
		MAX-ACCESS			 read-write
		STATUS					 current
		DESCRIPTION			 " -- "
		::=  { eNBMeasComCfg  4 }


	eNBMeasComPeriodicForIot		 OBJECT-TYPE
		SYNTAX					 Unsigned32( 0 .. 65535 )
		MAX-ACCESS			 read-write
		STATUS					 current
		DESCRIPTION			 " -- "
		::=  { eNBMeasComCfg  5 }


	eNBMeasComFilterCoeffForIot		 OBJECT-TYPE
		SYNTAX					 INTEGER{ val0(0),val1(1),val2(2),val3(3),val4(4),val5(5),val6(6),val7(7),val8(8),val9(9),val11(10),val13(11),val15(12),val17(13),val19(14)  }
		MAX-ACCESS			 read-write
		STATUS					 current
		DESCRIPTION			 " -- "
		::=  { eNBMeasComCfg  6 }


	timer		 OBJECT IDENTIFIER
		::=  { networkElementLayoutPlan  7 }


	protocolTimerInfo		 OBJECT IDENTIFIER
		::=  { timer  1 }


	timerS1RLOCpre		 OBJECT-TYPE
		SYNTAX					 Unsigned32( 0 .. 30000 )
		MAX-ACCESS			 read-write
		STATUS					 current
		DESCRIPTION			 " -- "
		::=  { protocolTimerInfo  1 }


	timerS1RLOCoverall		 OBJECT-TYPE
		SYNTAX					 Unsigned32( 0 .. 30000 )
		MAX-ACCESS			 read-write
		STATUS					 current
		DESCRIPTION			 " -- "
		::=  { protocolTimerInfo  2 }


	timerS1TimeToWait		 OBJECT-TYPE
		SYNTAX					 INTEGER{ s1(0),s2(1),s5(2),s10(3),s20(4),s60(5)  }
		MAX-ACCESS			 read-write
		STATUS					 current
		DESCRIPTION			 " -- "
		::=  { protocolTimerInfo  3 }


	timerX2RLOCpre		 OBJECT-TYPE
		SYNTAX					 Unsigned32( 0 .. 30000 )
		MAX-ACCESS			 read-write
		STATUS					 current
		DESCRIPTION			 " -- "
		::=  { protocolTimerInfo  4 }


	timerX2RLOCoverall		 OBJECT-TYPE
		SYNTAX					 Unsigned32( 0 .. 30000 )
		MAX-ACCESS			 read-write
		STATUS					 current
		DESCRIPTION			 " -- "
		::=  { protocolTimerInfo  5 }


	timerX2TimeToWait		 OBJECT-TYPE
		SYNTAX					 INTEGER{ s1(0),s2(1),s5(2),s10(3),s20(4),s60(5)  }
		MAX-ACCESS			 read-write
		STATUS					 current
		DESCRIPTION			 " -- "
		::=  { protocolTimerInfo  6 }


	eNBTimerInfo		 OBJECT IDENTIFIER
		::=  { timer  2 }


	timerRrcConnCmplt		 OBJECT-TYPE
		SYNTAX					 Integer32( 0 .. 65535 )
		MAX-ACCESS			 read-write
		STATUS					 current
		DESCRIPTION			 " -- "
		::=  { eNBTimerInfo  1 }


	timerUeCapaRsp		 OBJECT-TYPE
		SYNTAX					 Integer32( 0 .. 65535 )
		MAX-ACCESS			 read-write
		STATUS					 current
		DESCRIPTION			 " -- "
		::=  { eNBTimerInfo  2 }


	timerRrcRecfgCmplt		 OBJECT-TYPE
		SYNTAX					 Integer32( 0 .. 65535 )
		MAX-ACCESS			 read-write
		STATUS					 current
		DESCRIPTION			 " -- "
		::=  { eNBTimerInfo  3 }


	timerRrcReestablishCmplt		 OBJECT-TYPE
		SYNTAX					 Integer32( 0 .. 65535 )
		MAX-ACCESS			 read-write
		STATUS					 current
		DESCRIPTION			 " -- "
		::=  { eNBTimerInfo  4 }


	timerWaitRrcReestablishReq		 OBJECT-TYPE
		SYNTAX					 Integer32( 0 .. 65535 )
		MAX-ACCESS			 read-write
		STATUS					 current
		DESCRIPTION			 " -- "
		::=  { eNBTimerInfo  5 }


	timerWaitSecurityActCmplt		 OBJECT-TYPE
		SYNTAX					 Integer32( 0 .. 65535 )
		MAX-ACCESS			 read-write
		STATUS					 current
		DESCRIPTION			 " -- "
		::=  { eNBTimerInfo  6 }


	timerWaitCountCheckRsp		 OBJECT-TYPE
		SYNTAX					 Integer32( 0 .. 65535 )
		MAX-ACCESS			 read-write
		STATUS					 current
		DESCRIPTION			 " -- "
		::=  { eNBTimerInfo  7 }


	timerRrcConnRel		 OBJECT-TYPE
		SYNTAX					 Integer32( 0 .. 65535 )
		MAX-ACCESS			 read-write
		STATUS					 current
		DESCRIPTION			 " -- "
		::=  { eNBTimerInfo  8 }


	timerAnrRptEutraTimer		 OBJECT-TYPE
		SYNTAX					 Unsigned32( 1000 .. 65535 )
		MAX-ACCESS			 read-write
		STATUS					 current
		DESCRIPTION			 " -- "
		::=  { eNBTimerInfo  9 }


	timerAnrRptInterRatTimer		 OBJECT-TYPE
		SYNTAX					 Unsigned32( 1000 .. 65535 )
		MAX-ACCESS			 read-write
		STATUS					 current
		DESCRIPTION			 " -- "
		::=  { eNBTimerInfo  10 }


	timerAnrRemTimer		 OBJECT-TYPE
		SYNTAX					 Unsigned32( 0 .. 4294967295 )
		MAX-ACCESS			 read-write
		STATUS					 current
		DESCRIPTION			 " -- "
		::=  { eNBTimerInfo  11 }


	timerAnrUtraDetectTimer		 OBJECT-TYPE
		SYNTAX					 Unsigned32( 0 .. 65535 )
		MAX-ACCESS			 read-write
		STATUS					 current
		DESCRIPTION			 " -- "
		::=  { eNBTimerInfo  12 }


	timerAnrCdma2000DetectTimer		 OBJECT-TYPE
		SYNTAX					 Unsigned32( 0 .. 65535 )
		MAX-ACCESS			 read-write
		STATUS					 current
		DESCRIPTION			 " -- "
		::=  { eNBTimerInfo  13 }


	timerWaitOtherSfuRsp		 OBJECT-TYPE
		SYNTAX					 Unsigned32( 0 .. 65535 )
		MAX-ACCESS			 read-write
		STATUS					 current
		DESCRIPTION			 " -- "
		::=  { eNBTimerInfo  14 }


	timerWaitS1Rsp		 OBJECT-TYPE
		SYNTAX					 Unsigned32( 0 .. 30000 )
		MAX-ACCESS			 read-write
		STATUS					 current
		DESCRIPTION			 " -- "
		::=  { eNBTimerInfo  15 }


	timerWaitX2Rsp		 OBJECT-TYPE
		SYNTAX					 Unsigned32( 0 .. 30000 )
		MAX-ACCESS			 read-write
		STATUS					 current
		DESCRIPTION			 " -- "
		::=  { eNBTimerInfo  16 }


	timerWaitEndMarker		 OBJECT-TYPE
		SYNTAX					 Unsigned32( 50 .. 200 )
		MAX-ACCESS			 read-write
		STATUS					 current
		DESCRIPTION			 " -- "
		::=  { eNBTimerInfo  17 }


	timerHcPrepare		 OBJECT-TYPE
		SYNTAX					 Unsigned32( 0 .. 65535 )
		MAX-ACCESS			 read-write
		STATUS					 current
		DESCRIPTION			 " -- "
		::=  { eNBTimerInfo  18 }


	timerHcSrcHandover		 OBJECT-TYPE
		SYNTAX					 Unsigned32( 0 .. 65535 )
		MAX-ACCESS			 read-write
		STATUS					 current
		DESCRIPTION			 " -- "
		::=  { eNBTimerInfo  19 }


	timerHcTarHandover		 OBJECT-TYPE
		SYNTAX					 Unsigned32( 0 .. 65535 )
		MAX-ACCESS			 read-write
		STATUS					 current
		DESCRIPTION			 " -- "
		::=  { eNBTimerInfo  20 }


	timerIcicHii		 OBJECT-TYPE
		SYNTAX					 Unsigned32( 0 .. 65535 )
		MAX-ACCESS			 read-write
		STATUS					 current
		DESCRIPTION			 " -- "
		::=  { eNBTimerInfo  21 }


	timerIcicOi		 OBJECT-TYPE
		SYNTAX					 Unsigned32( 0 .. 65535 )
		MAX-ACCESS			 read-write
		STATUS					 current
		DESCRIPTION			 " -- "
		::=  { eNBTimerInfo  22 }


	timerUeProtect		 OBJECT-TYPE
		SYNTAX					 Unsigned32( 0 .. 180000 )
		MAX-ACCESS			 read-write
		STATUS					 current
		DESCRIPTION			 " -- "
		::=  { eNBTimerInfo  23 }


	timerStoreUeCtx		 OBJECT-TYPE
		SYNTAX					 Unsigned32( 0 .. 1800000 )
		MAX-ACCESS			 read-write
		STATUS					 current
		DESCRIPTION			 " -- "
		::=  { eNBTimerInfo  24 }


	timerInterRatGeranCco		 OBJECT-TYPE
		SYNTAX					 Unsigned32( 0 .. 65535 )
		MAX-ACCESS			 read-write
		STATUS					 current
		DESCRIPTION			 " -- "
		::=  { eNBTimerInfo  25 }


	timerInterRatUtraPsHcPrepare		 OBJECT-TYPE
		SYNTAX					 Unsigned32( 0 .. 65535 )
		MAX-ACCESS			 read-write
		STATUS					 current
		DESCRIPTION			 " -- "
		::=  { eNBTimerInfo  26 }


	timerInterRatUtraPsHc		 OBJECT-TYPE
		SYNTAX					 Unsigned32( 0 .. 65535 )
		MAX-ACCESS			 read-write
		STATUS					 current
		DESCRIPTION			 " -- "
		::=  { eNBTimerInfo  27 }


	timerMeasRptCsfb		 OBJECT-TYPE
		SYNTAX					 Unsigned32( 0 .. 65535 )
		MAX-ACCESS			 read-write
		STATUS					 current
		DESCRIPTION			 " -- "
		::=  { eNBTimerInfo  28 }


	timerWaitPdcpRsp		 OBJECT-TYPE
		SYNTAX					 Unsigned32( 0 .. 65535 )
		MAX-ACCESS			 read-write
		STATUS					 current
		DESCRIPTION			 " -- "
		::=  { eNBTimerInfo  29 }


	timerS1Setup		 OBJECT-TYPE
		SYNTAX					 INTEGER{ s30(30),s60(60),s300(300),s900(900),s1800(1800)  }
		MAX-ACCESS			 read-write
		STATUS					 current
		DESCRIPTION			 " -- "
		::=  { eNBTimerInfo  30 }


	timerWaitOmRsp		 OBJECT-TYPE
		SYNTAX					 Unsigned32( 0 .. 65535 )
		MAX-ACCESS			 read-write
		STATUS					 current
		DESCRIPTION			 " -- "
		::=  { eNBTimerInfo  31 }


	timerWaitTime		 OBJECT-TYPE
		SYNTAX					 Unsigned32( 1 .. 16 )
		MAX-ACCESS			 read-write
		STATUS					 current
		DESCRIPTION			 " -- "
		::=  { eNBTimerInfo  32 }


	timerInterRatGeranHcPrepare		 OBJECT-TYPE
		SYNTAX					 Unsigned32( 0 .. 65535 )
		MAX-ACCESS			 read-write
		STATUS					 current
		DESCRIPTION			 " -- "
		::=  { eNBTimerInfo  33 }


	timerInterRatGeranHc		 OBJECT-TYPE
		SYNTAX					 Unsigned32( 0 .. 65535 )
		MAX-ACCESS			 read-write
		STATUS					 current
		DESCRIPTION			 " -- "
		::=  { eNBTimerInfo  34 }


	timerWatiProcAp		 OBJECT-TYPE
		SYNTAX					 Unsigned32( 0 .. 65535 )
		MAX-ACCESS			 read-write
		STATUS					 current
		DESCRIPTION			 " -- "
		::=  { eNBTimerInfo  35 }


	timerProtectReestablish		 OBJECT-TYPE
		SYNTAX					 Unsigned32( 0 .. 65535 )
		MAX-ACCESS			 read-write
		STATUS					 current
		DESCRIPTION			 " -- "
		::=  { eNBTimerInfo  36 }


	timerSearchUeContext		 OBJECT-TYPE
		SYNTAX					 Unsigned32( 0 .. 65535 )
		MAX-ACCESS			 read-write
		STATUS					 current
		DESCRIPTION			 " -- "
		::=  { eNBTimerInfo  37 }


	timerRrcReestablishUeContext		 OBJECT-TYPE
		SYNTAX					 Unsigned32( 0 .. 2000 )
		MAX-ACCESS			 read-write
		STATUS					 current
		DESCRIPTION			 " -- "
		::=  { eNBTimerInfo  38 }


	timerApDelaySendHoNotify		 OBJECT-TYPE
		SYNTAX					 Unsigned32( 0 .. 4000 )
		MAX-ACCESS			 read-write
		STATUS					 current
		DESCRIPTION			 " -- "
		::=  { eNBTimerInfo  39 }


	staticTrafficPara		 OBJECT IDENTIFIER
		::=  { networkElementLayoutPlan  8 }


	sndRlcCfgTable		 OBJECT-TYPE
		SYNTAX					 SEQUENCE  OF	 SndRlcCfgEntry
		MAX-ACCESS			 not-accessible
		STATUS					 current
		DESCRIPTION			 " -- "
		::=  { staticTrafficPara  1 }


	sndRlcCfgEntry		 OBJECT-TYPE
		SYNTAX					 SndRlcCfgEntry
		MAX-ACCESS			 not-accessible
		STATUS					 current
		DESCRIPTION			 " -- "
		INDEX						{ sndRlcCfgId }
		::=  { sndRlcCfgTable  1 }


	SndRlcCfgEntry		 ::=  SEQUENCE {
		sndRlcCfgId					Integer32,
		sndRlcRowStatus					RowStatus,
		sndRlcTPollRetransmit					INTEGER,
		sndRlcPollPdu					INTEGER,
		sndRlcPollByte					INTEGER,
		sndRlcMaxRetxThreshold					INTEGER,
		sndRlcSnFieldLength					INTEGER
		}


	sndRlcCfgId		 OBJECT-TYPE
		SYNTAX					 Integer32( 0 .. 10 )
		MAX-ACCESS			 not-accessible
		STATUS					 current
		DESCRIPTION			 " -- "
		::=  { sndRlcCfgEntry  1 }


	sndRlcRowStatus		 OBJECT-TYPE
		SYNTAX					 RowStatus
		MAX-ACCESS			 read-create
		STATUS					 current
		DESCRIPTION			 " -- "
		::=  { sndRlcCfgEntry  2 }


	sndRlcTPollRetransmit		 OBJECT-TYPE
		SYNTAX					 INTEGER{ ms5(0),ms10(1),ms15(2),ms20(3),ms25(4),ms30(5),ms35(6),ms40(7),ms45(8),ms50(9),ms55(10),ms60(11),ms65(12),ms70(13),ms75(14),ms80(15),ms85(16),ms90(17),ms95(18),ms100(19),ms105(20),ms110(21),ms115(22),ms120(23),ms125(24),ms130(25),ms135(26),ms140(27),ms145(28),ms150(29),ms155(30),ms160(31),ms165(32),ms170(33),ms175(34),ms180(35),ms185(36),ms190(37),ms195(38),ms200(39),ms205(40),ms210(41),ms215(42),ms220(43),ms225(44),ms230(45),ms235(46),ms240(47),ms245(48),ms250(49),ms300(50),ms350(51),ms400(52),ms450(53),ms500(54)  }
		MAX-ACCESS			 read-create
		STATUS					 current
		DESCRIPTION			 " -- "
		::=  { sndRlcCfgEntry  3 }


	sndRlcPollPdu		 OBJECT-TYPE
		SYNTAX					 INTEGER{ p4(0),p8(1),p16(2),p32(3),p64(4),p128(5),p256(6),pInfinity(7)  }
		MAX-ACCESS			 read-create
		STATUS					 current
		DESCRIPTION			 " -- "
		::=  { sndRlcCfgEntry  4 }


	sndRlcPollByte		 OBJECT-TYPE
		SYNTAX					 INTEGER{ kb25(0),kb50(1),kb75(2),kb100(3),kb125(4),kb250(5),kb375(6),kb500(7),kb750(8),kb1000(9),kb1250(10),kb1500(11),kb2000(12),kb3000(13),kbinfinity(14)  }
		MAX-ACCESS			 read-create
		STATUS					 current
		DESCRIPTION			 " -- "
		::=  { sndRlcCfgEntry  5 }


	sndRlcMaxRetxThreshold		 OBJECT-TYPE
		SYNTAX					 INTEGER{ t1(0),t2(1),t3(2),t4(3),t6(4),t8(5),t16(6),t32(7)  }
		MAX-ACCESS			 read-create
		STATUS					 current
		DESCRIPTION			 " -- "
		::=  { sndRlcCfgEntry  6 }


	sndRlcSnFieldLength		 OBJECT-TYPE
		SYNTAX					 INTEGER{ size5(0),size10(1)  }
		MAX-ACCESS			 read-create
		STATUS					 current
		DESCRIPTION			 " -- "
		::=  { sndRlcCfgEntry  7 }


	recvRlcCfgTable		 OBJECT-TYPE
		SYNTAX					 SEQUENCE  OF	 RecvRlcCfgEntry
		MAX-ACCESS			 not-accessible
		STATUS					 current
		DESCRIPTION			 " -- "
		::=  { staticTrafficPara  2 }


	recvRlcCfgEntry		 OBJECT-TYPE
		SYNTAX					 RecvRlcCfgEntry
		MAX-ACCESS			 not-accessible
		STATUS					 current
		DESCRIPTION			 " -- "
		INDEX						{ recvRlcCfgId }
		::=  { recvRlcCfgTable  1 }


	RecvRlcCfgEntry		 ::=  SEQUENCE {
		recvRlcCfgId					Integer32,
		recvRlcRowStatus					RowStatus,
		recvRlcTAmReordering					INTEGER,
		recvRlcTUmReordering					INTEGER,
		recvRlcTStatusProhibit					INTEGER,
		recvRlcSnFieldLength					INTEGER
		}


	recvRlcCfgId		 OBJECT-TYPE
		SYNTAX					 Integer32( 0 .. 10 )
		MAX-ACCESS			 not-accessible
		STATUS					 current
		DESCRIPTION			 " -- "
		::=  { recvRlcCfgEntry  1 }


	recvRlcRowStatus		 OBJECT-TYPE
		SYNTAX					 RowStatus
		MAX-ACCESS			 read-create
		STATUS					 current
		DESCRIPTION			 " -- "
		::=  { recvRlcCfgEntry  2 }


	recvRlcTAmReordering		 OBJECT-TYPE
		SYNTAX					 INTEGER{ ms0(0),ms5(1),ms10(2),ms15(3),ms20(4),ms25(5),ms30(6),ms35(7),ms40(8),ms45(9),ms50(10),ms55(11),ms60(12),ms65(13),ms70(14),ms75(15),ms80(16),ms85(17),ms90(18),ms95(19),ms100(20),ms110(21),ms120(22),ms130(23),ms140(24),ms150(25),ms160(26),ms170(27),ms180(28),ms190(29),ms200(30)  }
		MAX-ACCESS			 read-create
		STATUS					 current
		DESCRIPTION			 " -- "
		::=  { recvRlcCfgEntry  3 }


	recvRlcTUmReordering		 OBJECT-TYPE
		SYNTAX					 INTEGER{ ms0(0),ms5(1),ms10(2),ms15(3),ms20(4),ms25(5),ms30(6),ms35(7),ms40(8),ms45(9),ms50(10),ms55(11),ms60(12),ms65(13),ms70(14),ms75(15),ms80(16),ms85(17),ms90(18),ms95(19),ms100(20),ms110(21),ms120(22),ms130(23),ms140(24),ms150(25),ms160(26),ms170(27),ms180(28),ms190(29),ms200(30)  }
		MAX-ACCESS			 read-create
		STATUS					 current
		DESCRIPTION			 " -- "
		::=  { recvRlcCfgEntry  4 }


	recvRlcTStatusProhibit		 OBJECT-TYPE
		SYNTAX					 INTEGER{ ms0(0),ms5(1),ms10(2),ms15(3),ms20(4),ms25(5),ms30(6),ms35(7),ms40(8),ms45(9),ms50(10),ms55(11),ms60(12),ms65(13),ms70(14),ms75(15),ms80(16),ms85(17),ms90(18),ms95(19),ms100(20),ms105(21),ms110(22),ms115(23),ms120(24),ms125(25),ms130(26),ms135(27),ms140(28),ms145(29),ms150(30),ms155(31),ms160(32),ms165(33),ms170(34),ms175(35),ms180(36),ms185(37),ms190(38),ms195(39),ms200(40),ms205(41),ms210(42),ms215(43),ms220(44),ms225(45),ms230(46),ms235(47),ms240(48),ms245(49),ms250(50),ms300(51),ms350(52),ms400(53),ms450(54),ms500(55)  }
		MAX-ACCESS			 read-create
		STATUS					 current
		DESCRIPTION			 " -- "
		::=  { recvRlcCfgEntry  5 }


	recvRlcSnFieldLength		 OBJECT-TYPE
		SYNTAX					 INTEGER{ size5(0),size10(1)  }
		MAX-ACCESS			 read-create
		STATUS					 current
		DESCRIPTION			 " -- "
		::=  { recvRlcCfgEntry  6 }


	pdcpCfgTable		 OBJECT-TYPE
		SYNTAX					 SEQUENCE  OF	 PdcpCfgEntry
		MAX-ACCESS			 not-accessible
		STATUS					 current
		DESCRIPTION			 " -- "
		::=  { staticTrafficPara  3 }


	pdcpCfgEntry		 OBJECT-TYPE
		SYNTAX					 PdcpCfgEntry
		MAX-ACCESS			 not-accessible
		STATUS					 current
		DESCRIPTION			 " -- "
		INDEX						{ pdcpCfgId }
		::=  { pdcpCfgTable  1 }


	PdcpCfgEntry		 ::=  SEQUENCE {
		pdcpCfgId					Integer32,
		pdcpRowStatus					RowStatus,
		pdcpDiscardTimerFlag					INTEGER,
		pdcpDiscardTimer					INTEGER,
		pdcpStatusReportRequired					INTEGER,
		pdcpSnSize					INTEGER,
		pdcpHeaderCompressionFlag					INTEGER,
		pdcpMaxCid					Integer32,
		pdcpProfile0x0001Flag					INTEGER,
		pdcpProfile0x0002Flag					INTEGER,
		pdcpProfile0x0003Flag					INTEGER,
		pdcpProfile0x0004Flag					INTEGER,
		pdcpProfile0x0006Flag					INTEGER,
		pdcpProfile0x0101Flag					INTEGER,
		pdcpProfile0x0102Flag					INTEGER,
		pdcpProfile0x0103Flag					INTEGER,
		pdcpProfile0x0104Flag					INTEGER,
		pdcpDiscardTimerExCfg					Integer32,
		pdcpDiscardTimerExCfgQci9					Integer32
		}


	pdcpCfgId		 OBJECT-TYPE
		SYNTAX					 Integer32( 0 .. 10 )
		MAX-ACCESS			 not-accessible
		STATUS					 current
		DESCRIPTION			 " -- "
		::=  { pdcpCfgEntry  1 }


	pdcpRowStatus		 OBJECT-TYPE
		SYNTAX					 RowStatus
		MAX-ACCESS			 read-create
		STATUS					 current
		DESCRIPTION			 " -- "
		::=  { pdcpCfgEntry  2 }


	pdcpDiscardTimerFlag		 OBJECT-TYPE
		SYNTAX					 INTEGER{ notExist(0),exist(1)  }
		MAX-ACCESS			 read-create
		STATUS					 current
		DESCRIPTION			 " -- "
		::=  { pdcpCfgEntry  3 }


	pdcpDiscardTimer		 OBJECT-TYPE
		SYNTAX					 INTEGER{ ms50(0),ms100(1),ms150(2),ms300(3),ms500(4),ms750(5),ms1500(6),infinity(7)  }
		MAX-ACCESS			 read-create
		STATUS					 current
		DESCRIPTION			 " -- "
		::=  { pdcpCfgEntry  4 }


	pdcpStatusReportRequired		 OBJECT-TYPE
		SYNTAX					 INTEGER{ false(0),true(1)  }
		MAX-ACCESS			 read-create
		STATUS					 current
		DESCRIPTION			 " -- "
		::=  { pdcpCfgEntry  5 }


	pdcpSnSize		 OBJECT-TYPE
		SYNTAX					 INTEGER{ bits7(0),bits12(1)  }
		MAX-ACCESS			 read-create
		STATUS					 current
		DESCRIPTION			 " -- "
		::=  { pdcpCfgEntry  6 }


	pdcpHeaderCompressionFlag		 OBJECT-TYPE
		SYNTAX					 INTEGER{ false(0),true(1)  }
		MAX-ACCESS			 read-create
		STATUS					 current
		DESCRIPTION			 " -- "
		::=  { pdcpCfgEntry  7 }


	pdcpMaxCid		 OBJECT-TYPE
		SYNTAX					 Integer32( 1 .. 16383 )
		MAX-ACCESS			 read-create
		STATUS					 current
		DESCRIPTION			 " -- "
		::=  { pdcpCfgEntry  8 }


	pdcpProfile0x0001Flag		 OBJECT-TYPE
		SYNTAX					 INTEGER{ true(1),false(0)  }
		MAX-ACCESS			 read-create
		STATUS					 current
		DESCRIPTION			 " -- "
		::=  { pdcpCfgEntry  9 }


	pdcpProfile0x0002Flag		 OBJECT-TYPE
		SYNTAX					 INTEGER{ true(1),false(0)  }
		MAX-ACCESS			 read-create
		STATUS					 current
		DESCRIPTION			 " -- "
		::=  { pdcpCfgEntry  10 }


	pdcpProfile0x0003Flag		 OBJECT-TYPE
		SYNTAX					 INTEGER{ true(1),false(0)  }
		MAX-ACCESS			 read-create
		STATUS					 current
		DESCRIPTION			 " -- "
		::=  { pdcpCfgEntry  11 }


	pdcpProfile0x0004Flag		 OBJECT-TYPE
		SYNTAX					 INTEGER{ true(1),false(0)  }
		MAX-ACCESS			 read-create
		STATUS					 current
		DESCRIPTION			 " -- "
		::=  { pdcpCfgEntry  12 }


	pdcpProfile0x0006Flag		 OBJECT-TYPE
		SYNTAX					 INTEGER{ true(1),false(0)  }
		MAX-ACCESS			 read-create
		STATUS					 current
		DESCRIPTION			 " -- "
		::=  { pdcpCfgEntry  13 }


	pdcpProfile0x0101Flag		 OBJECT-TYPE
		SYNTAX					 INTEGER{ true(1),false(0)  }
		MAX-ACCESS			 read-create
		STATUS					 current
		DESCRIPTION			 " -- "
		::=  { pdcpCfgEntry  14 }


	pdcpProfile0x0102Flag		 OBJECT-TYPE
		SYNTAX					 INTEGER{ true(1),false(0)  }
		MAX-ACCESS			 read-create
		STATUS					 current
		DESCRIPTION			 " -- "
		::=  { pdcpCfgEntry  15 }


	pdcpProfile0x0103Flag		 OBJECT-TYPE
		SYNTAX					 INTEGER{ true(1),false(0)  }
		MAX-ACCESS			 read-create
		STATUS					 current
		DESCRIPTION			 " -- "
		::=  { pdcpCfgEntry  16 }


	pdcpProfile0x0104Flag		 OBJECT-TYPE
		SYNTAX					 INTEGER{ true(1),false(0)  }
		MAX-ACCESS			 read-create
		STATUS					 current
		DESCRIPTION			 " -- "
		::=  { pdcpCfgEntry  17 }


	pdcpDiscardTimerExCfg		 OBJECT-TYPE
		SYNTAX					 Integer32( 0 .. 7 )
		MAX-ACCESS			 read-create
		STATUS					 current
		DESCRIPTION			 " -- "
		::=  { pdcpCfgEntry  18 }


	pdcpDiscardTimerExCfgQci9		 OBJECT-TYPE
		SYNTAX					 Integer32( 0 .. 7 )
		MAX-ACCESS			 read-create
		STATUS					 current
		DESCRIPTION			 " -- "
		::=  { pdcpCfgEntry  19 }


	srbTable		 OBJECT-TYPE
		SYNTAX					 SEQUENCE  OF	 SrbEntry
		MAX-ACCESS			 not-accessible
		STATUS					 current
		DESCRIPTION			 " -- "
		::=  { staticTrafficPara  4 }


	srbEntry		 OBJECT-TYPE
		SYNTAX					 SrbEntry
		MAX-ACCESS			 not-accessible
		STATUS					 current
		DESCRIPTION			 " -- "
		INDEX						{ srbId }
		::=  { srbTable  1 }


	SrbEntry		 ::=  SEQUENCE {
		srbId					Integer32,
		srbRowStatus					RowStatus,
		srbRlcDefaultCfgFlag					INTEGER,
		srbLochDefaultCfgFlag					INTEGER,
		srbSendRlcCfgId					Integer32,
		srbRecvRlcCfgId					Integer32,
		srbUlLoPriority					Integer32,
		srbUlLoChGroup					Integer32,
		srbDlLoPriority					Integer32
		}


	srbId		 OBJECT-TYPE
		SYNTAX					 Integer32( 1 .. 2 )
		MAX-ACCESS			 not-accessible
		STATUS					 current
		DESCRIPTION			 " -- "
		::=  { srbEntry  1 }


	srbRowStatus		 OBJECT-TYPE
		SYNTAX					 RowStatus
		MAX-ACCESS			 read-create
		STATUS					 current
		DESCRIPTION			 " -- "
		::=  { srbEntry  2 }


	srbRlcDefaultCfgFlag		 OBJECT-TYPE
		SYNTAX					 INTEGER{ rlcDefaultCfg(0),rlcExplicitCfg(1)  }
		MAX-ACCESS			 read-create
		STATUS					 current
		DESCRIPTION			 " -- "
		::=  { srbEntry  3 }


	srbLochDefaultCfgFlag		 OBJECT-TYPE
		SYNTAX					 INTEGER{ lochDefaultCfg(0),lochExplicitCfg(1)  }
		MAX-ACCESS			 read-create
		STATUS					 current
		DESCRIPTION			 " -- "
		::=  { srbEntry  4 }


	srbSendRlcCfgId		 OBJECT-TYPE
		SYNTAX					 Integer32( 0 .. 1 )
		MAX-ACCESS			 read-create
		STATUS					 current
		DESCRIPTION			 " -- "
		::=  { srbEntry  5 }


	srbRecvRlcCfgId		 OBJECT-TYPE
		SYNTAX					 Integer32( 0 .. 3 )
		MAX-ACCESS			 read-create
		STATUS					 current
		DESCRIPTION			 " -- "
		::=  { srbEntry  6 }


	srbUlLoPriority		 OBJECT-TYPE
		SYNTAX					 Integer32( 1 .. 16 )
		MAX-ACCESS			 read-create
		STATUS					 current
		DESCRIPTION			 " -- "
		::=  { srbEntry  7 }


	srbUlLoChGroup		 OBJECT-TYPE
		SYNTAX					 Integer32( 0 .. 3 )
		MAX-ACCESS			 read-create
		STATUS					 current
		DESCRIPTION			 " -- "
		::=  { srbEntry  8 }


	srbDlLoPriority		 OBJECT-TYPE
		SYNTAX					 Integer32( 1 .. 16 )
		MAX-ACCESS			 read-create
		STATUS					 current
		DESCRIPTION			 " -- "
		::=  { srbEntry  9 }


	drbTable		 OBJECT-TYPE
		SYNTAX					 SEQUENCE  OF	 DrbEntry
		MAX-ACCESS			 not-accessible
		STATUS					 current
		DESCRIPTION			 " -- "
		::=  { staticTrafficPara  5 }


	drbEntry		 OBJECT-TYPE
		SYNTAX					 DrbEntry
		MAX-ACCESS			 not-accessible
		STATUS					 current
		DESCRIPTION			 " -- "
		INDEX						{ drbQci }
		::=  { drbTable  1 }


	DrbEntry		 ::=  SEQUENCE {
		drbQci					Integer32,
		drbRowStatus					RowStatus,
		drbMode					INTEGER,
		drbPdcpCfgId					Integer32,
		drbSendRlcCfgId					Integer32,
		drbRecvRlcCfgId					Integer32,
		drbUlLoPriority					Integer32,
		drbPbr					INTEGER,
		drbMinbr					INTEGER,
		drbBucketSizeDuration					INTEGER,
		drbUlLoChGroup					Integer32,
		drbDlLoPriority					Integer32,
		drbDataforwardFlag					INTEGER,
		drbSecondaryMode					INTEGER,
		drbSecondaryPdcpCfgId					Integer32,
		drbSecondarySendRlcCfgId					Integer32,
		drbSecondaryRecvRlcCfgId					Integer32,
		drbS1ResMapCoef					Integer32,
		drbDlBucketSizeDuration					INTEGER
		}


	drbQci		 OBJECT-TYPE
		SYNTAX					 Integer32( 1 .. 9 )
		MAX-ACCESS			 not-accessible
		STATUS					 current
		DESCRIPTION			 " -- "
		::=  { drbEntry  1 }


	drbRowStatus		 OBJECT-TYPE
		SYNTAX					 RowStatus
		MAX-ACCESS			 read-create
		STATUS					 current
		DESCRIPTION			 " -- "
		::=  { drbEntry  2 }


	drbMode		 OBJECT-TYPE
		SYNTAX					 INTEGER{ am(1),umBi(2),umUniUl(3),umUniDl(4)  }
		MAX-ACCESS			 read-create
		STATUS					 current
		DESCRIPTION			 " -- "
		::=  { drbEntry  3 }


	drbPdcpCfgId		 OBJECT-TYPE
		SYNTAX					 Integer32( 0 .. 6 )
		MAX-ACCESS			 read-create
		STATUS					 current
		DESCRIPTION			 " -- "
		::=  { drbEntry  4 }


	drbSendRlcCfgId		 OBJECT-TYPE
		SYNTAX					 Integer32( 0 .. 2 )
		MAX-ACCESS			 read-create
		STATUS					 current
		DESCRIPTION			 " -- "
		::=  { drbEntry  5 }


	drbRecvRlcCfgId		 OBJECT-TYPE
		SYNTAX					 Integer32( 0 .. 2 )
		MAX-ACCESS			 read-create
		STATUS					 current
		DESCRIPTION			 " -- "
		::=  { drbEntry  6 }


	drbUlLoPriority		 OBJECT-TYPE
		SYNTAX					 Integer32( 1 .. 16 )
		MAX-ACCESS			 read-create
		STATUS					 current
		DESCRIPTION			 " -- "
		::=  { drbEntry  7 }


	drbPbr		 OBJECT-TYPE
		SYNTAX					 INTEGER{ kB0(0),kB8(1),kB16(2),kB32(3),kB64(4),kB128(5),kB256(6),infinity(7)  }
		MAX-ACCESS			 read-create
		STATUS					 current
		DESCRIPTION			 " -- "
		::=  { drbEntry  8 }


	drbMinbr		 OBJECT-TYPE
		SYNTAX					 INTEGER{ kB0(0),kB8(1),kB16(2),kB32(3),kB64(4),kB128(5),kB256(6),infinity(7),kB640(8),kB512(9),kB768(10),kB896(11),kB1024(12),kB1152(13),kB1280(14),kB1408(15),kB1536(16),kB1664(17),kB1792(18),kB1920(19),kB2048(20),kB2176(21),kB2304(22),kB2432(23),kB2560(24)  }
		MAX-ACCESS			 read-create
		STATUS					 current
		DESCRIPTION			 " -- "
		::=  { drbEntry  9 }


	drbBucketSizeDuration		 OBJECT-TYPE
		SYNTAX					 INTEGER{ bsdMs50(0),bsdMs100(1),bsdMs150(2),bsdMs300(3),bsdMs500(4),bsdMs1000(5)  }
		MAX-ACCESS			 read-create
		STATUS					 current
		DESCRIPTION			 " -- "
		::=  { drbEntry  10 }


	drbUlLoChGroup		 OBJECT-TYPE
		SYNTAX					 Integer32( 0 .. 3 )
		MAX-ACCESS			 read-create
		STATUS					 current
		DESCRIPTION			 " -- "
		::=  { drbEntry  11 }


	drbDlLoPriority		 OBJECT-TYPE
		SYNTAX					 Integer32( 1 .. 16 )
		MAX-ACCESS			 read-create
		STATUS					 current
		DESCRIPTION			 " -- "
		::=  { drbEntry  12 }


	drbDataforwardFlag		 OBJECT-TYPE
		SYNTAX					 INTEGER{ dataforwardFalse(0),dataforwardTrue(1)  }
		MAX-ACCESS			 read-create
		STATUS					 current
		DESCRIPTION			 " -- "
		::=  { drbEntry  13 }


	drbSecondaryMode		 OBJECT-TYPE
		SYNTAX					 INTEGER{ am(1),umBi(2),umUniUl(3),umUniDl(4)  }
		MAX-ACCESS			 read-create
		STATUS					 current
		DESCRIPTION			 " -- "
		::=  { drbEntry  14 }


	drbSecondaryPdcpCfgId		 OBJECT-TYPE
		SYNTAX					 Integer32( 0 .. 6 )
		MAX-ACCESS			 read-create
		STATUS					 current
		DESCRIPTION			 " -- "
		::=  { drbEntry  15 }


	drbSecondarySendRlcCfgId		 OBJECT-TYPE
		SYNTAX					 Integer32( 0 .. 2 )
		MAX-ACCESS			 read-create
		STATUS					 current
		DESCRIPTION			 " -- "
		::=  { drbEntry  16 }


	drbSecondaryRecvRlcCfgId		 OBJECT-TYPE
		SYNTAX					 Integer32( 0 .. 2 )
		MAX-ACCESS			 read-create
		STATUS					 current
		DESCRIPTION			 " -- "
		::=  { drbEntry  17 }


	drbS1ResMapCoef		 OBJECT-TYPE
		SYNTAX					 Integer32( 0 .. 255 )
		MAX-ACCESS			 read-create
		STATUS					 current
		DESCRIPTION			 " -- "
		::=  { drbEntry  18 }


	drbDlBucketSizeDuration		 OBJECT-TYPE
		SYNTAX					 INTEGER{ bsdMs5(0),bsdMs50(1),bsdMs100(2),bsdMs250(3)  }
		MAX-ACCESS			 read-create
		STATUS					 current
		DESCRIPTION			 " -- "
		::=  { drbEntry  19 }


	pagingEnbInfo		 OBJECT IDENTIFIER
		::=  { staticTrafficPara  6 }


	pagingEnbDeftCycle		 OBJECT-TYPE
		SYNTAX					 INTEGER{ ms320(0),ms640(1),ms1280(2),ms2560(3)  }
		MAX-ACCESS			 read-write
		STATUS					 current
		DESCRIPTION			 " -- "
		::=  { pagingEnbInfo  1 }


	extendDrbTable		 OBJECT-TYPE
		SYNTAX					 SEQUENCE  OF	 ExtendDrbEntry
		MAX-ACCESS			 not-accessible
		STATUS					 current
		DESCRIPTION			 " -- "
		::=  { staticTrafficPara  7 }


	extendDrbEntry		 OBJECT-TYPE
		SYNTAX					 ExtendDrbEntry
		MAX-ACCESS			 not-accessible
		STATUS					 current
		DESCRIPTION			 " -- "
		INDEX						{ extendDrbIndex }
		::=  { extendDrbTable  1 }


	ExtendDrbEntry		 ::=  SEQUENCE {
		extendDrbIndex					Integer32,
		extendDrbRowStatus					RowStatus,
		extendDrbQci					Integer32,
		extendDrbMode					INTEGER,
		extendDrbPdcpCfgId					Integer32,
		extendDrbSendRlcCfgId					Integer32,
		extendDrbRecvRlcCfgId					Integer32,
		extendDrbUlLoPriority					Integer32,
		extendDrbPbr					INTEGER,
		extendDrbMinbr					INTEGER,
		extendDrbBucketSizeDuration					INTEGER,
		extendDrbUlLoChGroup					Integer32,
		extendDrbDlLoPriority					Integer32,
		extendDrbDataforwardFlag					INTEGER,
		extendDrbSecondaryMode					INTEGER,
		extendDrbSecondaryPdcpCfgId					Integer32,
		extendDrbSecondarySendRlcCfgId					Integer32,
		extendDrbSecondaryRecvRlcCfgId					Integer32,
		extendDrbS1ResMapCoef					Integer32,
		extendDrbPER					Integer32,
		extendDrbPDB					Integer32,
		extendDrbPriority					Integer32,
		extendDrbDlBucketSizeDuration					INTEGER
		}


	extendDrbIndex		 OBJECT-TYPE
		SYNTAX					 Integer32( 0 .. 4 )
		MAX-ACCESS			 not-accessible
		STATUS					 current
		DESCRIPTION			 " -- "
		::=  { extendDrbEntry  1 }


	extendDrbRowStatus		 OBJECT-TYPE
		SYNTAX					 RowStatus
		MAX-ACCESS			 read-create
		STATUS					 current
		DESCRIPTION			 " -- "
		::=  { extendDrbEntry  2 }


	extendDrbQci		 OBJECT-TYPE
		SYNTAX					 Integer32( 0 .. 255 )
		MAX-ACCESS			 read-create
		STATUS					 current
		DESCRIPTION			 " -- "
		::=  { extendDrbEntry  3 }


	extendDrbMode		 OBJECT-TYPE
		SYNTAX					 INTEGER{ am(1),umBi(2),umUniUl(3),umUniDl(4)  }
		MAX-ACCESS			 read-create
		STATUS					 current
		DESCRIPTION			 " -- "
		::=  { extendDrbEntry  4 }


	extendDrbPdcpCfgId		 OBJECT-TYPE
		SYNTAX					 Integer32( 0 .. 6 )
		MAX-ACCESS			 read-create
		STATUS					 current
		DESCRIPTION			 " -- "
		::=  { extendDrbEntry  5 }


	extendDrbSendRlcCfgId		 OBJECT-TYPE
		SYNTAX					 Integer32( 0 .. 2 )
		MAX-ACCESS			 read-create
		STATUS					 current
		DESCRIPTION			 " -- "
		::=  { extendDrbEntry  6 }


	extendDrbRecvRlcCfgId		 OBJECT-TYPE
		SYNTAX					 Integer32( 0 .. 2 )
		MAX-ACCESS			 read-create
		STATUS					 current
		DESCRIPTION			 " -- "
		::=  { extendDrbEntry  7 }


	extendDrbUlLoPriority		 OBJECT-TYPE
		SYNTAX					 Integer32( 1 .. 16 )
		MAX-ACCESS			 read-create
		STATUS					 current
		DESCRIPTION			 " -- "
		::=  { extendDrbEntry  8 }


	extendDrbPbr		 OBJECT-TYPE
		SYNTAX					 INTEGER{ kb0(0),kb8(1),kb16(2),kb32(3),kb64(4),kb128(5),kb256(6),infinity(7)  }
		MAX-ACCESS			 read-create
		STATUS					 current
		DESCRIPTION			 " -- "
		::=  { extendDrbEntry  9 }


	extendDrbMinbr		 OBJECT-TYPE
		SYNTAX					 INTEGER{ kb0(0),kb8(1),kb16(2),kb32(3),kb64(4),kb128(5),kb256(6),infinity(7)  }
		MAX-ACCESS			 read-create
		STATUS					 current
		DESCRIPTION			 " -- "
		::=  { extendDrbEntry  10 }


	extendDrbBucketSizeDuration		 OBJECT-TYPE
		SYNTAX					 INTEGER{ bsdMs50(0),bsdMs100(1),bsdMs150(2),bsdMs300(3),bsdMs500(4),bsdMs1000(5)  }
		MAX-ACCESS			 read-create
		STATUS					 current
		DESCRIPTION			 " -- "
		::=  { extendDrbEntry  11 }


	extendDrbUlLoChGroup		 OBJECT-TYPE
		SYNTAX					 Integer32( 0 .. 3 )
		MAX-ACCESS			 read-create
		STATUS					 current
		DESCRIPTION			 " -- "
		::=  { extendDrbEntry  12 }


	extendDrbDlLoPriority		 OBJECT-TYPE
		SYNTAX					 Integer32( 1 .. 16 )
		MAX-ACCESS			 read-create
		STATUS					 current
		DESCRIPTION			 " -- "
		::=  { extendDrbEntry  13 }


	extendDrbDataforwardFlag		 OBJECT-TYPE
		SYNTAX					 INTEGER{ dataforwardFalse(0),dataforwardTrue(1)  }
		MAX-ACCESS			 read-create
		STATUS					 current
		DESCRIPTION			 " -- "
		::=  { extendDrbEntry  14 }


	extendDrbSecondaryMode		 OBJECT-TYPE
		SYNTAX					 INTEGER{ am(1),umBi(2),umUniUl(3),umUniDl(4)  }
		MAX-ACCESS			 read-create
		STATUS					 current
		DESCRIPTION			 " -- "
		::=  { extendDrbEntry  15 }


	extendDrbSecondaryPdcpCfgId		 OBJECT-TYPE
		SYNTAX					 Integer32( 0 .. 6 )
		MAX-ACCESS			 read-create
		STATUS					 current
		DESCRIPTION			 " -- "
		::=  { extendDrbEntry  16 }


	extendDrbSecondarySendRlcCfgId		 OBJECT-TYPE
		SYNTAX					 Integer32( 0 .. 2 )
		MAX-ACCESS			 read-create
		STATUS					 current
		DESCRIPTION			 " -- "
		::=  { extendDrbEntry  17 }


	extendDrbSecondaryRecvRlcCfgId		 OBJECT-TYPE
		SYNTAX					 Integer32( 0 .. 2 )
		MAX-ACCESS			 read-create
		STATUS					 current
		DESCRIPTION			 " -- "
		::=  { extendDrbEntry  18 }


	extendDrbS1ResMapCoef		 OBJECT-TYPE
		SYNTAX					 Integer32( 0 .. 255 )
		MAX-ACCESS			 read-create
		STATUS					 current
		DESCRIPTION			 " -- "
		::=  { extendDrbEntry  19 }


	extendDrbPER		 OBJECT-TYPE
		SYNTAX					 Integer32( 0 .. 255 )
		MAX-ACCESS			 read-create
		STATUS					 current
		DESCRIPTION			 " -- "
		::=  { extendDrbEntry  20 }


	extendDrbPDB		 OBJECT-TYPE
		SYNTAX					 Integer32( 0 .. 65535 )
		MAX-ACCESS			 read-create
		STATUS					 current
		DESCRIPTION			 " -- "
		::=  { extendDrbEntry  21 }


	extendDrbPriority		 OBJECT-TYPE
		SYNTAX					 Integer32( 0 .. 255 )
		MAX-ACCESS			 read-create
		STATUS					 current
		DESCRIPTION			 " -- "
		::=  { extendDrbEntry  22 }


	extendDrbDlBucketSizeDuration		 OBJECT-TYPE
		SYNTAX					 INTEGER{ bsdMs5(0),bsdMs50(1),bsdMs100(2),bsdMs250(3)  }
		MAX-ACCESS			 read-create
		STATUS					 current
		DESCRIPTION			 " -- "
		::=  { extendDrbEntry  23 }


	smallPacketAlgTable		 OBJECT-TYPE
		SYNTAX					 SEQUENCE  OF	 SmallPacketAlgEntry
		MAX-ACCESS			 not-accessible
		STATUS					 current
		DESCRIPTION			 " -- "
		::=  { staticTrafficPara  8 }


	smallPacketAlgEntry		 OBJECT-TYPE
		SYNTAX					 SmallPacketAlgEntry
		MAX-ACCESS			 not-accessible
		STATUS					 current
		DESCRIPTION			 " -- "
		INDEX						{ smallPacketAlgLcid }
		::=  { smallPacketAlgTable  1 }


	SmallPacketAlgEntry		 ::=  SEQUENCE {
		smallPacketAlgLcid					Integer32,
		smallPacketAlgRowStatus					RowStatus,
		smallPacketCheckSwitch					INTEGER,
		smallPacketStasticPeriod					INTEGER,
		smallPacketDlPacketNumberThreshold					Integer32,
		smallPacketUlPacketNumberThreshold					Integer32,
		smallPacketPacketSizeThreshold					Integer32,
		smallPacketStasticRatioThreshold					Integer32,
		smallPacketUlSmallPacketConfluxThreshold					Integer32,
		smallPacketBSREnlargeCoeff					Integer32,
		smallPacketDlSmallPacketConfluxThreshold					Integer32,
		smallPacketDlBoTimeroutReportThreshold					Integer32,
		smallPacketPdcchCceUsedRatioThreshold					Integer32
		}


	smallPacketAlgLcid		 OBJECT-TYPE
		SYNTAX					 Integer32( 0 .. 23 )
		MAX-ACCESS			 not-accessible
		STATUS					 current
		DESCRIPTION			 " -- "
		::=  { smallPacketAlgEntry  1 }


	smallPacketAlgRowStatus		 OBJECT-TYPE
		SYNTAX					 RowStatus
		MAX-ACCESS			 read-create
		STATUS					 current
		DESCRIPTION			 " -- "
		::=  { smallPacketAlgEntry  2 }


	smallPacketCheckSwitch		 OBJECT-TYPE
		SYNTAX					 INTEGER{ off(0),on(1)  }
		MAX-ACCESS			 read-create
		STATUS					 current
		DESCRIPTION			 " -- "
		::=  { smallPacketAlgEntry  3 }


	smallPacketStasticPeriod		 OBJECT-TYPE
		SYNTAX					 INTEGER{ ms300(0),ms400(1),ms500(2),ms600(3),ms700(4),ms800(5),ms900(6),s1(7),s2(8),s3(9),s4(10),s5(11),s6(12),s7(13),s8(14),s9(15),s10(16)  }
		MAX-ACCESS			 read-create
		STATUS					 current
		DESCRIPTION			 " -- "
		::=  { smallPacketAlgEntry  4 }


	smallPacketDlPacketNumberThreshold		 OBJECT-TYPE
		SYNTAX					 Integer32( 0 .. 5000 )
		MAX-ACCESS			 read-create
		STATUS					 current
		DESCRIPTION			 " -- "
		::=  { smallPacketAlgEntry  5 }


	smallPacketUlPacketNumberThreshold		 OBJECT-TYPE
		SYNTAX					 Integer32( 0 .. 5000 )
		MAX-ACCESS			 read-create
		STATUS					 current
		DESCRIPTION			 " -- "
		::=  { smallPacketAlgEntry  6 }


	smallPacketPacketSizeThreshold		 OBJECT-TYPE
		SYNTAX					 Integer32( 100 .. 1000 )
		MAX-ACCESS			 read-create
		STATUS					 current
		DESCRIPTION			 " -- "
		::=  { smallPacketAlgEntry  7 }


	smallPacketStasticRatioThreshold		 OBJECT-TYPE
		SYNTAX					 Integer32( 0 .. 100 )
		MAX-ACCESS			 read-create
		STATUS					 current
		DESCRIPTION			 " -- "
		::=  { smallPacketAlgEntry  8 }


	smallPacketUlSmallPacketConfluxThreshold		 OBJECT-TYPE
		SYNTAX					 Integer32( 0 .. 1000 )
		MAX-ACCESS			 read-create
		STATUS					 current
		DESCRIPTION			 " -- "
		::=  { smallPacketAlgEntry  9 }


	smallPacketBSREnlargeCoeff		 OBJECT-TYPE
		SYNTAX					 Integer32( 110 .. 200 )
		MAX-ACCESS			 read-create
		STATUS					 current
		DESCRIPTION			 " -- "
		::=  { smallPacketAlgEntry  10 }


	smallPacketDlSmallPacketConfluxThreshold		 OBJECT-TYPE
		SYNTAX					 Integer32( 0 .. 1000 )
		MAX-ACCESS			 read-create
		STATUS					 current
		DESCRIPTION			 " -- "
		::=  { smallPacketAlgEntry  11 }


	smallPacketDlBoTimeroutReportThreshold		 OBJECT-TYPE
		SYNTAX					 Integer32( 0 .. 300 )
		MAX-ACCESS			 read-create
		STATUS					 current
		DESCRIPTION			 " -- "
		::=  { smallPacketAlgEntry  12 }


	smallPacketPdcchCceUsedRatioThreshold		 OBJECT-TYPE
		SYNTAX					 Integer32( 0 .. 100 )
		MAX-ACCESS			 read-create
		STATUS					 current
		DESCRIPTION			 " -- "
		::=  { smallPacketAlgEntry  13 }


	adjeNBCell		 OBJECT IDENTIFIER
		::=  { networkElementLayoutPlan  9 }


	cellAdjEutraCellTable		 OBJECT-TYPE
		SYNTAX					 SEQUENCE  OF	 CellAdjEutraCellEntry
		MAX-ACCESS			 not-accessible
		STATUS					 current
		DESCRIPTION			 " -- "
		::=  { adjeNBCell  1 }


	cellAdjEutraCellEntry		 OBJECT-TYPE
		SYNTAX					 CellAdjEutraCellEntry
		MAX-ACCESS			 not-accessible
		STATUS					 current
		DESCRIPTION			 " -- "
		INDEX						{ cellAdjEutraCellIndex }
		::=  { cellAdjEutraCellTable  1 }


	CellAdjEutraCellEntry		 ::=  SEQUENCE {
		cellAdjEutraCellIndex					Integer32,
		cellAdjEutraCellRowStatus					RowStatus,
		cellAdjEutraCellEnbGlobalId					Unsigned32,
		cellAdjEutraCellCellLocalId					Integer32,
		cellAdjEutraCellPhyCellId					Integer32,
		cellAdjEutraCellFreqBand					INTEGER,
		cellAdjEutraCellFreq					Integer32,
		cellAdjEutraCellTac					Integer32,
		cellAdjEutraCellPlmnMcc					MncMccType,
		cellAdjEutraCellPlmnMnc					MncMccType,
		cellAdjEutraCellEARFCN					Integer32,
		cellAdjEutranMultiBandEnhanceFlag					INTEGER,
		cellAdjEutranMultiBandEnhanceManualFlag					INTEGER
		}


	cellAdjEutraCellIndex		 OBJECT-TYPE
		SYNTAX					 Integer32( 0 .. 383 )
		MAX-ACCESS			 not-accessible
		STATUS					 current
		DESCRIPTION			 " -- "
		::=  { cellAdjEutraCellEntry  1 }


	cellAdjEutraCellRowStatus		 OBJECT-TYPE
		SYNTAX					 RowStatus
		MAX-ACCESS			 read-create
		STATUS					 current
		DESCRIPTION			 " -- "
		::=  { cellAdjEutraCellEntry  2 }


	cellAdjEutraCellEnbGlobalId		 OBJECT-TYPE
		SYNTAX					 Unsigned32( 0 .. 1048575 )
		MAX-ACCESS			 read-create
		STATUS					 current
		DESCRIPTION			 " -- "
		::=  { cellAdjEutraCellEntry  3 }


	cellAdjEutraCellCellLocalId		 OBJECT-TYPE
		SYNTAX					 Integer32( 0 .. 255 )
		MAX-ACCESS			 read-create
		STATUS					 current
		DESCRIPTION			 " -- "
		::=  { cellAdjEutraCellEntry  4 }


	cellAdjEutraCellPhyCellId		 OBJECT-TYPE
		SYNTAX					 Integer32( 0 .. 504|65535 )
		MAX-ACCESS			 read-create
		STATUS					 current
		DESCRIPTION			 " -- "
		::=  { cellAdjEutraCellEntry  5 }


	cellAdjEutraCellFreqBand		 OBJECT-TYPE
		SYNTAX					 INTEGER{ band1(1),band2(2),band3(3),band4(4),band5(5),band7(7),band8(8),band9(9),band10(10),band11(11),band12(12),band13(13),band14(14),band17(17),band18(18),band19(19),band20(20),band21(21),band22(22),band23(23),band24(24),band25(25),band26(26),band33(33),band34(34),band35(35),band36(36),band37(37),band38(38),band39(39),band40(40),band41(41),band44(44),band61(61),band62(62)  }
		MAX-ACCESS			 read-create
		STATUS					 current
		DESCRIPTION			 " -- "
		::=  { cellAdjEutraCellEntry  6 }


	cellAdjEutraCellFreq		 OBJECT-TYPE
		SYNTAX					 Integer32( 0 .. 65535 )
		MAX-ACCESS			 read-create
		STATUS					 current
		DESCRIPTION			 " -- "
		::=  { cellAdjEutraCellEntry  7 }


	cellAdjEutraCellTac		 OBJECT-TYPE
		SYNTAX					 Integer32( 0 .. 65535 )
		MAX-ACCESS			 read-create
		STATUS					 current
		DESCRIPTION			 " -- "
		::=  { cellAdjEutraCellEntry  8 }


	cellAdjEutraCellPlmnMcc		 OBJECT-TYPE
		SYNTAX					 MncMccType
		MAX-ACCESS			 read-create
		STATUS					 current
		DESCRIPTION			 " -- "
		::=  { cellAdjEutraCellEntry  9 }


	cellAdjEutraCellPlmnMnc		 OBJECT-TYPE
		SYNTAX					 MncMccType
		MAX-ACCESS			 read-create
		STATUS					 current
		DESCRIPTION			 " -- "
		::=  { cellAdjEutraCellEntry  10 }


	cellAdjEutraCellEARFCN		 OBJECT-TYPE
		SYNTAX					 Integer32( 0 .. 65535 )
		MAX-ACCESS			 read-only
		STATUS					 current
		DESCRIPTION			 " -- "
		::=  { cellAdjEutraCellEntry  12 }


	cellAdjEutranMultiBandEnhanceFlag		 OBJECT-TYPE
		SYNTAX					 INTEGER{ nobroadcaste(0),broadcasted(1),noSupport(2)  }
		MAX-ACCESS			 read-only
		STATUS					 current
		DESCRIPTION			 " -- "
		::=  { cellAdjEutraCellEntry  14 }


	cellAdjEutranMultiBandEnhanceManualFlag		 OBJECT-TYPE
		SYNTAX					 INTEGER{ nobroadcaste(0),broadcasted(1),noSupport(2)  }
		MAX-ACCESS			 read-create
		STATUS					 current
		DESCRIPTION			 " -- "
		::=  { cellAdjEutraCellEntry  15 }


	cellAdjUtraFddCellTable		 OBJECT-TYPE
		SYNTAX					 SEQUENCE  OF	 CellAdjUtraFddCellEntry
		MAX-ACCESS			 not-accessible
		STATUS					 current
		DESCRIPTION			 " -- "
		::=  { adjeNBCell  2 }


	cellAdjUtraFddCellEntry		 OBJECT-TYPE
		SYNTAX					 CellAdjUtraFddCellEntry
		MAX-ACCESS			 not-accessible
		STATUS					 current
		DESCRIPTION			 " -- "
		INDEX						{ cellAdjUtraFddCellIndex }
		::=  { cellAdjUtraFddCellTable  1 }


	CellAdjUtraFddCellEntry		 ::=  SEQUENCE {
		cellAdjUtraFddCellIndex					Integer32,
		cellAdjUtraFddCellRowStatus					RowStatus,
		cellAdjUtraFddCellArfcn					Integer32,
		cellAdjUtraFddCellPhyCellId					Integer32,
		cellAdjUtraFddCellCellId					Unsigned32,
		cellAdjUtraFddCellLAC					Integer32,
		cellAdjUtraFddCellRAC					Integer32,
		cellAdjUtraFddCellPlmnMcc					MncMccType,
		cellAdjUtraFddCellPlmnMnc					MncMccType,
		cellAdjUtraFddCellRncId					Integer32,
		cellAdjUtraFddDirectTunnelFlag					INTEGER,
		cellAdjUtraFddCellRacFlag					INTEGER,
		cellAdjUtraFddCellRim					INTEGER
		}


	cellAdjUtraFddCellIndex		 OBJECT-TYPE
		SYNTAX					 Integer32( 0 .. 191 )
		MAX-ACCESS			 not-accessible
		STATUS					 current
		DESCRIPTION			 " -- "
		::=  { cellAdjUtraFddCellEntry  1 }


	cellAdjUtraFddCellRowStatus		 OBJECT-TYPE
		SYNTAX					 RowStatus
		MAX-ACCESS			 read-create
		STATUS					 current
		DESCRIPTION			 " -- "
		::=  { cellAdjUtraFddCellEntry  2 }


	cellAdjUtraFddCellArfcn		 OBJECT-TYPE
		SYNTAX					 Integer32( 0 .. 16383 )
		MAX-ACCESS			 read-create
		STATUS					 current
		DESCRIPTION			 " -- "
		::=  { cellAdjUtraFddCellEntry  3 }


	cellAdjUtraFddCellPhyCellId		 OBJECT-TYPE
		SYNTAX					 Integer32( 0 .. 511 )
		MAX-ACCESS			 read-create
		STATUS					 current
		DESCRIPTION			 " -- "
		::=  { cellAdjUtraFddCellEntry  4 }


	cellAdjUtraFddCellCellId		 OBJECT-TYPE
		SYNTAX					 Unsigned32( 0 .. 65535 )
		MAX-ACCESS			 read-create
		STATUS					 current
		DESCRIPTION			 " -- "
		::=  { cellAdjUtraFddCellEntry  5 }


	cellAdjUtraFddCellLAC		 OBJECT-TYPE
		SYNTAX					 Integer32( 0 .. 65535 )
		MAX-ACCESS			 read-create
		STATUS					 current
		DESCRIPTION			 " -- "
		::=  { cellAdjUtraFddCellEntry  6 }


	cellAdjUtraFddCellRAC		 OBJECT-TYPE
		SYNTAX					 Integer32( 0 .. 255 )
		MAX-ACCESS			 read-create
		STATUS					 current
		DESCRIPTION			 " -- "
		::=  { cellAdjUtraFddCellEntry  7 }


	cellAdjUtraFddCellPlmnMcc		 OBJECT-TYPE
		SYNTAX					 MncMccType
		MAX-ACCESS			 read-create
		STATUS					 current
		DESCRIPTION			 " -- "
		::=  { cellAdjUtraFddCellEntry  8 }


	cellAdjUtraFddCellPlmnMnc		 OBJECT-TYPE
		SYNTAX					 MncMccType
		MAX-ACCESS			 read-create
		STATUS					 current
		DESCRIPTION			 " -- "
		::=  { cellAdjUtraFddCellEntry  9 }


	cellAdjUtraFddCellRncId		 OBJECT-TYPE
		SYNTAX					 Integer32( 0 .. 65535 )
		MAX-ACCESS			 read-create
		STATUS					 current
		DESCRIPTION			 " -- "
		::=  { cellAdjUtraFddCellEntry  10 }


	cellAdjUtraFddDirectTunnelFlag		 OBJECT-TYPE
		SYNTAX					 INTEGER{ false(0),true(1)  }
		MAX-ACCESS			 read-create
		STATUS					 current
		DESCRIPTION			 " -- "
		::=  { cellAdjUtraFddCellEntry  11 }


	cellAdjUtraFddCellRacFlag		 OBJECT-TYPE
		SYNTAX					 INTEGER{ false(0),true(1)  }
		MAX-ACCESS			 read-create
		STATUS					 current
		DESCRIPTION			 " -- "
		::=  { cellAdjUtraFddCellEntry  12 }


	cellAdjUtraFddCellRim		 OBJECT-TYPE
		SYNTAX					 INTEGER{ false(0),true(1)  }
		MAX-ACCESS			 read-create
		STATUS					 current
		DESCRIPTION			 " -- "
		::=  { cellAdjUtraFddCellEntry  13 }


	cellAdjUtraTddCellTable		 OBJECT-TYPE
		SYNTAX					 SEQUENCE  OF	 CellAdjUtraTddCellEntry
		MAX-ACCESS			 not-accessible
		STATUS					 current
		DESCRIPTION			 " -- "
		::=  { adjeNBCell  3 }


	cellAdjUtraTddCellEntry		 OBJECT-TYPE
		SYNTAX					 CellAdjUtraTddCellEntry
		MAX-ACCESS			 not-accessible
		STATUS					 current
		DESCRIPTION			 " -- "
		INDEX						{ cellAdjUtraTddCellIndex }
		::=  { cellAdjUtraTddCellTable  1 }


	CellAdjUtraTddCellEntry		 ::=  SEQUENCE {
		cellAdjUtraTddCellIndex					Integer32,
		cellAdjUtraTddCellRowStatus					RowStatus,
		cellAdjUtraTddCellArfcn					Integer32,
		cellAdjUtraTddCellPhyCellId					Integer32,
		cellAdjUtraTddCellCellId					Unsigned32,
		cellAdjUtraTddCellLAC					Integer32,
		cellAdjUtraTddCellRAC					Integer32,
		cellAdjUtraTddCellPlmnMcc					MncMccType,
		cellAdjUtraTddCellPlmnMnc					MncMccType,
		cellAdjUtraTddCellRncId					Integer32,
		cellAdjUtraTddDirectTunnelFlag					INTEGER,
		cellAdjUtraTddCellRacFlag					INTEGER,
		cellAdjUtraTddCellRim					INTEGER
		}


	cellAdjUtraTddCellIndex		 OBJECT-TYPE
		SYNTAX					 Integer32( 0 .. 191 )
		MAX-ACCESS			 not-accessible
		STATUS					 current
		DESCRIPTION			 " -- "
		::=  { cellAdjUtraTddCellEntry  1 }


	cellAdjUtraTddCellRowStatus		 OBJECT-TYPE
		SYNTAX					 RowStatus
		MAX-ACCESS			 read-create
		STATUS					 current
		DESCRIPTION			 " -- "
		::=  { cellAdjUtraTddCellEntry  2 }


	cellAdjUtraTddCellArfcn		 OBJECT-TYPE
		SYNTAX					 Integer32( 0 .. 16383 )
		MAX-ACCESS			 read-create
		STATUS					 current
		DESCRIPTION			 " -- "
		::=  { cellAdjUtraTddCellEntry  3 }


	cellAdjUtraTddCellPhyCellId		 OBJECT-TYPE
		SYNTAX					 Integer32( 0 .. 127 )
		MAX-ACCESS			 read-create
		STATUS					 current
		DESCRIPTION			 " -- "
		::=  { cellAdjUtraTddCellEntry  4 }


	cellAdjUtraTddCellCellId		 OBJECT-TYPE
		SYNTAX					 Unsigned32( 0 .. 65535 )
		MAX-ACCESS			 read-create
		STATUS					 current
		DESCRIPTION			 " -- "
		::=  { cellAdjUtraTddCellEntry  5 }


	cellAdjUtraTddCellLAC		 OBJECT-TYPE
		SYNTAX					 Integer32( 0 .. 65535 )
		MAX-ACCESS			 read-create
		STATUS					 current
		DESCRIPTION			 " -- "
		::=  { cellAdjUtraTddCellEntry  6 }


	cellAdjUtraTddCellRAC		 OBJECT-TYPE
		SYNTAX					 Integer32( 0 .. 255 )
		MAX-ACCESS			 read-create
		STATUS					 current
		DESCRIPTION			 " -- "
		::=  { cellAdjUtraTddCellEntry  7 }


	cellAdjUtraTddCellPlmnMcc		 OBJECT-TYPE
		SYNTAX					 MncMccType
		MAX-ACCESS			 read-create
		STATUS					 current
		DESCRIPTION			 " -- "
		::=  { cellAdjUtraTddCellEntry  8 }


	cellAdjUtraTddCellPlmnMnc		 OBJECT-TYPE
		SYNTAX					 MncMccType
		MAX-ACCESS			 read-create
		STATUS					 current
		DESCRIPTION			 " -- "
		::=  { cellAdjUtraTddCellEntry  9 }


	cellAdjUtraTddCellRncId		 OBJECT-TYPE
		SYNTAX					 Integer32( 0 .. 65535 )
		MAX-ACCESS			 read-create
		STATUS					 current
		DESCRIPTION			 " -- "
		::=  { cellAdjUtraTddCellEntry  10 }


	cellAdjUtraTddDirectTunnelFlag		 OBJECT-TYPE
		SYNTAX					 INTEGER{ false(0),true(1)  }
		MAX-ACCESS			 read-create
		STATUS					 current
		DESCRIPTION			 " -- "
		::=  { cellAdjUtraTddCellEntry  11 }


	cellAdjUtraTddCellRacFlag		 OBJECT-TYPE
		SYNTAX					 INTEGER{ false(0),true(1)  }
		MAX-ACCESS			 read-create
		STATUS					 current
		DESCRIPTION			 " -- "
		::=  { cellAdjUtraTddCellEntry  12 }


	cellAdjUtraTddCellRim		 OBJECT-TYPE
		SYNTAX					 INTEGER{ false(0),true(1)  }
		MAX-ACCESS			 read-create
		STATUS					 current
		DESCRIPTION			 " -- "
		::=  { cellAdjUtraTddCellEntry  13 }


	cellAdjGeranCellTable		 OBJECT-TYPE
		SYNTAX					 SEQUENCE  OF	 CellAdjGeranCellEntry
		MAX-ACCESS			 not-accessible
		STATUS					 current
		DESCRIPTION			 " -- "
		::=  { adjeNBCell  4 }


	cellAdjGeranCellEntry		 OBJECT-TYPE
		SYNTAX					 CellAdjGeranCellEntry
		MAX-ACCESS			 not-accessible
		STATUS					 current
		DESCRIPTION			 " -- "
		INDEX						{ cellAdjGeranCellIndex }
		::=  { cellAdjGeranCellTable  1 }


	CellAdjGeranCellEntry		 ::=  SEQUENCE {
		cellAdjGeranCellIndex					Integer32,
		cellAdjGeranCellRowStatus					RowStatus,
		cellAdjGeranCellNetworkColourCode					Integer32,
		cellAdjGeranCellBasestationColourCode					Integer32,
		cellAdjGeranCellLAC					Integer32,
		cellAdjGeranCellCellId					Integer32,
		cellAdjGeranCellRAC					Integer32,
		cellAdjGeranCellArfcn					Integer32,
		cellAdjGeranBandIndicator					INTEGER,
		cellAdjGeranPlmnMcc					MncMccType,
		cellAdjGeranPlmnMnc					MncMccType,
		cellAdjGeranCellRimFlag					INTEGER,
		cellAdjGeranPsHcFlag					INTEGER,
		cellAdjGeranDirectTunnelFlag					INTEGER,
		cellAdjGeranCellRacFlag					INTEGER,
		cellAdjGeranNetworkControlOrder					INTEGER
		}


	cellAdjGeranCellIndex		 OBJECT-TYPE
		SYNTAX					 Integer32( 0 .. 191 )
		MAX-ACCESS			 not-accessible
		STATUS					 current
		DESCRIPTION			 " -- "
		::=  { cellAdjGeranCellEntry  1 }


	cellAdjGeranCellRowStatus		 OBJECT-TYPE
		SYNTAX					 RowStatus
		MAX-ACCESS			 read-create
		STATUS					 current
		DESCRIPTION			 " -- "
		::=  { cellAdjGeranCellEntry  2 }


	cellAdjGeranCellNetworkColourCode		 OBJECT-TYPE
		SYNTAX					 Integer32( 0 .. 7 )
		MAX-ACCESS			 read-create
		STATUS					 current
		DESCRIPTION			 " -- "
		::=  { cellAdjGeranCellEntry  3 }


	cellAdjGeranCellBasestationColourCode		 OBJECT-TYPE
		SYNTAX					 Integer32( 0 .. 7 )
		MAX-ACCESS			 read-create
		STATUS					 current
		DESCRIPTION			 " -- "
		::=  { cellAdjGeranCellEntry  4 }


	cellAdjGeranCellLAC		 OBJECT-TYPE
		SYNTAX					 Integer32( 0 .. 65535 )
		MAX-ACCESS			 read-create
		STATUS					 current
		DESCRIPTION			 " -- "
		::=  { cellAdjGeranCellEntry  5 }


	cellAdjGeranCellCellId		 OBJECT-TYPE
		SYNTAX					 Integer32( 0 .. 65535 )
		MAX-ACCESS			 read-create
		STATUS					 current
		DESCRIPTION			 " -- "
		::=  { cellAdjGeranCellEntry  6 }


	cellAdjGeranCellRAC		 OBJECT-TYPE
		SYNTAX					 Integer32( 0 .. 255 )
		MAX-ACCESS			 read-create
		STATUS					 current
		DESCRIPTION			 " -- "
		::=  { cellAdjGeranCellEntry  7 }


	cellAdjGeranCellArfcn		 OBJECT-TYPE
		SYNTAX					 Integer32( 0 .. 1023 )
		MAX-ACCESS			 read-create
		STATUS					 current
		DESCRIPTION			 " -- "
		::=  { cellAdjGeranCellEntry  8 }


	cellAdjGeranBandIndicator		 OBJECT-TYPE
		SYNTAX					 INTEGER{ dcs1800(0),pcs1900(1)  }
		MAX-ACCESS			 read-create
		STATUS					 current
		DESCRIPTION			 " -- "
		::=  { cellAdjGeranCellEntry  9 }


	cellAdjGeranPlmnMcc		 OBJECT-TYPE
		SYNTAX					 MncMccType
		MAX-ACCESS			 read-create
		STATUS					 current
		DESCRIPTION			 " -- "
		::=  { cellAdjGeranCellEntry  10 }


	cellAdjGeranPlmnMnc		 OBJECT-TYPE
		SYNTAX					 MncMccType
		MAX-ACCESS			 read-create
		STATUS					 current
		DESCRIPTION			 " -- "
		::=  { cellAdjGeranCellEntry  11 }


	cellAdjGeranCellRimFlag		 OBJECT-TYPE
		SYNTAX					 INTEGER{ false(0),true(1)  }
		MAX-ACCESS			 read-create
		STATUS					 current
		DESCRIPTION			 " -- "
		::=  { cellAdjGeranCellEntry  12 }


	cellAdjGeranPsHcFlag		 OBJECT-TYPE
		SYNTAX					 INTEGER{ false(0),true(1)  }
		MAX-ACCESS			 read-create
		STATUS					 current
		DESCRIPTION			 " -- "
		::=  { cellAdjGeranCellEntry  13 }


	cellAdjGeranDirectTunnelFlag		 OBJECT-TYPE
		SYNTAX					 INTEGER{ false(0),true(1)  }
		MAX-ACCESS			 read-create
		STATUS					 current
		DESCRIPTION			 " -- "
		::=  { cellAdjGeranCellEntry  14 }


	cellAdjGeranCellRacFlag		 OBJECT-TYPE
		SYNTAX					 INTEGER{ false(0),true(1)  }
		MAX-ACCESS			 read-create
		STATUS					 current
		DESCRIPTION			 " -- "
		::=  { cellAdjGeranCellEntry  15 }


	cellAdjGeranNetworkControlOrder		 OBJECT-TYPE
		SYNTAX					 INTEGER{ nc0(0),nc1(1),nc2(2),reset(3)  }
		MAX-ACCESS			 read-create
		STATUS					 current
		DESCRIPTION			 " -- "
		::=  { cellAdjGeranCellEntry  16 }


	cellAdjCdma2000CellTable		 OBJECT-TYPE
		SYNTAX					 SEQUENCE  OF	 CellAdjCdma2000CellEntry
		MAX-ACCESS			 not-accessible
		STATUS					 current
		DESCRIPTION			 " -- "
		::=  { adjeNBCell  5 }


	cellAdjCdma2000CellEntry		 OBJECT-TYPE
		SYNTAX					 CellAdjCdma2000CellEntry
		MAX-ACCESS			 not-accessible
		STATUS					 current
		DESCRIPTION			 " -- "
		INDEX						{ cellAdjCdma2000CellIndex }
		::=  { cellAdjCdma2000CellTable  1 }


	CellAdjCdma2000CellEntry		 ::=  SEQUENCE {
		cellAdjCdma2000CellIndex					Integer32,
		cellAdjCdma2000CellRowStatus					RowStatus,
		cellAdjCdma2000CellArfcn					Integer32,
		cellAdjCdma2000CellPhyCellId					Integer32,
		cellAdjCdma2000CellType					INTEGER,
		cellAdjCdma2000CellBandclass					INTEGER
		}


	cellAdjCdma2000CellIndex		 OBJECT-TYPE
		SYNTAX					 Integer32( 0 .. 191 )
		MAX-ACCESS			 not-accessible
		STATUS					 current
		DESCRIPTION			 " -- "
		::=  { cellAdjCdma2000CellEntry  1 }


	cellAdjCdma2000CellRowStatus		 OBJECT-TYPE
		SYNTAX					 RowStatus
		MAX-ACCESS			 read-create
		STATUS					 current
		DESCRIPTION			 " -- "
		::=  { cellAdjCdma2000CellEntry  2 }


	cellAdjCdma2000CellArfcn		 OBJECT-TYPE
		SYNTAX					 Integer32( 0 .. 2047 )
		MAX-ACCESS			 read-create
		STATUS					 current
		DESCRIPTION			 " -- "
		::=  { cellAdjCdma2000CellEntry  3 }


	cellAdjCdma2000CellPhyCellId		 OBJECT-TYPE
		SYNTAX					 Integer32( 0 .. 511 )
		MAX-ACCESS			 read-create
		STATUS					 current
		DESCRIPTION			 " -- "
		::=  { cellAdjCdma2000CellEntry  4 }


	cellAdjCdma2000CellType		 OBJECT-TYPE
		SYNTAX					 INTEGER{ type1XRTT(0),typeHRPD(1)  }
		MAX-ACCESS			 read-create
		STATUS					 current
		DESCRIPTION			 " -- "
		::=  { cellAdjCdma2000CellEntry  5 }


	cellAdjCdma2000CellBandclass		 OBJECT-TYPE
		SYNTAX					 INTEGER{ bc0(0),bc1(1),bc2(2),bc3(3),bc4(4),bc5(5),bc6(6),bc7(7),bc8(8),bc9(9),bc10(10),bc11(11),bc12(12),bc13(13),bc14(14),bc15(15),bc16(16),bc17(17)  }
		MAX-ACCESS			 read-create
		STATUS					 current
		DESCRIPTION			 " -- "
		::=  { cellAdjCdma2000CellEntry  12 }


	adjeNB		 OBJECT IDENTIFIER
		::=  { networkElementLayoutPlan  10 }


	adjeNBTable		 OBJECT-TYPE
		SYNTAX					 SEQUENCE  OF	 AdjeNBEntry
		MAX-ACCESS			 not-accessible
		STATUS					 current
		DESCRIPTION			 " -- "
		::=  { adjeNB  1 }


	adjeNBEntry		 OBJECT-TYPE
		SYNTAX					 AdjeNBEntry
		MAX-ACCESS			 not-accessible
		STATUS					 current
		DESCRIPTION			 " -- "
		INDEX						{ adjeNBIndex }
		::=  { adjeNBTable  1 }


	AdjeNBEntry		 ::=  SEQUENCE {
		adjeNBIndex					Integer32,
		adjeNBRowStatus					RowStatus,
		adjeNBGlobalId					Unsigned32,
		adjeNBPlmnMcc					MncMccType,
		adjeNBPlmnMnc					MncMccType,
		adjeNBMmeGroupId1					Integer32,
		adjeNBMmeGroupId2					Integer32,
		adjeNBMmeGroupId3					Integer32,
		adjeNBMmeGroupId4					Integer32,
		adjeNBMmeGroupId5					Integer32,
		adjeNBMmeGroupId6					Integer32,
		adjeNBMmeGroupId7					Integer32,
		adjeNBMmeGroupId8					Integer32,
		adjeNBMmeGroupId9					Integer32,
		adjeNBMmeGroupId10					Integer32,
		adjeNBMmeGroupId11					Integer32,
		adjeNBMmeGroupId12					Integer32,
		adjeNBMmeGroupId13					Integer32,
		adjeNBMmeGroupId14					Integer32,
		adjeNBMmeGroupId15					Integer32,
		adjeNBMmeGroupId16					Integer32,
		adjeNBSctpIndex					Integer32
		}


	adjeNBIndex		 OBJECT-TYPE
		SYNTAX					 Integer32( 0 .. 127 )
		MAX-ACCESS			 not-accessible
		STATUS					 current
		DESCRIPTION			 " -- "
		::=  { adjeNBEntry  1 }


	adjeNBRowStatus		 OBJECT-TYPE
		SYNTAX					 RowStatus
		MAX-ACCESS			 read-create
		STATUS					 current
		DESCRIPTION			 " -- "
		::=  { adjeNBEntry  2 }


	adjeNBGlobalId		 OBJECT-TYPE
		SYNTAX					 Unsigned32( 0 .. 1048575 )
		MAX-ACCESS			 read-create
		STATUS					 current
		DESCRIPTION			 " -- "
		::=  { adjeNBEntry  3 }


	adjeNBPlmnMcc		 OBJECT-TYPE
		SYNTAX					 MncMccType
		MAX-ACCESS			 read-create
		STATUS					 current
		DESCRIPTION			 " -- "
		::=  { adjeNBEntry  4 }


	adjeNBPlmnMnc		 OBJECT-TYPE
		SYNTAX					 MncMccType
		MAX-ACCESS			 read-create
		STATUS					 current
		DESCRIPTION			 " -- "
		::=  { adjeNBEntry  5 }


	adjeNBMmeGroupId1		 OBJECT-TYPE
		SYNTAX					 Integer32( 0 .. 65535|-1 )
		MAX-ACCESS			 read-create
		STATUS					 current
		DESCRIPTION			 " -- "
		::=  { adjeNBEntry  6 }


	adjeNBMmeGroupId2		 OBJECT-TYPE
		SYNTAX					 Integer32( 0 .. 65535|-1 )
		MAX-ACCESS			 read-create
		STATUS					 current
		DESCRIPTION			 " -- "
		::=  { adjeNBEntry  7 }


	adjeNBMmeGroupId3		 OBJECT-TYPE
		SYNTAX					 Integer32( 0 .. 65535|-1 )
		MAX-ACCESS			 read-create
		STATUS					 current
		DESCRIPTION			 " -- "
		::=  { adjeNBEntry  8 }


	adjeNBMmeGroupId4		 OBJECT-TYPE
		SYNTAX					 Integer32( 0 .. 65535|-1 )
		MAX-ACCESS			 read-create
		STATUS					 current
		DESCRIPTION			 " -- "
		::=  { adjeNBEntry  9 }


	adjeNBMmeGroupId5		 OBJECT-TYPE
		SYNTAX					 Integer32( 0 .. 65535|-1 )
		MAX-ACCESS			 read-create
		STATUS					 current
		DESCRIPTION			 " -- "
		::=  { adjeNBEntry  10 }


	adjeNBMmeGroupId6		 OBJECT-TYPE
		SYNTAX					 Integer32( 0 .. 65535|-1 )
		MAX-ACCESS			 read-create
		STATUS					 current
		DESCRIPTION			 " -- "
		::=  { adjeNBEntry  11 }


	adjeNBMmeGroupId7		 OBJECT-TYPE
		SYNTAX					 Integer32( 0 .. 65535|-1 )
		MAX-ACCESS			 read-create
		STATUS					 current
		DESCRIPTION			 " -- "
		::=  { adjeNBEntry  12 }


	adjeNBMmeGroupId8		 OBJECT-TYPE
		SYNTAX					 Integer32( 0 .. 65535|-1 )
		MAX-ACCESS			 read-create
		STATUS					 current
		DESCRIPTION			 " -- "
		::=  { adjeNBEntry  13 }


	adjeNBMmeGroupId9		 OBJECT-TYPE
		SYNTAX					 Integer32( 0 .. 65535|-1 )
		MAX-ACCESS			 read-create
		STATUS					 current
		DESCRIPTION			 " -- "
		::=  { adjeNBEntry  14 }


	adjeNBMmeGroupId10		 OBJECT-TYPE
		SYNTAX					 Integer32( 0 .. 65535|-1 )
		MAX-ACCESS			 read-create
		STATUS					 current
		DESCRIPTION			 " -- "
		::=  { adjeNBEntry  15 }


	adjeNBMmeGroupId11		 OBJECT-TYPE
		SYNTAX					 Integer32( 0 .. 65535|-1 )
		MAX-ACCESS			 read-create
		STATUS					 current
		DESCRIPTION			 " -- "
		::=  { adjeNBEntry  16 }


	adjeNBMmeGroupId12		 OBJECT-TYPE
		SYNTAX					 Integer32( 0 .. 65535|-1 )
		MAX-ACCESS			 read-create
		STATUS					 current
		DESCRIPTION			 " -- "
		::=  { adjeNBEntry  17 }


	adjeNBMmeGroupId13		 OBJECT-TYPE
		SYNTAX					 Integer32( 0 .. 65535|-1 )
		MAX-ACCESS			 read-create
		STATUS					 current
		DESCRIPTION			 " -- "
		::=  { adjeNBEntry  18 }


	adjeNBMmeGroupId14		 OBJECT-TYPE
		SYNTAX					 Integer32( 0 .. 65535|-1 )
		MAX-ACCESS			 read-create
		STATUS					 current
		DESCRIPTION			 " -- "
		::=  { adjeNBEntry  19 }


	adjeNBMmeGroupId15		 OBJECT-TYPE
		SYNTAX					 Integer32( 0 .. 65535|-1 )
		MAX-ACCESS			 read-create
		STATUS					 current
		DESCRIPTION			 " -- "
		::=  { adjeNBEntry  20 }


	adjeNBMmeGroupId16		 OBJECT-TYPE
		SYNTAX					 Integer32( 0 .. 65535|-1 )
		MAX-ACCESS			 read-create
		STATUS					 current
		DESCRIPTION			 " -- "
		::=  { adjeNBEntry  21 }


	adjeNBSctpIndex		 OBJECT-TYPE
		SYNTAX					 Integer32( 0 .. 81|255 )
		MAX-ACCESS			 read-only
		STATUS					 current
		DESCRIPTION			 " -- "
		::=  { adjeNBEntry  22 }


	globalAlgorithm		 OBJECT IDENTIFIER
		::=  { networkElementLayoutPlan  11 }


	encryptAlgorithmTable		 OBJECT-TYPE
		SYNTAX					 SEQUENCE  OF	 EncryptAlgorithmEntry
		MAX-ACCESS			 not-accessible
		STATUS					 current
		DESCRIPTION			 " -- "
		::=  { globalAlgorithm  1 }


	encryptAlgorithmEntry		 OBJECT-TYPE
		SYNTAX					 EncryptAlgorithmEntry
		MAX-ACCESS			 not-accessible
		STATUS					 current
		DESCRIPTION			 " -- "
		INDEX						{ encryptAlgorithmIndex }
		::=  { encryptAlgorithmTable  1 }


	EncryptAlgorithmEntry		 ::=  SEQUENCE {
		encryptAlgorithmIndex					Integer32,
		encryptAlgorithmRowStatus					RowStatus,
		encryptAlgorithmType					INTEGER,
		encryptAlgorithmPriority					Integer32
		}


	encryptAlgorithmIndex		 OBJECT-TYPE
		SYNTAX					 Integer32( 0 .. 3 )
		MAX-ACCESS			 not-accessible
		STATUS					 current
		DESCRIPTION			 " -- "
		::=  { encryptAlgorithmEntry  1 }


	encryptAlgorithmRowStatus		 OBJECT-TYPE
		SYNTAX					 RowStatus
		MAX-ACCESS			 read-create
		STATUS					 current
		DESCRIPTION			 " -- "
		::=  { encryptAlgorithmEntry  2 }


	encryptAlgorithmType		 OBJECT-TYPE
		SYNTAX					 INTEGER{ eea0(0),eea1(1),eea2(2),eea3(3)  }
		MAX-ACCESS			 read-create
		STATUS					 current
		DESCRIPTION			 " -- "
		::=  { encryptAlgorithmEntry  3 }


	encryptAlgorithmPriority		 OBJECT-TYPE
		SYNTAX					 Integer32( 0 .. 3 )
		MAX-ACCESS			 read-create
		STATUS					 current
		DESCRIPTION			 " -- "
		::=  { encryptAlgorithmEntry  4 }


	integrityAlgorithmTable		 OBJECT-TYPE
		SYNTAX					 SEQUENCE  OF	 IntegrityAlgorithmEntry
		MAX-ACCESS			 not-accessible
		STATUS					 current
		DESCRIPTION			 " -- "
		::=  { globalAlgorithm  2 }


	integrityAlgorithmEntry		 OBJECT-TYPE
		SYNTAX					 IntegrityAlgorithmEntry
		MAX-ACCESS			 not-accessible
		STATUS					 current
		DESCRIPTION			 " -- "
		INDEX						{ integrityAlgorithmIndex }
		::=  { integrityAlgorithmTable  1 }


	IntegrityAlgorithmEntry		 ::=  SEQUENCE {
		integrityAlgorithmIndex					Integer32,
		integrityAlgorithmRowStatus					RowStatus,
		integrityAlgorithmType					INTEGER,
		integrityAlgorithmPriority					Integer32
		}


	integrityAlgorithmIndex		 OBJECT-TYPE
		SYNTAX					 Integer32( 0 .. 3 )
		MAX-ACCESS			 not-accessible
		STATUS					 current
		DESCRIPTION			 " -- "
		::=  { integrityAlgorithmEntry  1 }


	integrityAlgorithmRowStatus		 OBJECT-TYPE
		SYNTAX					 RowStatus
		MAX-ACCESS			 read-create
		STATUS					 current
		DESCRIPTION			 " -- "
		::=  { integrityAlgorithmEntry  2 }


	integrityAlgorithmType		 OBJECT-TYPE
		SYNTAX					 INTEGER{ eia0(0),eia1(1),eia2(2),eia3(3)  }
		MAX-ACCESS			 read-create
		STATUS					 current
		DESCRIPTION			 " -- "
		::=  { integrityAlgorithmEntry  3 }


	integrityAlgorithmPriority		 OBJECT-TYPE
		SYNTAX					 Integer32( 0 .. 3 )
		MAX-ACCESS			 read-create
		STATUS					 current
		DESCRIPTION			 " -- "
		::=  { integrityAlgorithmEntry  4 }


	anrAlgorithmInfo		 OBJECT IDENTIFIER
		::=  { globalAlgorithm  3 }


	anrAlgorithmSwitch		 OBJECT-TYPE
		SYNTAX					 INTEGER{ off(0),on(1)  }
		MAX-ACCESS			 read-write
		STATUS					 current
		DESCRIPTION			 " -- "
		::=  { anrAlgorithmInfo  1 }


	anrRemoveSwitch		 OBJECT-TYPE
		SYNTAX					 INTEGER{ off(0),on(1)  }
		MAX-ACCESS			 read-write
		STATUS					 current
		DESCRIPTION			 " -- "
		::=  { anrAlgorithmInfo  2 }


	anrMeasRsrpTh		 OBJECT-TYPE
		SYNTAX					 Unsigned32( 0 .. 97 )
		MAX-ACCESS			 read-write
		STATUS					 current
		DESCRIPTION			 " -- "
		::=  { anrAlgorithmInfo  3 }


	anrRemThForActiveTimes		 OBJECT-TYPE
		SYNTAX					 Unsigned32( 0 .. 1048575 )
		MAX-ACCESS			 read-write
		STATUS					 current
		DESCRIPTION			 " -- "
		::=  { anrAlgorithmInfo  4 }


	anrExUeNum		 OBJECT-TYPE
		SYNTAX					 Integer32( 0 .. 1000 )
		MAX-ACCESS			 read-write
		STATUS					 current
		DESCRIPTION			 " -- "
		::=  { anrAlgorithmInfo  5 }


	anrRemoveInterRatSwitch		 OBJECT-TYPE
		SYNTAX					 INTEGER{ off(0),on(1)  }
		MAX-ACCESS			 read-write
		STATUS					 current
		DESCRIPTION			 " -- "
		::=  { anrAlgorithmInfo  7 }


	anrRemThForActiveTimesInterRat		 OBJECT-TYPE
		SYNTAX					 Unsigned32( 0 .. 1048575 )
		MAX-ACCESS			 read-write
		STATUS					 current
		DESCRIPTION			 " -- "
		::=  { anrAlgorithmInfo  8 }


	anrMode		 OBJECT-TYPE
		SYNTAX					 INTEGER{ controlled(0),selfOpt(1)  }
		MAX-ACCESS			 read-write
		STATUS					 current
		DESCRIPTION			 " -- "
		::=  { anrAlgorithmInfo  9 }


	anrMeasRscpTh		 OBJECT-TYPE
		SYNTAX					 Integer32( -5 .. 91 )
		MAX-ACCESS			 read-write
		STATUS					 current
		DESCRIPTION			 " -- "
		::=  { anrAlgorithmInfo  10 }


	anrMeasEcnoTh		 OBJECT-TYPE
		SYNTAX					 Unsigned32( 0 .. 49 )
		MAX-ACCESS			 read-write
		STATUS					 current
		DESCRIPTION			 " -- "
		::=  { anrAlgorithmInfo  11 }


	anrMeasRssiTh		 OBJECT-TYPE
		SYNTAX					 Unsigned32( 0 .. 76 )
		MAX-ACCESS			 read-write
		STATUS					 current
		DESCRIPTION			 " -- "
		::=  { anrAlgorithmInfo  12 }


	anrTestAdjrelationNum		 OBJECT-TYPE
		SYNTAX					 Unsigned32( 0 .. 256 )
		MAX-ACCESS			 read-write
		STATUS					 current
		DESCRIPTION			 " -- "
		::=  { anrAlgorithmInfo  13 }


	anrSonMeas2GSwitch		 OBJECT-TYPE
		SYNTAX					 INTEGER{ off(0),on(1)  }
		MAX-ACCESS			 read-write
		STATUS					 current
		DESCRIPTION			 " -- "
		::=  { anrAlgorithmInfo  14 }


	anrSonMeas3GSwitch		 OBJECT-TYPE
		SYNTAX					 INTEGER{ off(0),on(1)  }
		MAX-ACCESS			 read-write
		STATUS					 current
		DESCRIPTION			 " -- "
		::=  { anrAlgorithmInfo  15 }


	anrMode2G		 OBJECT-TYPE
		SYNTAX					 INTEGER{ controlled(0),selfOpt(1)  }
		MAX-ACCESS			 read-write
		STATUS					 current
		DESCRIPTION			 " -- "
		::=  { anrAlgorithmInfo  16 }


	anrMode3G		 OBJECT-TYPE
		SYNTAX					 INTEGER{ controlled(0),selfOpt(1)  }
		MAX-ACCESS			 read-write
		STATUS					 current
		DESCRIPTION			 " -- "
		::=  { anrAlgorithmInfo  17 }


	anr2GAdjrelationNum		 OBJECT-TYPE
		SYNTAX					 Unsigned32( 0 .. 192 )
		MAX-ACCESS			 read-write
		STATUS					 current
		DESCRIPTION			 " -- "
		::=  { anrAlgorithmInfo  18 }


	anr3GAdjrelationNum		 OBJECT-TYPE
		SYNTAX					 Unsigned32( 0 .. 192 )
		MAX-ACCESS			 read-write
		STATUS					 current
		DESCRIPTION			 " -- "
		::=  { anrAlgorithmInfo  19 }


	anrMeasPeriodSwitch		 OBJECT-TYPE
		SYNTAX					 INTEGER{ off(0),on(1)  }
		MAX-ACCESS			 read-write
		STATUS					 current
		DESCRIPTION			 " -- "
		::=  { anrAlgorithmInfo  20 }


	anrMeasEventSwitch		 OBJECT-TYPE
		SYNTAX					 BITS{ a3(0),a4(1),a5(2)  }
		MAX-ACCESS			 read-write
		STATUS					 current
		DESCRIPTION			 " -- "
		::=  { anrAlgorithmInfo  21 }


	anrInterFreqSwitch		 OBJECT-TYPE
		SYNTAX					 INTEGER{ off(0),on(1)  }
		MAX-ACCESS			 read-write
		STATUS					 current
		DESCRIPTION			 " -- "
		::=  { anrAlgorithmInfo  22 }


	pciAlgorithmInfo		 OBJECT IDENTIFIER
		::=  { globalAlgorithm  4 }


	pciAlgorithmSwitch		 OBJECT-TYPE
		SYNTAX					 INTEGER{ off(0),on(1)  }
		MAX-ACCESS			 read-write
		STATUS					 current
		DESCRIPTION			 " -- "
		::=  { pciAlgorithmInfo  1 }


	pciCheckTrigger		 OBJECT-TYPE
		SYNTAX					 INTEGER{ off(0),on(1)  }
		MAX-ACCESS			 read-write
		STATUS					 current
		DESCRIPTION			 " -- "
		::=  { pciAlgorithmInfo  4 }


	selfStartupAlgorithmInfo		 OBJECT IDENTIFIER
		::=  { globalAlgorithm  5 }


	selfStartupAlgorithmSwitch		 OBJECT-TYPE
		SYNTAX					 INTEGER{ off(0),on(1)  }
		MAX-ACCESS			 read-write
		STATUS					 current
		DESCRIPTION			 " -- "
		::=  { selfStartupAlgorithmInfo  1 }


	selfStartupIpSecSwitch		 OBJECT-TYPE
		SYNTAX					 INTEGER{ off(0),on(1)  }
		MAX-ACCESS			 read-write
		STATUS					 current
		DESCRIPTION			 " -- "
		::=  { selfStartupAlgorithmInfo  2 }


	s1Flex		 OBJECT IDENTIFIER
		::=  { globalAlgorithm  6 }


	s1FlexSwitch		 OBJECT-TYPE
		SYNTAX					 INTEGER{ off(0),on(1)  }
		MAX-ACCESS			 read-write
		STATUS					 current
		DESCRIPTION			 " -- "
		::=  { s1Flex  1 }


	s1FlexDefMmePlmnMcc		 OBJECT-TYPE
		SYNTAX					 MncMccType
		MAX-ACCESS			 read-write
		STATUS					 current
		DESCRIPTION			 " -- "
		::=  { s1Flex  2 }


	s1FlexDefMmePlmnMnc		 OBJECT-TYPE
		SYNTAX					 MncMccType
		MAX-ACCESS			 read-write
		STATUS					 current
		DESCRIPTION			 " -- "
		::=  { s1Flex  3 }


	s1FlexDefMmeGroupId		 OBJECT-TYPE
		SYNTAX					 Integer32( 0 .. 65535|-1 )
		MAX-ACCESS			 read-write
		STATUS					 current
		DESCRIPTION			 " -- "
		::=  { s1Flex  4 }


	s1FlexDefMmeCode		 OBJECT-TYPE
		SYNTAX					 Integer32( 0 .. 255|-1 )
		MAX-ACCESS			 read-write
		STATUS					 current
		DESCRIPTION			 " -- "
		::=  { s1Flex  5 }


	s1FlexDefMmeExistStatus		 OBJECT-TYPE
		SYNTAX					 INTEGER{ invalid(0),notMatched(1),matched(2)  }
		MAX-ACCESS			 read-write
		STATUS					 current
		DESCRIPTION			 " -- "
		::=  { s1Flex  6 }


	geranFeature		 OBJECT IDENTIFIER
		::=  { globalAlgorithm  7 }


	geranDtmFlag		 OBJECT-TYPE
		SYNTAX					 INTEGER{ off(0),on(1)  }
		MAX-ACCESS			 read-write
		STATUS					 current
		DESCRIPTION			 " -- "
		::=  { geranFeature  1 }


	dummyMme		 OBJECT IDENTIFIER
		::=  { globalAlgorithm  8 }


	dummyMmeFuncSwitch		 OBJECT-TYPE
		SYNTAX					 INTEGER{ close(0),open(1)  }
		MAX-ACCESS			 read-write
		STATUS					 current
		DESCRIPTION			 " -- "
		::=  { dummyMme  1 }


	eNBTrafficTest		 OBJECT IDENTIFIER
		::=  { globalAlgorithm  9 }


	eNBIotAlarmSwitch		 OBJECT-TYPE
		SYNTAX					 INTEGER{ off(0),on(1)  }
		MAX-ACCESS			 read-write
		STATUS					 current
		DESCRIPTION			 " -- "
		::=  { eNBTrafficTest  1 }


	eNBIotAlarmPeriod		 OBJECT-TYPE
		SYNTAX					 Unsigned32( 180 .. 3600 )
		MAX-ACCESS			 read-write
		STATUS					 current
		DESCRIPTION			 " -- "
		::=  { eNBTrafficTest  2 }


	eNBIotAlarmThreshold		 OBJECT-TYPE
		SYNTAX					 Integer32( 7 .. 62 )
		MAX-ACCESS			 read-write
		STATUS					 current
		DESCRIPTION			 " -- "
		::=  { eNBTrafficTest  3 }


	eNBIotAlarmPRBnum		 OBJECT-TYPE
		SYNTAX					 Unsigned32( 0 .. 100 )
		MAX-ACCESS			 read-write
		STATUS					 current
		DESCRIPTION			 " -- "
		::=  { eNBTrafficTest  4 }


	eNBMroAlarmSwitch		 OBJECT-TYPE
		SYNTAX					 INTEGER{ off(0),on(1)  }
		MAX-ACCESS			 read-write
		STATUS					 current
		DESCRIPTION			 " -- "
		::=  { eNBTrafficTest  5 }


	eNBIotAlarmDelayNum		 OBJECT-TYPE
		SYNTAX					 Unsigned32( 1 .. 65535 )
		MAX-ACCESS			 read-write
		STATUS					 current
		DESCRIPTION			 " -- "
		::=  { eNBTrafficTest  7 }


	eNBEnergyConservationStrategy		 OBJECT IDENTIFIER
		::=  { globalAlgorithm  10 }


	eNBPathShutdownStrategySwitch		 OBJECT-TYPE
		SYNTAX					 INTEGER{ off(0),on(1)  }
		MAX-ACCESS			 read-write
		STATUS					 current
		DESCRIPTION			 " -- "
		::=  { eNBEnergyConservationStrategy  1 }


	eNBCellShutdownStrategySwitch		 OBJECT-TYPE
		SYNTAX					 INTEGER{ off(0),on(1)  }
		MAX-ACCESS			 read-write
		STATUS					 current
		DESCRIPTION			 " -- "
		::=  { eNBEnergyConservationStrategy  2 }


	eNBEnergyConservStartTimeHour		 OBJECT-TYPE
		SYNTAX					 Unsigned32( 0 .. 23 )
		MAX-ACCESS			 read-write
		STATUS					 current
		DESCRIPTION			 " -- "
		::=  { eNBEnergyConservationStrategy  3 }


	eNBEnergyConservStartTimeMinute		 OBJECT-TYPE
		SYNTAX					 Unsigned32( 0 .. 59 )
		MAX-ACCESS			 read-write
		STATUS					 current
		DESCRIPTION			 " -- "
		::=  { eNBEnergyConservationStrategy  4 }


	eNBEnergyConservEndTimeHour		 OBJECT-TYPE
		SYNTAX					 Unsigned32( 0 .. 23 )
		MAX-ACCESS			 read-write
		STATUS					 current
		DESCRIPTION			 " -- "
		::=  { eNBEnergyConservationStrategy  5 }


	eNBEnergyConservEndTimeMinute		 OBJECT-TYPE
		SYNTAX					 Unsigned32( 0 .. 59 )
		MAX-ACCESS			 read-write
		STATUS					 current
		DESCRIPTION			 " -- "
		::=  { eNBEnergyConservationStrategy  6 }


	eNBEnergyConservDelayTime		 OBJECT-TYPE
		SYNTAX					 Unsigned32( 0 .. 15 )
		MAX-ACCESS			 read-write
		STATUS					 current
		DESCRIPTION			 " -- "
		::=  { eNBEnergyConservationStrategy  7 }


	eNBPathShutdownLowThreshold		 OBJECT-TYPE
		SYNTAX					 Unsigned32( 1 .. 99 )
		MAX-ACCESS			 read-write
		STATUS					 current
		DESCRIPTION			 " -- "
		::=  { eNBEnergyConservationStrategy  8 }


	eNBPathShutdownHighThreshold		 OBJECT-TYPE
		SYNTAX					 Unsigned32( 1 .. 99 )
		MAX-ACCESS			 read-write
		STATUS					 current
		DESCRIPTION			 " -- "
		::=  { eNBEnergyConservationStrategy  9 }


	eNBCellShutdownLowThreshold		 OBJECT-TYPE
		SYNTAX					 Unsigned32( 1 .. 99 )
		MAX-ACCESS			 read-write
		STATUS					 current
		DESCRIPTION			 " -- "
		::=  { eNBEnergyConservationStrategy  10 }


	eNBCellShutdownHighThreshold		 OBJECT-TYPE
		SYNTAX					 Unsigned32( 1 .. 99 )
		MAX-ACCESS			 read-write
		STATUS					 current
		DESCRIPTION			 " -- "
		::=  { eNBEnergyConservationStrategy  11 }


	eNBMBSFNSwitch		 OBJECT-TYPE
		SYNTAX					 INTEGER{ off(0),auto(1),static(2)  }
		MAX-ACCESS			 read-write
		STATUS					 current
		DESCRIPTION			 " -- "
		::=  { eNBEnergyConservationStrategy  12 }


	eNBMBSFNShutdownLowThreshold		 OBJECT-TYPE
		SYNTAX					 Unsigned32( 1 .. 99 )
		MAX-ACCESS			 read-write
		STATUS					 current
		DESCRIPTION			 " -- "
		::=  { eNBEnergyConservationStrategy  13 }


	eNBMBSFNShutdownHighThreshold		 OBJECT-TYPE
		SYNTAX					 Unsigned32( 1 .. 99 )
		MAX-ACCESS			 read-write
		STATUS					 current
		DESCRIPTION			 " -- "
		::=  { eNBEnergyConservationStrategy  14 }


	eNBSymbolSwitch		 OBJECT-TYPE
		SYNTAX					 INTEGER{ off(0),on(1)  }
		MAX-ACCESS			 read-write
		STATUS					 current
		DESCRIPTION			 " -- "
		::=  { eNBEnergyConservationStrategy  15 }


	eNBSymbolShutdownLowThreshold		 OBJECT-TYPE
		SYNTAX					 Unsigned32( 1 .. 99 )
		MAX-ACCESS			 read-write
		STATUS					 current
		DESCRIPTION			 " -- "
		::=  { eNBEnergyConservationStrategy  16 }


	eNBSymbolShutdownHighThreshold		 OBJECT-TYPE
		SYNTAX					 Unsigned32( 1 .. 99 )
		MAX-ACCESS			 read-write
		STATUS					 current
		DESCRIPTION			 " -- "
		::=  { eNBEnergyConservationStrategy  17 }


	eNBCarrierSwitch		 OBJECT-TYPE
		SYNTAX					 INTEGER{ off(0),on(1)  }
		MAX-ACCESS			 read-write
		STATUS					 current
		DESCRIPTION			 " -- "
		::=  { eNBEnergyConservationStrategy  18 }


	eNBCarrierShutdownLowThreshold		 OBJECT-TYPE
		SYNTAX					 Unsigned32( 1 .. 99 )
		MAX-ACCESS			 read-write
		STATUS					 current
		DESCRIPTION			 " -- "
		::=  { eNBEnergyConservationStrategy  19 }


	eNBCarrierShutdownHighThreshold		 OBJECT-TYPE
		SYNTAX					 Unsigned32( 1 .. 99 )
		MAX-ACCESS			 read-write
		STATUS					 current
		DESCRIPTION			 " -- "
		::=  { eNBEnergyConservationStrategy  20 }


	eNBPRBRadioType		 OBJECT-TYPE
		SYNTAX					 INTEGER{ autualPRB(0),switchedPRB(1)  }
		MAX-ACCESS			 read-write
		STATUS					 current
		DESCRIPTION			 " -- "
		::=  { eNBEnergyConservationStrategy  21 }


	eNBEightPathShutdownType		 OBJECT-TYPE
		SYNTAX					 INTEGER{ off1port4(0),off2port2(1)  }
		MAX-ACCESS			 read-write
		STATUS					 current
		DESCRIPTION			 " -- "
		::=  { eNBEnergyConservationStrategy  22 }


	eNBPaReconfigSwitch		 OBJECT-TYPE
		SYNTAX					 INTEGER{ off(0),on(1)  }
		MAX-ACCESS			 read-write
		STATUS					 current
		DESCRIPTION			 " -- "
		::=  { eNBEnergyConservationStrategy  23 }


	eNBPathShutdownReceiveSwitch		 OBJECT-TYPE
		SYNTAX					 INTEGER{ off(0),on(1)  }
		MAX-ACCESS			 read-write
		STATUS					 current
		DESCRIPTION			 " -- "
		::=  { eNBEnergyConservationStrategy  24 }


	eNBPathShutdownPriority		 OBJECT-TYPE
		SYNTAX					 Integer32( 0 .. 3 )
		MAX-ACCESS			 read-write
		STATUS					 current
		DESCRIPTION			 " -- "
		::=  { eNBEnergyConservationStrategy  25 }


	eNBCellShutdownPriority		 OBJECT-TYPE
		SYNTAX					 Integer32( 0 .. 3 )
		MAX-ACCESS			 read-write
		STATUS					 current
		DESCRIPTION			 " -- "
		::=  { eNBEnergyConservationStrategy  26 }


	eNBMBSFNOrSymbolPriority		 OBJECT-TYPE
		SYNTAX					 Integer32( 0 .. 3 )
		MAX-ACCESS			 read-write
		STATUS					 current
		DESCRIPTION			 " -- "
		::=  { eNBEnergyConservationStrategy  27 }


	eNBCarrierPriority		 OBJECT-TYPE
		SYNTAX					 Integer32( 0 .. 3 )
		MAX-ACCESS			 read-write
		STATUS					 current
		DESCRIPTION			 " -- "
		::=  { eNBEnergyConservationStrategy  28 }


	eNBMacSymbolShutSwitch		 OBJECT-TYPE
		SYNTAX					 INTEGER{ off(0),on(1)  }
		MAX-ACCESS			 read-write
		STATUS					 current
		DESCRIPTION			 " -- "
		::=  { eNBEnergyConservationStrategy  29 }


	eNBPathRecoverDelayTime		 OBJECT-TYPE
		SYNTAX					 Unsigned32( 1 .. 30 )
		MAX-ACCESS			 read-write
		STATUS					 current
		DESCRIPTION			 " -- "
		::=  { eNBEnergyConservationStrategy  30 }


	equipLicenseInfo		 OBJECT IDENTIFIER
		::=  { globalAlgorithm  11 }


	equipMultiChannelBBUCarrierNum		 OBJECT-TYPE
		SYNTAX					 Unsigned32( 0 .. 4294967295 )
		MAX-ACCESS			 read-only
		STATUS					 current
		DESCRIPTION			 " -- "
		::=  { equipLicenseInfo  1 }


	equipDualChannelBBUCarrierNum		 OBJECT-TYPE
		SYNTAX					 Unsigned32( 0 .. 4294967295 )
		MAX-ACCESS			 read-only
		STATUS					 current
		DESCRIPTION			 " -- "
		::=  { equipLicenseInfo  2 }


	equipMultiChannelRRUCarrierNumm		 OBJECT-TYPE
		SYNTAX					 Unsigned32( 0 .. 4294967295 )
		MAX-ACCESS			 read-only
		STATUS					 current
		DESCRIPTION			 " -- "
		::=  { equipLicenseInfo  3 }


	equipDualChannelRRUCarrierNum		 OBJECT-TYPE
		SYNTAX					 Unsigned32( 0 .. 4294967295 )
		MAX-ACCESS			 read-only
		STATUS					 current
		DESCRIPTION			 " -- "
		::=  { equipLicenseInfo  4 }


	equipConnectUeNum		 OBJECT-TYPE
		SYNTAX					 Unsigned32( 0 .. 4294967295 )
		MAX-ACCESS			 read-only
		STATUS					 current
		DESCRIPTION			 " -- "
		::=  { equipLicenseInfo  5 }


	hcPenaltyAlgorithm		 OBJECT IDENTIFIER
		::=  { globalAlgorithm  12 }


	hcFailPenaltyTag		 OBJECT-TYPE
		SYNTAX					 INTEGER{ off(0),on(1)  }
		MAX-ACCESS			 read-write
		STATUS					 current
		DESCRIPTION			 " -- "
		::=  { hcPenaltyAlgorithm  1 }


	hcFailMaxNumForLteCell		 OBJECT-TYPE
		SYNTAX					 Unsigned32( 1 .. 20 )
		MAX-ACCESS			 read-write
		STATUS					 current
		DESCRIPTION			 " -- "
		::=  { hcPenaltyAlgorithm  2 }


	hcFailPenaltyTime		 OBJECT-TYPE
		SYNTAX					 Unsigned32( 1 .. 600 )
		MAX-ACCESS			 read-write
		STATUS					 current
		DESCRIPTION			 " -- "
		::=  { hcPenaltyAlgorithm  3 }


	hcSrvccFailPenaltyTag		 OBJECT-TYPE
		SYNTAX					 INTEGER{ off(0),on(1)  }
		MAX-ACCESS			 read-write
		STATUS					 current
		DESCRIPTION			 " -- "
		::=  { hcPenaltyAlgorithm  4 }


	hcFailMaxNumForInterRat		 OBJECT-TYPE
		SYNTAX					 Unsigned32( 1 .. 20 )
		MAX-ACCESS			 read-write
		STATUS					 current
		DESCRIPTION			 " -- "
		::=  { hcPenaltyAlgorithm  5 }


	hcFailStaTime		 OBJECT-TYPE
		SYNTAX					 Unsigned32( 1 .. 100 )
		MAX-ACCESS			 read-write
		STATUS					 current
		DESCRIPTION			 " -- "
		::=  { hcPenaltyAlgorithm  7 }


	resourceCheck		 OBJECT IDENTIFIER
		::=  { globalAlgorithm  13 }


	resChkHlGlobalTestSwitchCheckPeriod		 OBJECT-TYPE
		SYNTAX					 Unsigned32( 0 .. 240 )
		MAX-ACCESS			 read-write
		STATUS					 current
		DESCRIPTION			 " -- "
		::=  { resourceCheck  1 }


	resChkHlGlobalTestSwitchDeActiveSwitch		 OBJECT-TYPE
		SYNTAX					 INTEGER{ close(0),open(1)  }
		MAX-ACCESS			 read-write
		STATUS					 current
		DESCRIPTION			 " -- "
		::=  { resourceCheck  2 }


	resChkHlGlobalTestResAuditSwitch		 OBJECT-TYPE
		SYNTAX					 INTEGER{ close(0),open(1)  }
		MAX-ACCESS			 read-write
		STATUS					 current
		DESCRIPTION			 " -- "
		::=  { resourceCheck  3 }


	resChkHlGlobalTestResExpDectSwitch		 OBJECT-TYPE
		SYNTAX					 INTEGER{ close(0),open(1)  }
		MAX-ACCESS			 read-write
		STATUS					 current
		DESCRIPTION			 " -- "
		::=  { resourceCheck  4 }


	resChkL2GlobalTestResExpDectSwitch		 OBJECT-TYPE
		SYNTAX					 INTEGER{ close(0),open(1)  }
		MAX-ACCESS			 read-write
		STATUS					 current
		DESCRIPTION			 " -- "
		::=  { resourceCheck  5 }


	resChkHlGlobalTestSwitchUeActiveLimit		 OBJECT-TYPE
		SYNTAX					 Unsigned32( 1 .. 1440 )
		MAX-ACCESS			 read-write
		STATUS					 current
		DESCRIPTION			 " -- "
		::=  { resourceCheck  6 }


	resChkHlGlobalTestUeTimeOut		 OBJECT-TYPE
		SYNTAX					 Unsigned32( 0 .. 65535 )
		MAX-ACCESS			 read-only
		STATUS					 current
		DESCRIPTION			 " -- "
		::=  { resourceCheck  7 }


	resChkHlGlobalTestL3ResChkSwitch		 OBJECT-TYPE
		SYNTAX					 INTEGER{ close(0),open(1)  }
		MAX-ACCESS			 read-write
		STATUS					 current
		DESCRIPTION			 " -- "
		::=  { resourceCheck  9 }


	resChkHlGlobalTestInstanceOccupyTimeThr		 OBJECT-TYPE
		SYNTAX					 Unsigned32( 20 .. 6000 )
		MAX-ACCESS			 read-write
		STATUS					 current
		DESCRIPTION			 " -- "
		::=  { resourceCheck  10 }


	largeCapacityProtect		 OBJECT IDENTIFIER
		::=  { globalAlgorithm  14 }


	lcAcSwitch		 OBJECT-TYPE
		SYNTAX					 INTEGER{ close(0),open(1)  }
		MAX-ACCESS			 read-write
		STATUS					 current
		DESCRIPTION			 " -- "
		::=  { largeCapacityProtect  1 }


	lcAcUeCountTimerLen		 OBJECT-TYPE
		SYNTAX					 INTEGER{ s10(0),s20(1),s30(2),s40(3),s50(4),s60(5)  }
		MAX-ACCESS			 read-write
		STATUS					 current
		DESCRIPTION			 " -- "
		::=  { largeCapacityProtect  2 }


	lcAcUeThForSignal1		 OBJECT-TYPE
		SYNTAX					 Integer32( 1 .. 1200 )
		MAX-ACCESS			 read-write
		STATUS					 current
		DESCRIPTION			 " -- "
		::=  { largeCapacityProtect  3 }


	lcAcUeThForSignal2		 OBJECT-TYPE
		SYNTAX					 Integer32( 1 .. 1200 )
		MAX-ACCESS			 read-write
		STATUS					 current
		DESCRIPTION			 " -- "
		::=  { largeCapacityProtect  4 }


	lcAcUeThForSignal3		 OBJECT-TYPE
		SYNTAX					 Integer32( 1 .. 1200 )
		MAX-ACCESS			 read-write
		STATUS					 current
		DESCRIPTION			 " -- "
		::=  { largeCapacityProtect  5 }


	lcAcProbFactorForSignal1		 OBJECT-TYPE
		SYNTAX					 INTEGER{ p00(0),p05(1),p10(2),p15(3),p20(4),p25(5),p30(6),p40(7),p50(8),p60(9),p70(10),p75(11),p80(12),p85(13),p90(14),p95(15)  }
		MAX-ACCESS			 read-write
		STATUS					 current
		DESCRIPTION			 " -- "
		::=  { largeCapacityProtect  6 }


	lcAcProbFactorForSignal2		 OBJECT-TYPE
		SYNTAX					 INTEGER{ p00(0),p05(1),p10(2),p15(3),p20(4),p25(5),p30(6),p40(7),p50(8),p60(9),p70(10),p75(11),p80(12),p85(13),p90(14),p95(15)  }
		MAX-ACCESS			 read-write
		STATUS					 current
		DESCRIPTION			 " -- "
		::=  { largeCapacityProtect  7 }


	lcAcProbFactorForSignal3		 OBJECT-TYPE
		SYNTAX					 INTEGER{ p00(0),p05(1),p10(2),p15(3),p20(4),p25(5),p30(6),p40(7),p50(8),p60(9),p70(10),p75(11),p80(12),p85(13),p90(14),p95(15)  }
		MAX-ACCESS			 read-write
		STATUS					 current
		DESCRIPTION			 " -- "
		::=  { largeCapacityProtect  8 }


	lcAcBarTimeForSignal1		 OBJECT-TYPE
		SYNTAX					 INTEGER{ s4(0),s8(1),s16(2),s32(3),s64(4),s128(5),s256(6),s512(7)  }
		MAX-ACCESS			 read-write
		STATUS					 current
		DESCRIPTION			 " -- "
		::=  { largeCapacityProtect  9 }


	lcAcBarTimeForSignal2		 OBJECT-TYPE
		SYNTAX					 INTEGER{ s4(0),s8(1),s16(2),s32(3),s64(4),s128(5),s256(6),s512(7)  }
		MAX-ACCESS			 read-write
		STATUS					 current
		DESCRIPTION			 " -- "
		::=  { largeCapacityProtect  10 }


	lcAcBarTimeForSignal3		 OBJECT-TYPE
		SYNTAX					 INTEGER{ s4(0),s8(1),s16(2),s32(3),s64(4),s128(5),s256(6),s512(7)  }
		MAX-ACCESS			 read-write
		STATUS					 current
		DESCRIPTION			 " -- "
		::=  { largeCapacityProtect  11 }


	lcAcUeThForMoc1		 OBJECT-TYPE
		SYNTAX					 Integer32( 1 .. 1200 )
		MAX-ACCESS			 read-write
		STATUS					 current
		DESCRIPTION			 " -- "
		::=  { largeCapacityProtect  12 }


	lcAcUeThForMoc2		 OBJECT-TYPE
		SYNTAX					 Integer32( 1 .. 1200 )
		MAX-ACCESS			 read-write
		STATUS					 current
		DESCRIPTION			 " -- "
		::=  { largeCapacityProtect  13 }


	lcAcUeThForMoc3		 OBJECT-TYPE
		SYNTAX					 Integer32( 1 .. 1200 )
		MAX-ACCESS			 read-write
		STATUS					 current
		DESCRIPTION			 " -- "
		::=  { largeCapacityProtect  14 }


	lcAcProbFactorForMoc1		 OBJECT-TYPE
		SYNTAX					 INTEGER{ p00(0),p05(1),p10(2),p15(3),p20(4),p25(5),p30(6),p40(7),p50(8),p60(9),p70(10),p75(11),p80(12),p85(13),p90(14),p95(15)  }
		MAX-ACCESS			 read-write
		STATUS					 current
		DESCRIPTION			 " -- "
		::=  { largeCapacityProtect  15 }


	lcAcProbFactorForMoc2		 OBJECT-TYPE
		SYNTAX					 INTEGER{ p00(0),p05(1),p10(2),p15(3),p20(4),p25(5),p30(6),p40(7),p50(8),p60(9),p70(10),p75(11),p80(12),p85(13),p90(14),p95(15)  }
		MAX-ACCESS			 read-write
		STATUS					 current
		DESCRIPTION			 " -- "
		::=  { largeCapacityProtect  16 }


	lcAcProbFactorForMoc3		 OBJECT-TYPE
		SYNTAX					 INTEGER{ p00(0),p05(1),p10(2),p15(3),p20(4),p25(5),p30(6),p40(7),p50(8),p60(9),p70(10),p75(11),p80(12),p85(13),p90(14),p95(15)  }
		MAX-ACCESS			 read-write
		STATUS					 current
		DESCRIPTION			 " -- "
		::=  { largeCapacityProtect  17 }


	lcAcBarTimeForMoc1		 OBJECT-TYPE
		SYNTAX					 INTEGER{ s4(0),s8(1),s16(2),s32(3),s64(4),s128(5),s256(6),s512(7)  }
		MAX-ACCESS			 read-write
		STATUS					 current
		DESCRIPTION			 " -- "
		::=  { largeCapacityProtect  18 }


	lcAcBarTimeForMoc2		 OBJECT-TYPE
		SYNTAX					 INTEGER{ s4(0),s8(1),s16(2),s32(3),s64(4),s128(5),s256(6),s512(7)  }
		MAX-ACCESS			 read-write
		STATUS					 current
		DESCRIPTION			 " -- "
		::=  { largeCapacityProtect  19 }


	lcAcBarTimeForMoc3		 OBJECT-TYPE
		SYNTAX					 INTEGER{ s4(0),s8(1),s16(2),s32(3),s64(4),s128(5),s256(6),s512(7)  }
		MAX-ACCESS			 read-write
		STATUS					 current
		DESCRIPTION			 " -- "
		::=  { largeCapacityProtect  20 }


	lcAcPreventPPNum		 OBJECT-TYPE
		SYNTAX					 Integer32( 1 .. 10 )
		MAX-ACCESS			 read-write
		STATUS					 current
		DESCRIPTION			 " -- "
		::=  { largeCapacityProtect  21 }


	lcInsureHoInSwitch		 OBJECT-TYPE
		SYNTAX					 INTEGER{ close(0),open(1)  }
		MAX-ACCESS			 read-write
		STATUS					 current
		DESCRIPTION			 " -- "
		::=  { largeCapacityProtect  22 }


	lcInsureHoOutSwitch		 OBJECT-TYPE
		SYNTAX					 INTEGER{ close(0),open(1)  }
		MAX-ACCESS			 read-write
		STATUS					 current
		DESCRIPTION			 " -- "
		::=  { largeCapacityProtect  23 }


	cpuLoadContrlInfo		 OBJECT IDENTIFIER
		::=  { globalAlgorithm  15 }


	cpuMidLoadTh		 OBJECT-TYPE
		SYNTAX					 Unsigned32( 0 .. 100 )
		MAX-ACCESS			 read-write
		STATUS					 current
		DESCRIPTION			 " -- "
		::=  { cpuLoadContrlInfo  1 }


	cpuHighLoadTh		 OBJECT-TYPE
		SYNTAX					 Unsigned32( 0 .. 100 )
		MAX-ACCESS			 read-write
		STATUS					 current
		DESCRIPTION			 " -- "
		::=  { cpuLoadContrlInfo  2 }


	cpuOverLoadTh		 OBJECT-TYPE
		SYNTAX					 Unsigned32( 0 .. 100 )
		MAX-ACCESS			 read-write
		STATUS					 current
		DESCRIPTION			 " -- "
		::=  { cpuLoadContrlInfo  3 }


	cpuLoadStateUpTimeToTrig		 OBJECT-TYPE
		SYNTAX					 Unsigned32( 1 .. 100 )
		MAX-ACCESS			 read-write
		STATUS					 current
		DESCRIPTION			 " -- "
		::=  { cpuLoadContrlInfo  4 }


	cpuHigLoadThTimeToTrig		 OBJECT-TYPE
		SYNTAX					 Unsigned32( 1 .. 100 )
		MAX-ACCESS			 read-write
		STATUS					 current
		DESCRIPTION			 " -- "
		::=  { cpuLoadContrlInfo  5 }


	cpuOverloadControlTag		 OBJECT-TYPE
		SYNTAX					 INTEGER{ off(0),on(1)  }
		MAX-ACCESS			 read-write
		STATUS					 current
		DESCRIPTION			 " -- "
		::=  { cpuLoadContrlInfo  6 }


	cpuContrlAlgorithmTag		 OBJECT-TYPE
		SYNTAX					 INTEGER{ off(0),on(1)  }
		MAX-ACCESS			 read-write
		STATUS					 current
		DESCRIPTION			 " -- "
		::=  { cpuLoadContrlInfo  7 }


	cpuCAPSTh		 OBJECT-TYPE
		SYNTAX					 Integer32( 1 .. 120 )
		MAX-ACCESS			 read-write
		STATUS					 current
		DESCRIPTION			 " -- "
		::=  { cpuLoadContrlInfo  8 }


	ueStaticsInformation		 OBJECT IDENTIFIER
		::=  { networkElementLayoutPlan  12 }


	ueInfoStaticsTable		 OBJECT-TYPE
		SYNTAX					 SEQUENCE  OF	 UeInfoStaticsEntry
		MAX-ACCESS			 not-accessible
		STATUS					 current
		DESCRIPTION			 " -- "
		::=  { ueStaticsInformation  1 }


	ueInfoStaticsEntry		 OBJECT-TYPE
		SYNTAX					 UeInfoStaticsEntry
		MAX-ACCESS			 not-accessible
		STATUS					 current
		DESCRIPTION			 " -- "
		INDEX						{ ueInfoStatLcId }
		::=  { ueInfoStaticsTable  1 }


	UeInfoStaticsEntry		 ::=  SEQUENCE {
		ueInfoStatLcId					Integer32,
		ueInfoStatRowStatus					RowStatus,
		ueInfoStatUeNum					Integer32,
		ueInfoStatQciRbCnt					Unsigned32Array
		}


	ueInfoStatLcId		 OBJECT-TYPE
		SYNTAX					 Integer32( 0 .. 23 )
		MAX-ACCESS			 not-accessible
		STATUS					 current
		DESCRIPTION			 " -- "
		::=  { ueInfoStaticsEntry  1 }


	ueInfoStatRowStatus		 OBJECT-TYPE
		SYNTAX					 RowStatus
		MAX-ACCESS			 read-only
		STATUS					 current
		DESCRIPTION			 " -- "
		::=  { ueInfoStaticsEntry  2 }


	ueInfoStatUeNum		 OBJECT-TYPE
		SYNTAX					 Integer32( 0 .. 65535 )
		MAX-ACCESS			 read-only
		STATUS					 current
		DESCRIPTION			 " -- "
		::=  { ueInfoStaticsEntry  3 }


	ueInfoStatQciRbCnt		 OBJECT-TYPE
		SYNTAX					 Unsigned32Array
		MAX-ACCESS			 read-only
		STATUS					 current
		DESCRIPTION			 " -- "
		::=  { ueInfoStaticsEntry  4 }


	cellPrbInfoTable		 OBJECT-TYPE
		SYNTAX					 SEQUENCE  OF	 CellPrbInfoEntry
		MAX-ACCESS			 not-accessible
		STATUS					 current
		DESCRIPTION			 " -- "
		::=  { ueStaticsInformation  2 }


	cellPrbInfoEntry		 OBJECT-TYPE
		SYNTAX					 CellPrbInfoEntry
		MAX-ACCESS			 not-accessible
		STATUS					 current
		DESCRIPTION			 " -- "
		INDEX						{ cellPrbLcId }
		::=  { cellPrbInfoTable  1 }


	CellPrbInfoEntry		 ::=  SEQUENCE {
		cellPrbLcId					Integer32,
		cellPrbRowStatus					RowStatus,
		cellPrbUlPrbInfo					Unsigned32Array,
		cellPrbDlPrbInfo					Unsigned32Array
		}


	cellPrbLcId		 OBJECT-TYPE
		SYNTAX					 Integer32( 0 .. 23 )
		MAX-ACCESS			 not-accessible
		STATUS					 current
		DESCRIPTION			 " -- "
		::=  { cellPrbInfoEntry  1 }


	cellPrbRowStatus		 OBJECT-TYPE
		SYNTAX					 RowStatus
		MAX-ACCESS			 read-only
		STATUS					 current
		DESCRIPTION			 " -- "
		::=  { cellPrbInfoEntry  2 }


	cellPrbUlPrbInfo		 OBJECT-TYPE
		SYNTAX					 Unsigned32Array
		MAX-ACCESS			 read-only
		STATUS					 current
		DESCRIPTION			 " -- "
		::=  { cellPrbInfoEntry  3 }


	cellPrbDlPrbInfo		 OBJECT-TYPE
		SYNTAX					 Unsigned32Array
		MAX-ACCESS			 read-only
		STATUS					 current
		DESCRIPTION			 " -- "
		::=  { cellPrbInfoEntry  4 }


	ueAdaptiveIrcStatTable		 OBJECT-TYPE
		SYNTAX					 SEQUENCE  OF	 UeAdaptiveIrcStatEntry
		MAX-ACCESS			 not-accessible
		STATUS					 current
		DESCRIPTION			 " -- "
		::=  { ueStaticsInformation  3 }


	ueAdaptiveIrcStatEntry		 OBJECT-TYPE
		SYNTAX					 UeAdaptiveIrcStatEntry
		MAX-ACCESS			 not-accessible
		STATUS					 current
		DESCRIPTION			 " -- "
		INDEX						{ ueAdaptiveLcId,ueAdaptiveIndex }
		::=  { ueAdaptiveIrcStatTable  1 }


	UeAdaptiveIrcStatEntry		 ::=  SEQUENCE {
		ueAdaptiveLcId					Integer32,
		ueAdaptiveIndex					Unsigned32,
		ueAdaptiveRowStatus					RowStatus,
		ueAdaptiveIrcNum					Unsigned32,
		ueAdaptivePrbNum					Unsigned32,
		ueAdaptiveIrcRate					Unsigned32
		}


	ueAdaptiveLcId		 OBJECT-TYPE
		SYNTAX					 Integer32( 0 .. 23 )
		MAX-ACCESS			 not-accessible
		STATUS					 current
		DESCRIPTION			 " -- "
		::=  { ueAdaptiveIrcStatEntry  1 }


	ueAdaptiveIndex		 OBJECT-TYPE
		SYNTAX					 Unsigned32( 0 .. 1200 )
		MAX-ACCESS			 not-accessible
		STATUS					 current
		DESCRIPTION			 " -- "
		::=  { ueAdaptiveIrcStatEntry  2 }


	ueAdaptiveRowStatus		 OBJECT-TYPE
		SYNTAX					 RowStatus
		MAX-ACCESS			 read-only
		STATUS					 current
		DESCRIPTION			 " -- "
		::=  { ueAdaptiveIrcStatEntry  3 }


	ueAdaptiveIrcNum		 OBJECT-TYPE
		SYNTAX					 Unsigned32( 0 .. 120000 )
		MAX-ACCESS			 read-only
		STATUS					 current
		DESCRIPTION			 " -- "
		::=  { ueAdaptiveIrcStatEntry  4 }


	ueAdaptivePrbNum		 OBJECT-TYPE
		SYNTAX					 Unsigned32( 0 .. 120000 )
		MAX-ACCESS			 read-only
		STATUS					 current
		DESCRIPTION			 " -- "
		::=  { ueAdaptiveIrcStatEntry  5 }


	ueAdaptiveIrcRate		 OBJECT-TYPE
		SYNTAX					 Unsigned32( 0 .. 100 )
		MAX-ACCESS			 read-only
		STATUS					 current
		DESCRIPTION			 " -- "
		::=  { ueAdaptiveIrcStatEntry  6 }


	cellPrbRatioTable		 OBJECT-TYPE
		SYNTAX					 SEQUENCE  OF	 CellPrbRatioEntry
		MAX-ACCESS			 not-accessible
		STATUS					 current
		DESCRIPTION			 " -- "
		::=  { ueStaticsInformation  4 }


	cellPrbRatioEntry		 OBJECT-TYPE
		SYNTAX					 CellPrbRatioEntry
		MAX-ACCESS			 not-accessible
		STATUS					 current
		DESCRIPTION			 " -- "
		INDEX						{ cellPrbRatioLcId }
		::=  { cellPrbRatioTable  1 }


	CellPrbRatioEntry		 ::=  SEQUENCE {
		cellPrbRatioLcId					Integer32,
		cellPrbRatioRowStatus					RowStatus,
		cellPrbRatioUl					Unsigned32,
		cellPrbRatioDl					Unsigned32
		}


	cellPrbRatioLcId		 OBJECT-TYPE
		SYNTAX					 Integer32( 0 .. 23 )
		MAX-ACCESS			 not-accessible
		STATUS					 current
		DESCRIPTION			 " -- "
		::=  { cellPrbRatioEntry  1 }


	cellPrbRatioRowStatus		 OBJECT-TYPE
		SYNTAX					 RowStatus
		MAX-ACCESS			 read-only
		STATUS					 current
		DESCRIPTION			 " -- "
		::=  { cellPrbRatioEntry  2 }


	cellPrbRatioUl		 OBJECT-TYPE
		SYNTAX					 Unsigned32( 0 .. 100 )
		MAX-ACCESS			 read-only
		STATUS					 current
		DESCRIPTION			 " -- "
		::=  { cellPrbRatioEntry  3 }


	cellPrbRatioDl		 OBJECT-TYPE
		SYNTAX					 Unsigned32( 0 .. 100 )
		MAX-ACCESS			 read-only
		STATUS					 current
		DESCRIPTION			 " -- "
		::=  { cellPrbRatioEntry  4 }


	cellCompanyVideoNumTable		 OBJECT-TYPE
		SYNTAX					 SEQUENCE  OF	 CellCompanyVideoNumEntry
		MAX-ACCESS			 not-accessible
		STATUS					 current
		DESCRIPTION			 " -- "
		::=  { ueStaticsInformation  5 }


	cellCompanyVideoNumEntry		 OBJECT-TYPE
		SYNTAX					 CellCompanyVideoNumEntry
		MAX-ACCESS			 not-accessible
		STATUS					 current
		DESCRIPTION			 " -- "
		INDEX						{ cellCompanyVideoNumLcId }
		::=  { cellCompanyVideoNumTable  1 }


	CellCompanyVideoNumEntry		 ::=  SEQUENCE {
		cellCompanyVideoNumLcId					Integer32,
		cellCompanyVideoNumRowStatus					RowStatus,
		cellCompanyVideoTecentVideoNum					Integer32,
		cellCompanyVideoAiqiyiVideoNum					Integer32,
		cellCompanyVideoYoukuVideoNum					Integer32,
		cellCompanyVideoLeshiVideoNum					Integer32,
		cellCompanyVideoMiguVideoNum					Integer32,
		cellCompanyVideoKuaishouVideoNum					Integer32,
		cellCompanyVideoMangguoVideoNum					Integer32,
		cellCompanyVideoReserver1VideoNum					Integer32,
		cellCompanyVideoReserver2VideoNum					Integer32,
		cellCompanyVideoReserver3VideoNum					Integer32,
		cellCompanyVideoReserver4VideoNum					Integer32,
		cellCompanyVideoReserver5VideoNum					Integer32,
		cellCompanyVideoReserver6VideoNum					Integer32,
		cellCompanyVideoReserver7VideoNum					Integer32,
		cellCompanyVideoReserver8VideoNum					Integer32,
		cellCompanyVideoReserver9VideoNum					Integer32,
		cellCompanyVideoReserver10VideoNum					Integer32,
		cellCompanyVideoReserver11VideoNum					Integer32,
		cellCompanyVideoReserver12VideoNum					Integer32,
		cellCompanyVideoReserver13VideoNum					Integer32,
		cellCompanyVideoReserver14VideoNum					Integer32,
		cellCompanyVideoReserver15VideoNum					Integer32,
		cellCompanyVideoReserver16VideoNum					Integer32,
		cellCompanyVideoReserver17VideoNum					Integer32,
		cellCompanyVideoReserver18VideoNum					Integer32,
		cellCompanyVideoReserver19VideoNum					Integer32,
		cellCompanyVideoReserver20VideoNum					Integer32
		}


	cellCompanyVideoNumLcId		 OBJECT-TYPE
		SYNTAX					 Integer32( 0 .. 23 )
		MAX-ACCESS			 not-accessible
		STATUS					 current
		DESCRIPTION			 " -- "
		::=  { cellCompanyVideoNumEntry  1 }


	cellCompanyVideoNumRowStatus		 OBJECT-TYPE
		SYNTAX					 RowStatus
		MAX-ACCESS			 read-only
		STATUS					 current
		DESCRIPTION			 " -- "
		::=  { cellCompanyVideoNumEntry  2 }


	cellCompanyVideoTecentVideoNum		 OBJECT-TYPE
		SYNTAX					 Integer32( 0 .. 255 )
		MAX-ACCESS			 read-only
		STATUS					 current
		DESCRIPTION			 " -- "
		::=  { cellCompanyVideoNumEntry  3 }


	cellCompanyVideoAiqiyiVideoNum		 OBJECT-TYPE
		SYNTAX					 Integer32( 0 .. 255 )
		MAX-ACCESS			 read-only
		STATUS					 current
		DESCRIPTION			 " -- "
		::=  { cellCompanyVideoNumEntry  4 }


	cellCompanyVideoYoukuVideoNum		 OBJECT-TYPE
		SYNTAX					 Integer32( 0 .. 255 )
		MAX-ACCESS			 read-only
		STATUS					 current
		DESCRIPTION			 " -- "
		::=  { cellCompanyVideoNumEntry  5 }


	cellCompanyVideoLeshiVideoNum		 OBJECT-TYPE
		SYNTAX					 Integer32( 0 .. 255 )
		MAX-ACCESS			 read-only
		STATUS					 current
		DESCRIPTION			 " -- "
		::=  { cellCompanyVideoNumEntry  6 }


	cellCompanyVideoMiguVideoNum		 OBJECT-TYPE
		SYNTAX					 Integer32( 0 .. 255 )
		MAX-ACCESS			 read-only
		STATUS					 current
		DESCRIPTION			 " -- "
		::=  { cellCompanyVideoNumEntry  7 }


	cellCompanyVideoKuaishouVideoNum		 OBJECT-TYPE
		SYNTAX					 Integer32( 0 .. 255 )
		MAX-ACCESS			 read-only
		STATUS					 current
		DESCRIPTION			 " -- "
		::=  { cellCompanyVideoNumEntry  8 }


	cellCompanyVideoMangguoVideoNum		 OBJECT-TYPE
		SYNTAX					 Integer32( 0 .. 255 )
		MAX-ACCESS			 read-only
		STATUS					 current
		DESCRIPTION			 " -- "
		::=  { cellCompanyVideoNumEntry  9 }


	cellCompanyVideoReserver1VideoNum		 OBJECT-TYPE
		SYNTAX					 Integer32( 0 .. 255 )
		MAX-ACCESS			 read-only
		STATUS					 current
		DESCRIPTION			 " -- "
		::=  { cellCompanyVideoNumEntry  10 }


	cellCompanyVideoReserver2VideoNum		 OBJECT-TYPE
		SYNTAX					 Integer32( 0 .. 255 )
		MAX-ACCESS			 read-only
		STATUS					 current
		DESCRIPTION			 " -- "
		::=  { cellCompanyVideoNumEntry  11 }


	cellCompanyVideoReserver3VideoNum		 OBJECT-TYPE
		SYNTAX					 Integer32( 0 .. 255 )
		MAX-ACCESS			 read-only
		STATUS					 current
		DESCRIPTION			 " -- "
		::=  { cellCompanyVideoNumEntry  12 }


	cellCompanyVideoReserver4VideoNum		 OBJECT-TYPE
		SYNTAX					 Integer32( 0 .. 255 )
		MAX-ACCESS			 read-only
		STATUS					 current
		DESCRIPTION			 " -- "
		::=  { cellCompanyVideoNumEntry  13 }


	cellCompanyVideoReserver5VideoNum		 OBJECT-TYPE
		SYNTAX					 Integer32( 0 .. 255 )
		MAX-ACCESS			 read-only
		STATUS					 current
		DESCRIPTION			 " -- "
		::=  { cellCompanyVideoNumEntry  14 }


	cellCompanyVideoReserver6VideoNum		 OBJECT-TYPE
		SYNTAX					 Integer32( 0 .. 255 )
		MAX-ACCESS			 read-only
		STATUS					 current
		DESCRIPTION			 " -- "
		::=  { cellCompanyVideoNumEntry  15 }


	cellCompanyVideoReserver7VideoNum		 OBJECT-TYPE
		SYNTAX					 Integer32( 0 .. 255 )
		MAX-ACCESS			 read-only
		STATUS					 current
		DESCRIPTION			 " -- "
		::=  { cellCompanyVideoNumEntry  16 }


	cellCompanyVideoReserver8VideoNum		 OBJECT-TYPE
		SYNTAX					 Integer32( 0 .. 255 )
		MAX-ACCESS			 read-only
		STATUS					 current
		DESCRIPTION			 " -- "
		::=  { cellCompanyVideoNumEntry  17 }


	cellCompanyVideoReserver9VideoNum		 OBJECT-TYPE
		SYNTAX					 Integer32( 0 .. 255 )
		MAX-ACCESS			 read-only
		STATUS					 current
		DESCRIPTION			 " -- "
		::=  { cellCompanyVideoNumEntry  18 }


	cellCompanyVideoReserver10VideoNum		 OBJECT-TYPE
		SYNTAX					 Integer32( 0 .. 255 )
		MAX-ACCESS			 read-only
		STATUS					 current
		DESCRIPTION			 " -- "
		::=  { cellCompanyVideoNumEntry  19 }


	cellCompanyVideoReserver11VideoNum		 OBJECT-TYPE
		SYNTAX					 Integer32( 0 .. 255 )
		MAX-ACCESS			 read-only
		STATUS					 current
		DESCRIPTION			 " -- "
		::=  { cellCompanyVideoNumEntry  20 }


	cellCompanyVideoReserver12VideoNum		 OBJECT-TYPE
		SYNTAX					 Integer32( 0 .. 255 )
		MAX-ACCESS			 read-only
		STATUS					 current
		DESCRIPTION			 " -- "
		::=  { cellCompanyVideoNumEntry  21 }


	cellCompanyVideoReserver13VideoNum		 OBJECT-TYPE
		SYNTAX					 Integer32( 0 .. 255 )
		MAX-ACCESS			 read-only
		STATUS					 current
		DESCRIPTION			 " -- "
		::=  { cellCompanyVideoNumEntry  22 }


	cellCompanyVideoReserver14VideoNum		 OBJECT-TYPE
		SYNTAX					 Integer32( 0 .. 255 )
		MAX-ACCESS			 read-only
		STATUS					 current
		DESCRIPTION			 " -- "
		::=  { cellCompanyVideoNumEntry  23 }


	cellCompanyVideoReserver15VideoNum		 OBJECT-TYPE
		SYNTAX					 Integer32( 0 .. 255 )
		MAX-ACCESS			 read-only
		STATUS					 current
		DESCRIPTION			 " -- "
		::=  { cellCompanyVideoNumEntry  24 }


	cellCompanyVideoReserver16VideoNum		 OBJECT-TYPE
		SYNTAX					 Integer32( 0 .. 255 )
		MAX-ACCESS			 read-only
		STATUS					 current
		DESCRIPTION			 " -- "
		::=  { cellCompanyVideoNumEntry  25 }


	cellCompanyVideoReserver17VideoNum		 OBJECT-TYPE
		SYNTAX					 Integer32( 0 .. 255 )
		MAX-ACCESS			 read-only
		STATUS					 current
		DESCRIPTION			 " -- "
		::=  { cellCompanyVideoNumEntry  26 }


	cellCompanyVideoReserver18VideoNum		 OBJECT-TYPE
		SYNTAX					 Integer32( 0 .. 255 )
		MAX-ACCESS			 read-only
		STATUS					 current
		DESCRIPTION			 " -- "
		::=  { cellCompanyVideoNumEntry  27 }


	cellCompanyVideoReserver19VideoNum		 OBJECT-TYPE
		SYNTAX					 Integer32( 0 .. 255 )
		MAX-ACCESS			 read-only
		STATUS					 current
		DESCRIPTION			 " -- "
		::=  { cellCompanyVideoNumEntry  28 }


	cellCompanyVideoReserver20VideoNum		 OBJECT-TYPE
		SYNTAX					 Integer32( 0 .. 255 )
		MAX-ACCESS			 read-only
		STATUS					 current
		DESCRIPTION			 " -- "
		::=  { cellCompanyVideoNumEntry  29 }


	globalTestSwitch		 OBJECT IDENTIFIER
		::=  { networkElementLayoutPlan  13 }


	hlGlobalTestSwitchInfo		 OBJECT IDENTIFIER
		::=  { globalTestSwitch  1 }


	hlGlobalTestSwitchSrsCfgSwitch		 OBJECT-TYPE
		SYNTAX					 INTEGER{ close(0),open(1)  }
		MAX-ACCESS			 read-write
		STATUS					 current
		DESCRIPTION			 " -- "
		::=  { hlGlobalTestSwitchInfo  1 }


	hlGlobalTestSwitchMroSwitch		 OBJECT-TYPE
		SYNTAX					 INTEGER{ close(0),open(1)  }
		MAX-ACCESS			 read-write
		STATUS					 current
		DESCRIPTION			 " -- "
		::=  { hlGlobalTestSwitchInfo  2 }


	hlGlobalTestSwitchEcidTag		 OBJECT-TYPE
		SYNTAX					 INTEGER{ close(0),open(1)  }
		MAX-ACCESS			 read-write
		STATUS					 current
		DESCRIPTION			 " -- "
		::=  { hlGlobalTestSwitchInfo  4 }


	hlGlobalTestSwitchCapsControlFlag		 OBJECT-TYPE
		SYNTAX					 INTEGER{ close(0),open(1)  }
		MAX-ACCESS			 read-write
		STATUS					 current
		DESCRIPTION			 " -- "
		::=  { hlGlobalTestSwitchInfo  5 }


	hlGlobalTestSwitchCapsThreshold		 OBJECT-TYPE
		SYNTAX					 Unsigned32( 10 .. 1000 )
		MAX-ACCESS			 read-write
		STATUS					 current
		DESCRIPTION			 " -- "
		::=  { hlGlobalTestSwitchInfo  6 }


	hlGlobalTestSwitchUeNumPeriodLpm		 OBJECT-TYPE
		SYNTAX					 Unsigned32( 0 .. 50 )
		MAX-ACCESS			 read-write
		STATUS					 current
		DESCRIPTION			 " -- "
		::=  { hlGlobalTestSwitchInfo  7 }


	hlGlobalTestSwitchUeNumPeriodLpmProcessing		 OBJECT-TYPE
		SYNTAX					 Unsigned32( 0 .. 1200 )
		MAX-ACCESS			 read-write
		STATUS					 current
		DESCRIPTION			 " -- "
		::=  { hlGlobalTestSwitchInfo  8 }


	hlGlobalTestTaMeasT2		 OBJECT-TYPE
		SYNTAX					 Unsigned32( 0 .. 65536 )
		MAX-ACCESS			 read-write
		STATUS					 current
		DESCRIPTION			 " -- "
		::=  { hlGlobalTestSwitchInfo  9 }


	hlGlobalTestSwitchR9R10IESwitch		 OBJECT-TYPE
		SYNTAX					 INTEGER{ close(0),open(1)  }
		MAX-ACCESS			 read-write
		STATUS					 current
		DESCRIPTION			 " -- "
		::=  { hlGlobalTestSwitchInfo  10 }


	hlGlobalTestSwitcheNBUeContrlSwith		 OBJECT-TYPE
		SYNTAX					 INTEGER{ close(0),open(1)  }
		MAX-ACCESS			 read-write
		STATUS					 current
		DESCRIPTION			 " -- "
		::=  { hlGlobalTestSwitchInfo  11 }


	hlGlobalTestSwitcheNBUeContrlPeriod		 OBJECT-TYPE
		SYNTAX					 Unsigned32( 5 .. 600 )
		MAX-ACCESS			 read-write
		STATUS					 current
		DESCRIPTION			 " -- "
		::=  { hlGlobalTestSwitchInfo  12 }


	hlGlobalTestSwitcheNBUeContrlHighThresh		 OBJECT-TYPE
		SYNTAX					 Unsigned32( 1 .. 3600 )
		MAX-ACCESS			 read-write
		STATUS					 current
		DESCRIPTION			 " -- "
		::=  { hlGlobalTestSwitchInfo  13 }


	hlGlobalTestSwitcheNBUeContrlLowThresh		 OBJECT-TYPE
		SYNTAX					 Unsigned32( 1 .. 3600 )
		MAX-ACCESS			 read-write
		STATUS					 current
		DESCRIPTION			 " -- "
		::=  { hlGlobalTestSwitchInfo  14 }


	hlGlobalTestPmInvalidValueSwitch		 OBJECT-TYPE
		SYNTAX					 INTEGER{ v2(0),v3(1)  }
		MAX-ACCESS			 read-write
		STATUS					 current
		DESCRIPTION			 " -- "
		::=  { hlGlobalTestSwitchInfo  15 }


	hlGlobalTestSwitchOverlapStd		 OBJECT-TYPE
		SYNTAX					 Unsigned32( 0 .. 20 )
		MAX-ACCESS			 read-write
		STATUS					 current
		DESCRIPTION			 " -- "
		::=  { hlGlobalTestSwitchInfo  16 }


	hlGlobalTestMaxCellProc		 OBJECT-TYPE
		SYNTAX					 Unsigned32( 1 .. 8 )
		MAX-ACCESS			 read-write
		STATUS					 current
		DESCRIPTION			 " -- "
		::=  { hlGlobalTestSwitchInfo  17 }


	hlGlobalTestMaxUeCell		 OBJECT-TYPE
		SYNTAX					 Unsigned32( 1 .. 1200 )
		MAX-ACCESS			 read-write
		STATUS					 current
		DESCRIPTION			 " -- "
		::=  { hlGlobalTestSwitchInfo  18 }


	hlGlobalTestDrbInteractionWithHcTag		 OBJECT-TYPE
		SYNTAX					 INTEGER{ close(0),open(1)  }
		MAX-ACCESS			 read-write
		STATUS					 current
		DESCRIPTION			 " -- "
		::=  { hlGlobalTestSwitchInfo  19 }


	hlGlobalTestThodelay		 OBJECT-TYPE
		SYNTAX					 Unsigned32( 0 .. 2000 )
		MAX-ACCESS			 read-write
		STATUS					 current
		DESCRIPTION			 " -- "
		::=  { hlGlobalTestSwitchInfo  20 }


	hlGlobalTestSwitchExtendRrcReestablishTag		 OBJECT-TYPE
		SYNTAX					 INTEGER{ close(0),open(1)  }
		MAX-ACCESS			 read-write
		STATUS					 current
		DESCRIPTION			 " -- "
		::=  { hlGlobalTestSwitchInfo  21 }


	hlGlobalTestSwitchL3InfoValueOnlyTag		 OBJECT-TYPE
		SYNTAX					 INTEGER{ close(0),open(1)  }
		MAX-ACCESS			 read-write
		STATUS					 current
		DESCRIPTION			 " -- "
		::=  { hlGlobalTestSwitchInfo  22 }


	hlGlobalTestSwitchOldtoNewBSSValueOnlyTag		 OBJECT-TYPE
		SYNTAX					 INTEGER{ close(0),open(1)  }
		MAX-ACCESS			 read-write
		STATUS					 current
		DESCRIPTION			 " -- "
		::=  { hlGlobalTestSwitchInfo  23 }


	hlGlobalTestSwitchUeCapabilityTransferFlag		 OBJECT-TYPE
		SYNTAX					 INTEGER{ close(0),open(1)  }
		MAX-ACCESS			 read-write
		STATUS					 current
		DESCRIPTION			 " -- "
		::=  { hlGlobalTestSwitchInfo  24 }


	hlGlobalTestSwitchanrAlgorithmSwitchTLS		 OBJECT-TYPE
		SYNTAX					 INTEGER{ off(0),on(1)  }
		MAX-ACCESS			 read-write
		STATUS					 current
		DESCRIPTION			 " -- "
		::=  { hlGlobalTestSwitchInfo  25 }


	hlGlobalTestSwitchpciAlgorithmSwitchTLS		 OBJECT-TYPE
		SYNTAX					 INTEGER{ off(0),on(1)  }
		MAX-ACCESS			 read-write
		STATUS					 current
		DESCRIPTION			 " -- "
		::=  { hlGlobalTestSwitchInfo  26 }


	macGlobalTestSwitchInfo		 OBJECT IDENTIFIER
		::=  { globalTestSwitch  2 }


	macGlobalTestSscSCAExternOptimizationSwitch		 OBJECT-TYPE
		SYNTAX					 INTEGER{ off(0),on(1)  }
		MAX-ACCESS			 read-write
		STATUS					 current
		DESCRIPTION			 " -- "
		::=  { macGlobalTestSwitchInfo  1 }


	ueMatchConfig		 OBJECT IDENTIFIER
		::=  { globalTestSwitch  3 }


	ueImsMatchConfigSrvccCapa		 OBJECT-TYPE
		SYNTAX					 INTEGER{ close(0),open(1)  }
		MAX-ACCESS			 read-write
		STATUS					 current
		DESCRIPTION			 " -- "
		::=  { ueMatchConfig  1 }


	ueImsMatchConfigVolteCapa		 OBJECT-TYPE
		SYNTAX					 INTEGER{ close(0),tddFDD(1),tdd(2),fdd(3)  }
		MAX-ACCESS			 read-write
		STATUS					 current
		DESCRIPTION			 " -- "
		::=  { ueMatchConfig  2 }


	ueImsMatchConfigBandCapa		 OBJECT-TYPE
		SYNTAX					 INTEGER{ close(0),open(1)  }
		MAX-ACCESS			 read-write
		STATUS					 current
		DESCRIPTION			 " -- "
		::=  { ueMatchConfig  3 }


	ueImsMatchConfigBandList		 OBJECT-TYPE
		SYNTAX					 Unsigned32Array
		MAX-ACCESS			 read-create
		STATUS					 current
		DESCRIPTION			 " -- "
		::=  { ueMatchConfig  4 }


	cellUlAnteIot		 OBJECT IDENTIFIER
		::=  { networkElementLayoutPlan  14 }


	cellUlAnteIotTable		 OBJECT-TYPE
		SYNTAX					 SEQUENCE  OF	 CellUlAnteIotEntry
		MAX-ACCESS			 not-accessible
		STATUS					 current
		DESCRIPTION			 " -- "
		::=  { cellUlAnteIot  1 }


	cellUlAnteIotEntry		 OBJECT-TYPE
		SYNTAX					 CellUlAnteIotEntry
		MAX-ACCESS			 not-accessible
		STATUS					 current
		DESCRIPTION			 " -- "
		INDEX						{ cellUlAnteIotLcId,cellUlAnteIotSubSfn,cellUlAnteIotAntNo }
		::=  { cellUlAnteIotTable  1 }


	CellUlAnteIotEntry		 ::=  SEQUENCE {
		cellUlAnteIotLcId					Integer32,
		cellUlAnteIotSubSfn					Integer32,
		cellUlAnteIotAntNo					Integer32,
		cellUlAnteIotRowStatus					RowStatus,
		cellUlAnteIotValue					Integer32Array
		}


	cellUlAnteIotLcId		 OBJECT-TYPE
		SYNTAX					 Integer32( 0 .. 23 )
		MAX-ACCESS			 not-accessible
		STATUS					 current
		DESCRIPTION			 " -- "
		::=  { cellUlAnteIotEntry  1 }


	cellUlAnteIotSubSfn		 OBJECT-TYPE
		SYNTAX					 Integer32( 0 .. 9 )
		MAX-ACCESS			 not-accessible
		STATUS					 current
		DESCRIPTION			 " -- "
		::=  { cellUlAnteIotEntry  2 }


	cellUlAnteIotAntNo		 OBJECT-TYPE
		SYNTAX					 Integer32( 1 .. 24 )
		MAX-ACCESS			 not-accessible
		STATUS					 current
		DESCRIPTION			 " -- "
		::=  { cellUlAnteIotEntry  3 }


	cellUlAnteIotRowStatus		 OBJECT-TYPE
		SYNTAX					 RowStatus
		MAX-ACCESS			 read-only
		STATUS					 current
		DESCRIPTION			 " -- "
		::=  { cellUlAnteIotEntry  4 }


	cellUlAnteIotValue		 OBJECT-TYPE
		SYNTAX					 Integer32Array
		MAX-ACCESS			 read-only
		STATUS					 current
		DESCRIPTION			 " -- "
		::=  { cellUlAnteIotEntry  5 }


	reservedParaInfo		 OBJECT IDENTIFIER
		::=  { networkElementLayoutPlan  15 }


	reservedENBParaInfo		 OBJECT IDENTIFIER
		::=  { reservedParaInfo  1 }


	reservedENBL1Para1		 OBJECT-TYPE
		SYNTAX					 Integer32( -2147483648 .. 2147483647 )
		MAX-ACCESS			 read-write
		STATUS					 current
		DESCRIPTION			 " -- "
		::=  { reservedENBParaInfo  1 }


	reservedENBL1Para2		 OBJECT-TYPE
		SYNTAX					 Integer32( -2147483648 .. 2147483647 )
		MAX-ACCESS			 read-write
		STATUS					 current
		DESCRIPTION			 " -- "
		::=  { reservedENBParaInfo  2 }


	reservedENBL1Para3		 OBJECT-TYPE
		SYNTAX					 Integer32( -2147483648 .. 2147483647 )
		MAX-ACCESS			 read-write
		STATUS					 current
		DESCRIPTION			 " -- "
		::=  { reservedENBParaInfo  3 }


	reservedENBL1Para4		 OBJECT-TYPE
		SYNTAX					 Integer32( -2147483648 .. 2147483647 )
		MAX-ACCESS			 read-write
		STATUS					 current
		DESCRIPTION			 " -- "
		::=  { reservedENBParaInfo  4 }


	reservedENBL1Para5		 OBJECT-TYPE
		SYNTAX					 Integer32( -2147483648 .. 2147483647 )
		MAX-ACCESS			 read-write
		STATUS					 current
		DESCRIPTION			 " -- "
		::=  { reservedENBParaInfo  5 }


	reservedENBL2Para1		 OBJECT-TYPE
		SYNTAX					 Integer32( -2147483648 .. 2147483647 )
		MAX-ACCESS			 read-write
		STATUS					 current
		DESCRIPTION			 " -- "
		::=  { reservedENBParaInfo  6 }


	reservedENBL2Para2		 OBJECT-TYPE
		SYNTAX					 Integer32( -2147483648 .. 2147483647 )
		MAX-ACCESS			 read-write
		STATUS					 current
		DESCRIPTION			 " -- "
		::=  { reservedENBParaInfo  7 }


	reservedENBL2Para3		 OBJECT-TYPE
		SYNTAX					 Integer32( -2147483648 .. 2147483647 )
		MAX-ACCESS			 read-write
		STATUS					 current
		DESCRIPTION			 " -- "
		::=  { reservedENBParaInfo  8 }


	reservedENBL2Para4		 OBJECT-TYPE
		SYNTAX					 Integer32( -2147483648 .. 2147483647 )
		MAX-ACCESS			 read-write
		STATUS					 current
		DESCRIPTION			 " -- "
		::=  { reservedENBParaInfo  9 }


	reservedENBL2Para5		 OBJECT-TYPE
		SYNTAX					 Integer32( -2147483648 .. 2147483647 )
		MAX-ACCESS			 read-write
		STATUS					 current
		DESCRIPTION			 " -- "
		::=  { reservedENBParaInfo  10 }


	reservedENBL3Para1		 OBJECT-TYPE
		SYNTAX					 Integer32( -2147483648 .. 2147483647 )
		MAX-ACCESS			 read-write
		STATUS					 current
		DESCRIPTION			 " -- "
		::=  { reservedENBParaInfo  11 }


	reservedENBL3Para2		 OBJECT-TYPE
		SYNTAX					 Integer32( -2147483648 .. 2147483647 )
		MAX-ACCESS			 read-write
		STATUS					 current
		DESCRIPTION			 " -- "
		::=  { reservedENBParaInfo  12 }


	reservedENBL3Para3		 OBJECT-TYPE
		SYNTAX					 Integer32( -2147483648 .. 2147483647 )
		MAX-ACCESS			 read-write
		STATUS					 current
		DESCRIPTION			 " -- "
		::=  { reservedENBParaInfo  13 }


	reservedENBL3Para4		 OBJECT-TYPE
		SYNTAX					 Integer32( -2147483648 .. 2147483647 )
		MAX-ACCESS			 read-write
		STATUS					 current
		DESCRIPTION			 " -- "
		::=  { reservedENBParaInfo  14 }


	reservedENBL3Para5		 OBJECT-TYPE
		SYNTAX					 Integer32( -2147483648 .. 2147483647 )
		MAX-ACCESS			 read-write
		STATUS					 current
		DESCRIPTION			 " -- "
		::=  { reservedENBParaInfo  15 }


	reservedENBOmPara1		 OBJECT-TYPE
		SYNTAX					 Integer32( -2147483648 .. 2147483647 )
		MAX-ACCESS			 read-write
		STATUS					 current
		DESCRIPTION			 " -- "
		::=  { reservedENBParaInfo  16 }


	reservedENBOmPara2		 OBJECT-TYPE
		SYNTAX					 Integer32( -2147483648 .. 2147483647 )
		MAX-ACCESS			 read-write
		STATUS					 current
		DESCRIPTION			 " -- "
		::=  { reservedENBParaInfo  17 }


	reservedENBOmPara3		 OBJECT-TYPE
		SYNTAX					 Integer32( -2147483648 .. 2147483647 )
		MAX-ACCESS			 read-write
		STATUS					 current
		DESCRIPTION			 " -- "
		::=  { reservedENBParaInfo  18 }


	reservedENBOmPara4		 OBJECT-TYPE
		SYNTAX					 Integer32( -2147483648 .. 2147483647 )
		MAX-ACCESS			 read-write
		STATUS					 current
		DESCRIPTION			 " -- "
		::=  { reservedENBParaInfo  19 }


	reservedENBOmPara5		 OBJECT-TYPE
		SYNTAX					 Integer32( -2147483648 .. 2147483647 )
		MAX-ACCESS			 read-write
		STATUS					 current
		DESCRIPTION			 " -- "
		::=  { reservedENBParaInfo  20 }


	reservedCellParaTable		 OBJECT-TYPE
		SYNTAX					 SEQUENCE  OF	 ReservedCellParaEntry
		MAX-ACCESS			 not-accessible
		STATUS					 current
		DESCRIPTION			 " -- "
		::=  { reservedParaInfo  2 }


	reservedCellParaEntry		 OBJECT-TYPE
		SYNTAX					 ReservedCellParaEntry
		MAX-ACCESS			 not-accessible
		STATUS					 current
		DESCRIPTION			 " -- "
		INDEX						{ reservedCellLcId }
		::=  { reservedCellParaTable  1 }


	ReservedCellParaEntry		 ::=  SEQUENCE {
		reservedCellLcId					Integer32,
		reservedCellRowStatus					RowStatus,
		reservedCellL1Para1					Integer32,
		reservedCellL1Para2					Integer32,
		reservedCellL1Para3					Integer32,
		reservedCellL1Para4					Integer32,
		reservedCellL1Para5					Integer32,
		reservedCellL1Para6					Integer32,
		reservedCellL1Para7					Integer32,
		reservedCellL1Para8					Integer32,
		reservedCellL1Para9					Integer32,
		reservedCellL1Para10					Integer32,
		reservedCellL2Para1					Integer32,
		reservedCellL2Para2					Integer32,
		reservedCellL2Para3					Integer32,
		reservedCellL2Para4					Integer32,
		reservedCellL2Para5					Integer32,
		reservedCellL2Para6					Integer32,
		reservedCellL2Para7					Integer32,
		reservedCellL2Para8					Integer32,
		reservedCellL2Para9					Integer32,
		reservedCellL2Para10					Integer32,
		reservedCellL3Para1					Integer32,
		reservedCellL3Para2					Integer32,
		reservedCellL3Para3					Integer32,
		reservedCellL3Para4					Integer32,
		reservedCellL3Para5					Integer32,
		reservedCellL3Para6					Integer32,
		reservedCellL3Para7					Integer32,
		reservedCellL3Para8					Integer32,
		reservedCellL3Para9					Integer32,
		reservedCellL3Para10					Integer32
		}


	reservedCellLcId		 OBJECT-TYPE
		SYNTAX					 Integer32( 0 .. 23 )
		MAX-ACCESS			 not-accessible
		STATUS					 current
		DESCRIPTION			 " -- "
		::=  { reservedCellParaEntry  1 }


	reservedCellRowStatus		 OBJECT-TYPE
		SYNTAX					 RowStatus
		MAX-ACCESS			 read-create
		STATUS					 current
		DESCRIPTION			 " -- "
		::=  { reservedCellParaEntry  2 }


	reservedCellL1Para1		 OBJECT-TYPE
		SYNTAX					 Integer32( -2147483648 .. 2147483647 )
		MAX-ACCESS			 read-create
		STATUS					 current
		DESCRIPTION			 " -- "
		::=  { reservedCellParaEntry  3 }


	reservedCellL1Para2		 OBJECT-TYPE
		SYNTAX					 Integer32( -2147483648 .. 2147483647 )
		MAX-ACCESS			 read-create
		STATUS					 current
		DESCRIPTION			 " -- "
		::=  { reservedCellParaEntry  4 }


	reservedCellL1Para3		 OBJECT-TYPE
		SYNTAX					 Integer32( -2147483648 .. 2147483647 )
		MAX-ACCESS			 read-create
		STATUS					 current
		DESCRIPTION			 " -- "
		::=  { reservedCellParaEntry  5 }


	reservedCellL1Para4		 OBJECT-TYPE
		SYNTAX					 Integer32( -2147483648 .. 2147483647 )
		MAX-ACCESS			 read-create
		STATUS					 current
		DESCRIPTION			 " -- "
		::=  { reservedCellParaEntry  6 }


	reservedCellL1Para5		 OBJECT-TYPE
		SYNTAX					 Integer32( -2147483648 .. 2147483647 )
		MAX-ACCESS			 read-create
		STATUS					 current
		DESCRIPTION			 " -- "
		::=  { reservedCellParaEntry  7 }


	reservedCellL1Para6		 OBJECT-TYPE
		SYNTAX					 Integer32( -2147483648 .. 2147483647 )
		MAX-ACCESS			 read-create
		STATUS					 current
		DESCRIPTION			 " -- "
		::=  { reservedCellParaEntry  8 }


	reservedCellL1Para7		 OBJECT-TYPE
		SYNTAX					 Integer32( -2147483648 .. 2147483647 )
		MAX-ACCESS			 read-create
		STATUS					 current
		DESCRIPTION			 " -- "
		::=  { reservedCellParaEntry  9 }


	reservedCellL1Para8		 OBJECT-TYPE
		SYNTAX					 Integer32( -2147483648 .. 2147483647 )
		MAX-ACCESS			 read-create
		STATUS					 current
		DESCRIPTION			 " -- "
		::=  { reservedCellParaEntry  10 }


	reservedCellL1Para9		 OBJECT-TYPE
		SYNTAX					 Integer32( -2147483648 .. 2147483647 )
		MAX-ACCESS			 read-create
		STATUS					 current
		DESCRIPTION			 " -- "
		::=  { reservedCellParaEntry  11 }


	reservedCellL1Para10		 OBJECT-TYPE
		SYNTAX					 Integer32( -2147483648 .. 2147483647 )
		MAX-ACCESS			 read-create
		STATUS					 current
		DESCRIPTION			 " -- "
		::=  { reservedCellParaEntry  12 }


	reservedCellL2Para1		 OBJECT-TYPE
		SYNTAX					 Integer32( -2147483648 .. 2147483647 )
		MAX-ACCESS			 read-create
		STATUS					 current
		DESCRIPTION			 " -- "
		::=  { reservedCellParaEntry  13 }


	reservedCellL2Para2		 OBJECT-TYPE
		SYNTAX					 Integer32( -2147483648 .. 2147483647 )
		MAX-ACCESS			 read-create
		STATUS					 current
		DESCRIPTION			 " -- "
		::=  { reservedCellParaEntry  14 }


	reservedCellL2Para3		 OBJECT-TYPE
		SYNTAX					 Integer32( -2147483648 .. 2147483647 )
		MAX-ACCESS			 read-create
		STATUS					 current
		DESCRIPTION			 " -- "
		::=  { reservedCellParaEntry  15 }


	reservedCellL2Para4		 OBJECT-TYPE
		SYNTAX					 Integer32( -2147483648 .. 2147483647 )
		MAX-ACCESS			 read-create
		STATUS					 current
		DESCRIPTION			 " -- "
		::=  { reservedCellParaEntry  16 }


	reservedCellL2Para5		 OBJECT-TYPE
		SYNTAX					 Integer32( -2147483648 .. 2147483647 )
		MAX-ACCESS			 read-create
		STATUS					 current
		DESCRIPTION			 " -- "
		::=  { reservedCellParaEntry  17 }


	reservedCellL2Para6		 OBJECT-TYPE
		SYNTAX					 Integer32( -2147483648 .. 2147483647 )
		MAX-ACCESS			 read-create
		STATUS					 current
		DESCRIPTION			 " -- "
		::=  { reservedCellParaEntry  18 }


	reservedCellL2Para7		 OBJECT-TYPE
		SYNTAX					 Integer32( -2147483648 .. 2147483647 )
		MAX-ACCESS			 read-create
		STATUS					 current
		DESCRIPTION			 " -- "
		::=  { reservedCellParaEntry  19 }


	reservedCellL2Para8		 OBJECT-TYPE
		SYNTAX					 Integer32( -2147483648 .. 2147483647 )
		MAX-ACCESS			 read-create
		STATUS					 current
		DESCRIPTION			 " -- "
		::=  { reservedCellParaEntry  20 }


	reservedCellL2Para9		 OBJECT-TYPE
		SYNTAX					 Integer32( -2147483648 .. 2147483647 )
		MAX-ACCESS			 read-create
		STATUS					 current
		DESCRIPTION			 " -- "
		::=  { reservedCellParaEntry  21 }


	reservedCellL2Para10		 OBJECT-TYPE
		SYNTAX					 Integer32( -2147483648 .. 2147483647 )
		MAX-ACCESS			 read-create
		STATUS					 current
		DESCRIPTION			 " -- "
		::=  { reservedCellParaEntry  22 }


	reservedCellL3Para1		 OBJECT-TYPE
		SYNTAX					 Integer32( -2147483648 .. 2147483647 )
		MAX-ACCESS			 read-create
		STATUS					 current
		DESCRIPTION			 " -- "
		::=  { reservedCellParaEntry  23 }


	reservedCellL3Para2		 OBJECT-TYPE
		SYNTAX					 Integer32( -2147483648 .. 2147483647 )
		MAX-ACCESS			 read-create
		STATUS					 current
		DESCRIPTION			 " -- "
		::=  { reservedCellParaEntry  24 }


	reservedCellL3Para3		 OBJECT-TYPE
		SYNTAX					 Integer32( -2147483648 .. 2147483647 )
		MAX-ACCESS			 read-create
		STATUS					 current
		DESCRIPTION			 " -- "
		::=  { reservedCellParaEntry  25 }


	reservedCellL3Para4		 OBJECT-TYPE
		SYNTAX					 Integer32( -2147483648 .. 2147483647 )
		MAX-ACCESS			 read-create
		STATUS					 current
		DESCRIPTION			 " -- "
		::=  { reservedCellParaEntry  26 }


	reservedCellL3Para5		 OBJECT-TYPE
		SYNTAX					 Integer32( -2147483648 .. 2147483647 )
		MAX-ACCESS			 read-create
		STATUS					 current
		DESCRIPTION			 " -- "
		::=  { reservedCellParaEntry  27 }


	reservedCellL3Para6		 OBJECT-TYPE
		SYNTAX					 Integer32( -2147483648 .. 2147483647 )
		MAX-ACCESS			 read-create
		STATUS					 current
		DESCRIPTION			 " -- "
		::=  { reservedCellParaEntry  28 }


	reservedCellL3Para7		 OBJECT-TYPE
		SYNTAX					 Integer32( -2147483648 .. 2147483647 )
		MAX-ACCESS			 read-create
		STATUS					 current
		DESCRIPTION			 " -- "
		::=  { reservedCellParaEntry  29 }


	reservedCellL3Para8		 OBJECT-TYPE
		SYNTAX					 Integer32( -2147483648 .. 2147483647 )
		MAX-ACCESS			 read-create
		STATUS					 current
		DESCRIPTION			 " -- "
		::=  { reservedCellParaEntry  30 }


	reservedCellL3Para9		 OBJECT-TYPE
		SYNTAX					 Integer32( -2147483648 .. 2147483647 )
		MAX-ACCESS			 read-create
		STATUS					 current
		DESCRIPTION			 " -- "
		::=  { reservedCellParaEntry  31 }


	reservedCellL3Para10		 OBJECT-TYPE
		SYNTAX					 Integer32( -2147483648 .. 2147483647 )
		MAX-ACCESS			 read-create
		STATUS					 current
		DESCRIPTION			 " -- "
		::=  { reservedCellParaEntry  32 }


	uplaneCfg		 OBJECT IDENTIFIER
		::=  { networkElementLayoutPlan  16 }


	pdcpParaCfgTable		 OBJECT-TYPE
		SYNTAX					 SEQUENCE  OF	 PdcpParaCfgEntry
		MAX-ACCESS			 not-accessible
		STATUS					 current
		DESCRIPTION			 " -- "
		::=  { uplaneCfg  1 }


	pdcpParaCfgEntry		 OBJECT-TYPE
		SYNTAX					 PdcpParaCfgEntry
		MAX-ACCESS			 not-accessible
		STATUS					 current
		DESCRIPTION			 " -- "
		INDEX						{ pdcpParaCfgLcId }
		::=  { pdcpParaCfgTable  1 }


	PdcpParaCfgEntry		 ::=  SEQUENCE {
		pdcpParaCfgLcId					Integer32,
		pdcpParaCfgRowStatus					RowStatus,
		pdcpParaWaitEndmarkerTimer					Integer32,
		pdcpParaSilenceCallThreshold					Integer32
		}


	pdcpParaCfgLcId		 OBJECT-TYPE
		SYNTAX					 Integer32( 0 .. 23 )
		MAX-ACCESS			 not-accessible
		STATUS					 current
		DESCRIPTION			 " -- "
		::=  { pdcpParaCfgEntry  1 }


	pdcpParaCfgRowStatus		 OBJECT-TYPE
		SYNTAX					 RowStatus
		MAX-ACCESS			 read-create
		STATUS					 current
		DESCRIPTION			 " -- "
		::=  { pdcpParaCfgEntry  2 }


	pdcpParaWaitEndmarkerTimer		 OBJECT-TYPE
		SYNTAX					 Integer32( 0 .. 2000 )
		MAX-ACCESS			 read-create
		STATUS					 current
		DESCRIPTION			 " -- "
		::=  { pdcpParaCfgEntry  3 }


	pdcpParaSilenceCallThreshold		 OBJECT-TYPE
		SYNTAX					 Integer32( 0 .. 65535 )
		MAX-ACCESS			 read-create
		STATUS					 current
		DESCRIPTION			 " -- "
		::=  { pdcpParaCfgEntry  4 }


	tdsSuperNodeB		 OBJECT IDENTIFIER
		::=  { networkElementLayoutPlan  100 }


	tdsConfigurationPerformance		 OBJECT IDENTIFIER
		::=  { tdsSuperNodeB  1 }


	tdsNodeBSystem		 OBJECT IDENTIFIER
		::=  { tdsConfigurationPerformance  1 }


	tdsNodeBSysCellPerfReportSwitch		 OBJECT-TYPE
		SYNTAX					 INTEGER{ off(0),on(1)  }
		MAX-ACCESS			 read-write
		STATUS					 current
		DESCRIPTION			 " -- "
		::=  { tdsNodeBSystem  1 }


	tdsNodeBSysRncIpAddrType		 OBJECT-TYPE
		SYNTAX					 InetAddressType
		MAX-ACCESS			 read-only
		STATUS					 current
		DESCRIPTION			 " -- "
		::=  { tdsNodeBSystem  2 }


	tdsNodeBSysRncIpAddr		 OBJECT-TYPE
		SYNTAX					 InetAddress
		MAX-ACCESS			 read-only
		STATUS					 current
		DESCRIPTION			 " -- "
		::=  { tdsNodeBSystem  3 }


	tdsNodeBSysDwptsSendMode		 OBJECT-TYPE
		SYNTAX					 INTEGER{ continuous(0),uncontinuous(1)  }
		MAX-ACCESS			 read-write
		STATUS					 current
		DESCRIPTION			 " -- "
		::=  { tdsNodeBSystem  4 }


	tdsNodeBSysUsedBRUNumSamplePeriod		 OBJECT-TYPE
		SYNTAX					 Unsigned32( 1 .. 30 )
		MAX-ACCESS			 read-write
		STATUS					 current
		DESCRIPTION			 " -- "
		::=  { tdsNodeBSystem  5 }


	tdsNodeBTimeSlotClosedStatPeriod		 OBJECT-TYPE
		SYNTAX					 Integer32( 1 .. 1440 )
		MAX-ACCESS			 read-write
		STATUS					 current
		DESCRIPTION			 " -- "
		::=  { tdsNodeBSystem  6 }


	tdsNodeBBRUStatisticType		 OBJECT-TYPE
		SYNTAX					 INTEGER{ averageBruNum(0),maxValSamplePeriodAverageBruNum(1),maxTTIValAverageBruNum(2)  }
		MAX-ACCESS			 read-write
		STATUS					 current
		DESCRIPTION			 " -- "
		::=  { tdsNodeBSystem  7 }


	tdsNodeBBRUStatisticQuotiety		 OBJECT-TYPE
		SYNTAX					 Integer32( 10 .. 5000 )
		MAX-ACCESS			 read-write
		STATUS					 current
		DESCRIPTION			 " -- "
		::=  { tdsNodeBSystem  8 }


	tdsNodeBHsupaBRUStatisticType		 OBJECT-TYPE
		SYNTAX					 INTEGER{ averageBruNum(0),maxValSamplePeriodAverageBruNum(1),maxTTIValAverageBruNum(2)  }
		MAX-ACCESS			 read-write
		STATUS					 current
		DESCRIPTION			 " -- "
		::=  { tdsNodeBSystem  9 }


	tdsNodeBHsupaBRUStatisticQuotiety		 OBJECT-TYPE
		SYNTAX					 Integer32( 10 .. 5000 )
		MAX-ACCESS			 read-write
		STATUS					 current
		DESCRIPTION			 " -- "
		::=  { tdsNodeBSystem  10 }


	tdsNodeBIubSmoothCtrlSwitch		 OBJECT-TYPE
		SYNTAX					 INTEGER{ off(0),on(1)  }
		MAX-ACCESS			 read-write
		STATUS					 current
		DESCRIPTION			 " -- "
		::=  { tdsNodeBSystem  11 }


	tdsNodeBIubSmoothConfigData		 OBJECT-TYPE
		SYNTAX					 Integer32( 0|2 .. 13 )
		MAX-ACCESS			 read-write
		STATUS					 current
		DESCRIPTION			 " -- "
		::=  { tdsNodeBSystem  12 }


	tdsNodeBIubSmoothRandomData		 OBJECT-TYPE
		SYNTAX					 Integer32( 2 .. 13 )
		MAX-ACCESS			 read-only
		STATUS					 current
		DESCRIPTION			 " -- "
		::=  { tdsNodeBSystem  13 }


	tdsNodeBSysUserTraceLogSwitch		 OBJECT-TYPE
		SYNTAX					 INTEGER{ off(0),onKpi(1),onHspa(2)  }
		MAX-ACCESS			 read-write
		STATUS					 current
		DESCRIPTION			 " -- "
		::=  { tdsNodeBSystem  14 }


	tdsNodeBRachAbnormalThreshold		 OBJECT-TYPE
		SYNTAX					 Unsigned32( 0 .. 4294967295 )
		MAX-ACCESS			 read-write
		STATUS					 current
		DESCRIPTION			 " -- "
		::=  { tdsNodeBSystem  15 }


	tdsNodeBBruStatisticAlgorithmSwitch		 OBJECT-TYPE
		SYNTAX					 INTEGER{ off(0),on(1)  }
		MAX-ACCESS			 read-write
		STATUS					 current
		DESCRIPTION			 " -- "
		::=  { tdsNodeBSystem  16 }


	tdsNodeBCODCHLoopSwitch		 OBJECT-TYPE
		SYNTAX					 INTEGER{ off(0),uuOn(1)  }
		MAX-ACCESS			 read-write
		STATUS					 current
		DESCRIPTION			 " -- "
		::=  { tdsNodeBSystem  17 }


	tdsNodeBCODCHLoopUserId		 OBJECT-TYPE
		SYNTAX					 Integer32( 0 .. 1048575 )
		MAX-ACCESS			 read-write
		STATUS					 current
		DESCRIPTION			 " -- "
		::=  { tdsNodeBSystem  18 }


	tdsNodeBSysE1LoopCheckSwitch		 OBJECT-TYPE
		SYNTAX					 INTEGER{ off(0),onKpi(1),onHspa(2)  }
		MAX-ACCESS			 read-write
		STATUS					 current
		DESCRIPTION			 " -- "
		::=  { tdsNodeBSystem  19 }


	tdsNodeBSysRncDisaSwitch		 OBJECT-TYPE
		SYNTAX					 INTEGER{ off(0),on(1)  }
		MAX-ACCESS			 read-write
		STATUS					 current
		DESCRIPTION			 " -- "
		::=  { tdsNodeBSystem  20 }


	tdsNodeBSysRncDisaCheckPeriod		 OBJECT-TYPE
		SYNTAX					 Integer32( 60 .. 86400 )
		MAX-ACCESS			 read-write
		STATUS					 current
		DESCRIPTION			 " -- "
		::=  { tdsNodeBSystem  21 }


	tdsNodeBSysRncDisaStatus		 OBJECT-TYPE
		SYNTAX					 INTEGER{ disasterhappened(1),disasterunhappened(2)  }
		MAX-ACCESS			 read-only
		STATUS					 current
		DESCRIPTION			 " -- "
		::=  { tdsNodeBSystem  22 }


	tdsNodeBSysSwitchToMasterRncTrigger		 OBJECT-TYPE
		SYNTAX					 INTEGER{ off(0),on(1)  }
		MAX-ACCESS			 read-write
		STATUS					 current
		DESCRIPTION			 " -- "
		::=  { tdsNodeBSystem  23 }


	tdsSysStartMode		 OBJECT IDENTIFIER
		::=  { tdsConfigurationPerformance  2 }


	tdsSysBruReportMode		 OBJECT-TYPE
		SYNTAX					 INTEGER{ notsdma(0),sdma(1)  }
		MAX-ACCESS			 read-write
		STATUS					 current
		DESCRIPTION			 " -- "
		::=  { tdsSysStartMode  1 }


	tdsSysISCPDetectPeriod		 OBJECT-TYPE
		SYNTAX					 Integer32( 5 .. 720|0 )
		MAX-ACCESS			 read-write
		STATUS					 current
		DESCRIPTION			 " -- "
		::=  { tdsSysStartMode  2 }


	tdsSysPolarAntDisaRecSwitch		 OBJECT-TYPE
		SYNTAX					 INTEGER{ off(0),on(1)  }
		MAX-ACCESS			 read-write
		STATUS					 current
		DESCRIPTION			 " -- "
		::=  { tdsSysStartMode  3 }


	tdsSysBbuAssignMode		 OBJECT-TYPE
		SYNTAX					 INTEGER{ powerSavingFirst(0),performanceFirst(1)  }
		MAX-ACCESS			 read-write
		STATUS					 current
		DESCRIPTION			 " -- "
		::=  { tdsSysStartMode  4 }


	tdsSysCarrierSlotISCPDetectPeriod		 OBJECT-TYPE
		SYNTAX					 Integer32( 0|3 .. 60 )
		MAX-ACCESS			 read-write
		STATUS					 current
		DESCRIPTION			 " -- "
		::=  { tdsSysStartMode  5 }


	tdsSysGpsShiftSwitch		 OBJECT-TYPE
		SYNTAX					 INTEGER{ off(0),on(1)  }
		MAX-ACCESS			 read-write
		STATUS					 current
		DESCRIPTION			 " -- "
		::=  { tdsSysStartMode  6 }


	tdsSysnfdetect		 OBJECT-TYPE
		SYNTAX					 Unsigned32( 1 .. 255 )
		MAX-ACCESS			 read-write
		STATUS					 current
		DESCRIPTION			 " -- "
		::=  { tdsSysStartMode  7 }


	tdsSysIscpabnormalthreshold		 OBJECT-TYPE
		SYNTAX					 Integer32( -120 .. -60 )
		MAX-ACCESS			 read-write
		STATUS					 current
		DESCRIPTION			 " -- "
		::=  { tdsSysStartMode  8 }


	tdsSysAbnormalSubsfnNum		 OBJECT-TYPE
		SYNTAX					 Unsigned32( 1 .. 255 )
		MAX-ACCESS			 read-write
		STATUS					 current
		DESCRIPTION			 " -- "
		::=  { tdsSysStartMode  9 }


	tdsSysGpsSnrThreshold		 OBJECT-TYPE
		SYNTAX					 Integer32( 0 .. 9 )
		MAX-ACCESS			 read-write
		STATUS					 current
		DESCRIPTION			 " -- "
		::=  { tdsSysStartMode  10 }


	tdsSysRruAcRxDelay		 OBJECT-TYPE
		SYNTAX					 Integer32( 0 .. 9 )
		MAX-ACCESS			 read-write
		STATUS					 current
		DESCRIPTION			 " -- "
		::=  { tdsSysStartMode  11 }


	tdsSysBbuOmLogRecSwitch		 OBJECT-TYPE
		SYNTAX					 INTEGER{ off(0),onDynCfg(1),onPerfStat(2),onDynCfgAndPerfStat(3),onAlm(4),onDynCfgAndAlm(5),onPerfStatAndAlm(6),onDynCfgAndPerfStatAndAlm(7),onSfnCal(8),onDynCfgAndSfnCal(9),onPerfStatAndSfnCal(10),onDynCfgAndPerfStatAndSfnCal(11),onAlmAndSfnCal(12),onDynCfgAndAlmAndSfnCal(13),onPerfStatAndAlmAndSfnCal(14),onAll(15)  }
		MAX-ACCESS			 read-write
		STATUS					 current
		DESCRIPTION			 " -- "
		::=  { tdsSysStartMode  12 }


	closeCarrier		 OBJECT IDENTIFIER
		::=  { tdsConfigurationPerformance  3 }


	closeBaseBandCarFrameNo		 OBJECT-TYPE
		SYNTAX					 Integer32( 0 .. 0 )
		MAX-ACCESS			 read-write
		STATUS					 current
		DESCRIPTION			 " -- "
		::=  { closeCarrier  1 }


	closeBaseBandCarSlotNo		 OBJECT-TYPE
		SYNTAX					 Integer32( 1 .. 7 )
		MAX-ACCESS			 read-write
		STATUS					 current
		DESCRIPTION			 " -- "
		::=  { closeCarrier  2 }


	closeBaseBandCarStartIndex		 OBJECT-TYPE
		SYNTAX					 Integer32( 0 .. 17 )
		MAX-ACCESS			 read-write
		STATUS					 current
		DESCRIPTION			 " -- "
		::=  { closeCarrier  3 }


	closeBaseBandCarEndIndex		 OBJECT-TYPE
		SYNTAX					 Integer32( 0 .. 17 )
		MAX-ACCESS			 read-write
		STATUS					 current
		DESCRIPTION			 " -- "
		::=  { closeCarrier  4 }


	closeBaseBandCarState		 OBJECT-TYPE
		SYNTAX					 INTEGER{ open(0),close(1)  }
		MAX-ACCESS			 read-write
		STATUS					 current
		DESCRIPTION			 " -- "
		::=  { closeCarrier  5 }


	hl		 OBJECT IDENTIFIER
		::=  { tdsSuperNodeB  2 }


	nbap		 OBJECT IDENTIFIER
		::=  { hl  1 }


	nbapCommon		 OBJECT IDENTIFIER
		::=  { nbap  1 }


	nbapNodeBResetTrigger		 OBJECT-TYPE
		SYNTAX					 INTEGER{ off(0),on(1)  }
		MAX-ACCESS			 read-write
		STATUS					 current
		DESCRIPTION			 " -- "
		::=  { nbapCommon  1 }


	nbapAuditTrigger		 OBJECT-TYPE
		SYNTAX					 INTEGER{ off(0),on(1)  }
		MAX-ACCESS			 read-write
		STATUS					 current
		DESCRIPTION			 " -- "
		::=  { nbapCommon  2 }


	nbapMutualCarrierNode		 OBJECT IDENTIFIER
		::=  { nbap  2 }


	nbapCarrierPriority		 OBJECT-TYPE
		SYNTAX					 INTEGER{ r4High(0),r5High(1),r4Equalr5(2)  }
		MAX-ACCESS			 read-write
		STATUS					 current
		DESCRIPTION			 " -- "
		::=  { nbapMutualCarrierNode  1 }


	nbapCarrierPreemptTimer		 OBJECT-TYPE
		SYNTAX					 Integer32( 0 .. 10000 )
		MAX-ACCESS			 read-write
		STATUS					 current
		DESCRIPTION			 " -- "
		::=  { nbapMutualCarrierNode  2 }


	nbapR4CarrierPriority		 OBJECT-TYPE
		SYNTAX					 INTEGER{ classOne(20),classTwo(30),classThree(40),classFour(50)  }
		MAX-ACCESS			 read-write
		STATUS					 current
		DESCRIPTION			 " -- "
		::=  { nbapMutualCarrierNode  3 }


	nbapHsdpaCarrierPriority		 OBJECT-TYPE
		SYNTAX					 INTEGER{ classOne(20),classTwo(30),classThree(40),classFour(50)  }
		MAX-ACCESS			 read-write
		STATUS					 current
		DESCRIPTION			 " -- "
		::=  { nbapMutualCarrierNode  4 }


	nbapMBMSCarrierPriority		 OBJECT-TYPE
		SYNTAX					 INTEGER{ classOne(20),classTwo(30),classThree(40),classFour(50)  }
		MAX-ACCESS			 read-write
		STATUS					 current
		DESCRIPTION			 " -- "
		::=  { nbapMutualCarrierNode  5 }


	nbapHsupaCarrierPriority		 OBJECT-TYPE
		SYNTAX					 INTEGER{ classOne(20),classTwo(30),classThree(40),classFour(50)  }
		MAX-ACCESS			 read-write
		STATUS					 current
		DESCRIPTION			 " -- "
		::=  { nbapMutualCarrierNode  6 }


	nbapMbmsNode		 OBJECT IDENTIFIER
		::=  { nbap  3 }


	nbapRandomPhaseSupport		 OBJECT-TYPE
		SYNTAX					 INTEGER{ unsupport(0),support(1)  }
		MAX-ACCESS			 read-write
		STATUS					 current
		DESCRIPTION			 " -- "
		::=  { nbapMbmsNode  1 }


	aps		 OBJECT IDENTIFIER
		::=  { nbap  4 }


	apsFpHrntiIndTimer		 OBJECT-TYPE
		SYNTAX					 Integer32( 100 .. 20000 )
		MAX-ACCESS			 read-write
		STATUS					 current
		DESCRIPTION			 " -- "
		::=  { aps  1 }


	apb		 OBJECT IDENTIFIER
		::=  { nbap  5 }


	apbMaxJointCmrFlag		 OBJECT-TYPE
		SYNTAX					 INTEGER{ off(0),on(1)  }
		MAX-ACCESS			 read-write
		STATUS					 current
		DESCRIPTION			 " -- "
		::=  { apb  4 }


	apbMaxJointCmrNum		 OBJECT-TYPE
		SYNTAX					 Integer32( 20 .. 120 )
		MAX-ACCESS			 read-write
		STATUS					 current
		DESCRIPTION			 " -- "
		::=  { apb  5 }


	machs		 OBJECT IDENTIFIER
		::=  { hl  2 }


	hsdpaAlgorithmNode		 OBJECT IDENTIFIER
		::=  { machs  1 }


	hsdpaAlgorithmTable		 OBJECT-TYPE
		SYNTAX					 SEQUENCE  OF	 HsdpaAlgorithmEntry
		MAX-ACCESS			 not-accessible
		STATUS					 current
		DESCRIPTION			 " -- "
		::=  { hsdpaAlgorithmNode  1 }


	hsdpaAlgorithmEntry		 OBJECT-TYPE
		SYNTAX					 HsdpaAlgorithmEntry
		MAX-ACCESS			 not-accessible
		STATUS					 current
		DESCRIPTION			 " -- "
		INDEX						{ hsdpaAlgorithmLcId }
		::=  { hsdpaAlgorithmTable  1 }


	HsdpaAlgorithmEntry		 ::=  SEQUENCE {
		hsdpaAlgorithmLcId					Integer32,
		hsdpaAlgorithmRowStatus					RowStatus,
		hsdpaSchedAlgorithm					INTEGER,
		hsdpaFlowCtrlAlgorithm					INTEGER,
		hsdpaCellSchedAdjRate					INTEGER
		}


	hsdpaAlgorithmLcId		 OBJECT-TYPE
		SYNTAX					 Integer32( 0 .. 11 )
		MAX-ACCESS			 not-accessible
		STATUS					 current
		DESCRIPTION			 " -- "
		::=  { hsdpaAlgorithmEntry  1 }


	hsdpaAlgorithmRowStatus		 OBJECT-TYPE
		SYNTAX					 RowStatus
		MAX-ACCESS			 read-only
		STATUS					 current
		DESCRIPTION			 " -- "
		::=  { hsdpaAlgorithmEntry  2 }


	hsdpaSchedAlgorithm		 OBJECT-TYPE
		SYNTAX					 INTEGER{ pf(0),maxci(1),roundRobin(2)  }
		MAX-ACCESS			 read-write
		STATUS					 current
		DESCRIPTION			 " -- "
		::=  { hsdpaAlgorithmEntry  3 }


	hsdpaFlowCtrlAlgorithm		 OBJECT-TYPE
		SYNTAX					 INTEGER{ simpleCtrl(0)  }
		MAX-ACCESS			 read-write
		STATUS					 current
		DESCRIPTION			 " -- "
		::=  { hsdpaAlgorithmEntry  4 }


	hsdpaCellSchedAdjRate		 OBJECT-TYPE
		SYNTAX					 INTEGER{ nojump(0),evenjump(1),jump(2)  }
		MAX-ACCESS			 read-write
		STATUS					 current
		DESCRIPTION			 " -- "
		::=  { hsdpaAlgorithmEntry  5 }


	hsdpaSchedAlgorithmNode		 OBJECT IDENTIFIER
		::=  { hsdpaAlgorithmNode  2 }


	hsdpaCQIReviseTable		 OBJECT-TYPE
		SYNTAX					 SEQUENCE  OF	 HsdpaCQIReviseEntry
		MAX-ACCESS			 not-accessible
		STATUS					 current
		DESCRIPTION			 " -- "
		::=  { hsdpaSchedAlgorithmNode  1 }


	hsdpaCQIReviseEntry		 OBJECT-TYPE
		SYNTAX					 HsdpaCQIReviseEntry
		MAX-ACCESS			 not-accessible
		STATUS					 current
		DESCRIPTION			 " -- "
		INDEX						{ hsdpaCQIReviseLcId }
		::=  { hsdpaCQIReviseTable  1 }


	HsdpaCQIReviseEntry		 ::=  SEQUENCE {
		hsdpaCQIReviseLcId					Integer32,
		hsdpaCQIRowStatus					RowStatus,
		hsdpaCQIReviseSwitch					INTEGER,
		hsdpaCQIStep					Integer32,
		hsdpaCQIMaxRTBSadd					Integer32,
		hsdpaCQIMinRTBSadd					Integer32,
		hsdpaCQIInitBLER					Integer32,
		hsdpaCQIResidualBLER					Integer32,
		hsdpaCQIMFR					Integer32,
		hsdpaCQIRestrictMFFlag					INTEGER,
		hsdpaCQIMaxDiff					Integer32,
		hsdpaCQIMinDiff					Integer32,
		hsdpaCQIInstantWinSize					Integer32,
		hsdpaCQIInstantThreshold					Integer32,
		hsdpaCQIVinSmoothGene					Integer32,
		hsdpaCQIACKLostRate					Integer32,
		hsdpaCQINACKLostRate					Integer32,
		hsdpaCQIACKToNACKRatio					Integer32,
		hsdpaCQINACKToACKRatio					Integer32,
		hsdpaCQIRestrictMaxRTBSFlag					INTEGER,
		hsdpaCQIRestrictMaxRTBS					Integer32
		}


	hsdpaCQIReviseLcId		 OBJECT-TYPE
		SYNTAX					 Integer32( 0 .. 11 )
		MAX-ACCESS			 not-accessible
		STATUS					 current
		DESCRIPTION			 " -- "
		::=  { hsdpaCQIReviseEntry  1 }


	hsdpaCQIRowStatus		 OBJECT-TYPE
		SYNTAX					 RowStatus
		MAX-ACCESS			 read-only
		STATUS					 current
		DESCRIPTION			 " -- "
		::=  { hsdpaCQIReviseEntry  2 }


	hsdpaCQIReviseSwitch		 OBJECT-TYPE
		SYNTAX					 INTEGER{ off(0),rtbs(1),codeRate(2)  }
		MAX-ACCESS			 read-write
		STATUS					 current
		DESCRIPTION			 " -- "
		::=  { hsdpaCQIReviseEntry  3 }


	hsdpaCQIStep		 OBJECT-TYPE
		SYNTAX					 Integer32( 0 .. 255 )
		MAX-ACCESS			 read-write
		STATUS					 current
		DESCRIPTION			 " -- "
		::=  { hsdpaCQIReviseEntry  4 }


	hsdpaCQIMaxRTBSadd		 OBJECT-TYPE
		SYNTAX					 Integer32( -128 .. 127 )
		MAX-ACCESS			 read-write
		STATUS					 current
		DESCRIPTION			 " -- "
		::=  { hsdpaCQIReviseEntry  5 }


	hsdpaCQIMinRTBSadd		 OBJECT-TYPE
		SYNTAX					 Integer32( -128 .. 127 )
		MAX-ACCESS			 read-write
		STATUS					 current
		DESCRIPTION			 " -- "
		::=  { hsdpaCQIReviseEntry  6 }


	hsdpaCQIInitBLER		 OBJECT-TYPE
		SYNTAX					 Integer32( 1 .. 20 )
		MAX-ACCESS			 read-write
		STATUS					 current
		DESCRIPTION			 " -- "
		::=  { hsdpaCQIReviseEntry  7 }


	hsdpaCQIResidualBLER		 OBJECT-TYPE
		SYNTAX					 Integer32( 1 .. 20 )
		MAX-ACCESS			 read-write
		STATUS					 current
		DESCRIPTION			 " -- "
		::=  { hsdpaCQIReviseEntry  8 }


	hsdpaCQIMFR		 OBJECT-TYPE
		SYNTAX					 Integer32( 1 .. 10 )
		MAX-ACCESS			 read-write
		STATUS					 current
		DESCRIPTION			 " -- "
		::=  { hsdpaCQIReviseEntry  9 }


	hsdpaCQIRestrictMFFlag		 OBJECT-TYPE
		SYNTAX					 INTEGER{ unrestricted(0),restricted(1)  }
		MAX-ACCESS			 read-write
		STATUS					 current
		DESCRIPTION			 " -- "
		::=  { hsdpaCQIReviseEntry  10 }


	hsdpaCQIMaxDiff		 OBJECT-TYPE
		SYNTAX					 Integer32( -500 .. 500 )
		MAX-ACCESS			 read-write
		STATUS					 current
		DESCRIPTION			 " -- "
		::=  { hsdpaCQIReviseEntry  11 }


	hsdpaCQIMinDiff		 OBJECT-TYPE
		SYNTAX					 Integer32( -500 .. 500 )
		MAX-ACCESS			 read-write
		STATUS					 current
		DESCRIPTION			 " -- "
		::=  { hsdpaCQIReviseEntry  12 }


	hsdpaCQIInstantWinSize		 OBJECT-TYPE
		SYNTAX					 Integer32( 1 .. 16 )
		MAX-ACCESS			 read-write
		STATUS					 current
		DESCRIPTION			 " -- "
		::=  { hsdpaCQIReviseEntry  13 }


	hsdpaCQIInstantThreshold		 OBJECT-TYPE
		SYNTAX					 Integer32( 1 .. 10000 )
		MAX-ACCESS			 read-write
		STATUS					 current
		DESCRIPTION			 " -- "
		::=  { hsdpaCQIReviseEntry  14 }


	hsdpaCQIVinSmoothGene		 OBJECT-TYPE
		SYNTAX					 Integer32( 0 .. 10000 )
		MAX-ACCESS			 read-write
		STATUS					 current
		DESCRIPTION			 " -- "
		::=  { hsdpaCQIReviseEntry  15 }


	hsdpaCQIACKLostRate		 OBJECT-TYPE
		SYNTAX					 Integer32( 0 .. 10000 )
		MAX-ACCESS			 read-write
		STATUS					 current
		DESCRIPTION			 " -- "
		::=  { hsdpaCQIReviseEntry  16 }


	hsdpaCQINACKLostRate		 OBJECT-TYPE
		SYNTAX					 Integer32( 0 .. 10000 )
		MAX-ACCESS			 read-write
		STATUS					 current
		DESCRIPTION			 " -- "
		::=  { hsdpaCQIReviseEntry  17 }


	hsdpaCQIACKToNACKRatio		 OBJECT-TYPE
		SYNTAX					 Integer32( 0 .. 100 )
		MAX-ACCESS			 read-write
		STATUS					 current
		DESCRIPTION			 " -- "
		::=  { hsdpaCQIReviseEntry  18 }


	hsdpaCQINACKToACKRatio		 OBJECT-TYPE
		SYNTAX					 Integer32( 0 .. 10 )
		MAX-ACCESS			 read-write
		STATUS					 current
		DESCRIPTION			 " -- "
		::=  { hsdpaCQIReviseEntry  19 }


	hsdpaCQIRestrictMaxRTBSFlag		 OBJECT-TYPE
		SYNTAX					 INTEGER{ unrestricted(0),restricted(1)  }
		MAX-ACCESS			 read-write
		STATUS					 current
		DESCRIPTION			 " -- "
		::=  { hsdpaCQIReviseEntry  20 }


	hsdpaCQIRestrictMaxRTBS		 OBJECT-TYPE
		SYNTAX					 Integer32( 0 .. 63 )
		MAX-ACCESS			 read-write
		STATUS					 current
		DESCRIPTION			 " -- "
		::=  { hsdpaCQIReviseEntry  21 }


	hsdpaPFTable		 OBJECT-TYPE
		SYNTAX					 SEQUENCE  OF	 HsdpaPFEntry
		MAX-ACCESS			 not-accessible
		STATUS					 current
		DESCRIPTION			 " -- "
		::=  { hsdpaSchedAlgorithmNode  2 }


	hsdpaPFEntry		 OBJECT-TYPE
		SYNTAX					 HsdpaPFEntry
		MAX-ACCESS			 not-accessible
		STATUS					 current
		DESCRIPTION			 " -- "
		INDEX						{ hsdpaPFLcId }
		::=  { hsdpaPFTable  1 }


	HsdpaPFEntry		 ::=  SEQUENCE {
		hsdpaPFLcId					Integer32,
		hsdpaPFRowStatus					RowStatus,
		hsdpaPFTcSlideWindowSize					Integer32,
		hsdpaPFInitPF					Integer32
		}


	hsdpaPFLcId		 OBJECT-TYPE
		SYNTAX					 Integer32( 0 .. 11 )
		MAX-ACCESS			 not-accessible
		STATUS					 current
		DESCRIPTION			 " -- "
		::=  { hsdpaPFEntry  1 }


	hsdpaPFRowStatus		 OBJECT-TYPE
		SYNTAX					 RowStatus
		MAX-ACCESS			 read-only
		STATUS					 current
		DESCRIPTION			 " -- "
		::=  { hsdpaPFEntry  2 }


	hsdpaPFTcSlideWindowSize		 OBJECT-TYPE
		SYNTAX					 Integer32( 1 .. 65535 )
		MAX-ACCESS			 read-write
		STATUS					 current
		DESCRIPTION			 " -- "
		::=  { hsdpaPFEntry  3 }


	hsdpaPFInitPF		 OBJECT-TYPE
		SYNTAX					 Integer32( 0 .. 65535 )
		MAX-ACCESS			 read-write
		STATUS					 current
		DESCRIPTION			 " -- "
		::=  { hsdpaPFEntry  4 }


	hsdpaMAXCITable		 OBJECT-TYPE
		SYNTAX					 SEQUENCE  OF	 HsdpaMAXCIEntry
		MAX-ACCESS			 not-accessible
		STATUS					 current
		DESCRIPTION			 " -- "
		::=  { hsdpaSchedAlgorithmNode  3 }


	hsdpaMAXCIEntry		 OBJECT-TYPE
		SYNTAX					 HsdpaMAXCIEntry
		MAX-ACCESS			 not-accessible
		STATUS					 current
		DESCRIPTION			 " -- "
		INDEX						{ hsdpaMaxCILcId }
		::=  { hsdpaMAXCITable  1 }


	HsdpaMAXCIEntry		 ::=  SEQUENCE {
		hsdpaMaxCILcId					Integer32,
		hsdpaMaxCIRowStatus					RowStatus,
		hsdpaMaxCITmR					Integer32
		}


	hsdpaMaxCILcId		 OBJECT-TYPE
		SYNTAX					 Integer32( 0 .. 11 )
		MAX-ACCESS			 not-accessible
		STATUS					 current
		DESCRIPTION			 " -- "
		::=  { hsdpaMAXCIEntry  1 }


	hsdpaMaxCIRowStatus		 OBJECT-TYPE
		SYNTAX					 RowStatus
		MAX-ACCESS			 read-only
		STATUS					 current
		DESCRIPTION			 " -- "
		::=  { hsdpaMAXCIEntry  2 }


	hsdpaMaxCITmR		 OBJECT-TYPE
		SYNTAX					 Integer32( 0 .. 65535 )
		MAX-ACCESS			 read-write
		STATUS					 current
		DESCRIPTION			 " -- "
		::=  { hsdpaMAXCIEntry  3 }


	hsdpaRoundRobin		 OBJECT IDENTIFIER
		::=  { hsdpaSchedAlgorithmNode  4 }


	hsdpaQosTable		 OBJECT-TYPE
		SYNTAX					 SEQUENCE  OF	 HsdpaQosEntry
		MAX-ACCESS			 not-accessible
		STATUS					 current
		DESCRIPTION			 " -- "
		::=  { hsdpaSchedAlgorithmNode  5 }


	hsdpaQosEntry		 OBJECT-TYPE
		SYNTAX					 HsdpaQosEntry
		MAX-ACCESS			 not-accessible
		STATUS					 current
		DESCRIPTION			 " -- "
		INDEX						{ hsdpaQosLcId }
		::=  { hsdpaQosTable  1 }


	HsdpaQosEntry		 ::=  SEQUENCE {
		hsdpaQosLcId					Integer32,
		hsdpaQosRowStatus					RowStatus,
		hsdpaQosSwitch					INTEGER,
		hsdpaQosRTExtraPriority					Integer32,
		hsdpaSpiAPrioFlag					INTEGER,
		hsdpaSpiDiscardTimer					Integer32,
		hsdpaSpiTmRate					INTEGER,
		hsdpaSpiTcWinSize					Integer32,
		hsdpaSpiNonGBRDelta					Integer32,
		hsdpaSpi1Weight					Integer32,
		hsdpaSpi2Weight					Integer32,
		hsdpaSpi3Weight					Integer32,
		hsdpaSpi4Weight					Integer32,
		hsdpaSpi5Weight					Integer32,
		hsdpaSpi6Weight					Integer32,
		hsdpaSpi7Weight					Integer32,
		hsdpaSpi8Weight					Integer32,
		hsdpaSpi9Weight					Integer32,
		hsdpaSpi10Weight					Integer32,
		hsdpaSpi11Weight					Integer32,
		hsdpaSpi12Weight					Integer32,
		hsdpaSpi13Weight					Integer32,
		hsdpaSpi14Weight					Integer32,
		hsdpaSpi15Weight					Integer32,
		hsdpaSpi16Weight					Integer32
		}


	hsdpaQosLcId		 OBJECT-TYPE
		SYNTAX					 Integer32( 0 .. 11 )
		MAX-ACCESS			 not-accessible
		STATUS					 current
		DESCRIPTION			 " -- "
		::=  { hsdpaQosEntry  1 }


	hsdpaQosRowStatus		 OBJECT-TYPE
		SYNTAX					 RowStatus
		MAX-ACCESS			 read-only
		STATUS					 current
		DESCRIPTION			 " -- "
		::=  { hsdpaQosEntry  2 }


	hsdpaQosSwitch		 OBJECT-TYPE
		SYNTAX					 INTEGER{ off(0),qos(1),spi(2)  }
		MAX-ACCESS			 read-write
		STATUS					 current
		DESCRIPTION			 " -- "
		::=  { hsdpaQosEntry  3 }


	hsdpaQosRTExtraPriority		 OBJECT-TYPE
		SYNTAX					 Integer32( 0 .. 255 )
		MAX-ACCESS			 read-write
		STATUS					 current
		DESCRIPTION			 " -- "
		::=  { hsdpaQosEntry  4 }


	hsdpaSpiAPrioFlag		 OBJECT-TYPE
		SYNTAX					 INTEGER{ aspiFirst(0),atdFirst(1)  }
		MAX-ACCESS			 read-write
		STATUS					 current
		DESCRIPTION			 " -- "
		::=  { hsdpaQosEntry  5 }


	hsdpaSpiDiscardTimer		 OBJECT-TYPE
		SYNTAX					 Integer32( 40 .. 2000 )
		MAX-ACCESS			 read-write
		STATUS					 current
		DESCRIPTION			 " -- "
		::=  { hsdpaQosEntry  6 }


	hsdpaSpiTmRate		 OBJECT-TYPE
		SYNTAX					 INTEGER{ val0(0),val2(2),val4(4),val6(6),val8(8),val10(10),val100(100),val1000(1000)  }
		MAX-ACCESS			 read-write
		STATUS					 current
		DESCRIPTION			 " -- "
		::=  { hsdpaQosEntry  7 }


	hsdpaSpiTcWinSize		 OBJECT-TYPE
		SYNTAX					 Integer32( 1 .. 65535 )
		MAX-ACCESS			 read-write
		STATUS					 current
		DESCRIPTION			 " -- "
		::=  { hsdpaQosEntry  8 }


	hsdpaSpiNonGBRDelta		 OBJECT-TYPE
		SYNTAX					 Integer32( 1 .. 2800 )
		MAX-ACCESS			 read-write
		STATUS					 current
		DESCRIPTION			 " -- "
		::=  { hsdpaQosEntry  9 }


	hsdpaSpi1Weight		 OBJECT-TYPE
		SYNTAX					 Integer32( 10 .. 30 )
		MAX-ACCESS			 read-write
		STATUS					 current
		DESCRIPTION			 " -- "
		::=  { hsdpaQosEntry  10 }


	hsdpaSpi2Weight		 OBJECT-TYPE
		SYNTAX					 Integer32( 10 .. 30 )
		MAX-ACCESS			 read-write
		STATUS					 current
		DESCRIPTION			 " -- "
		::=  { hsdpaQosEntry  11 }


	hsdpaSpi3Weight		 OBJECT-TYPE
		SYNTAX					 Integer32( 10 .. 30 )
		MAX-ACCESS			 read-write
		STATUS					 current
		DESCRIPTION			 " -- "
		::=  { hsdpaQosEntry  12 }


	hsdpaSpi4Weight		 OBJECT-TYPE
		SYNTAX					 Integer32( 10 .. 30 )
		MAX-ACCESS			 read-write
		STATUS					 current
		DESCRIPTION			 " -- "
		::=  { hsdpaQosEntry  13 }


	hsdpaSpi5Weight		 OBJECT-TYPE
		SYNTAX					 Integer32( 10 .. 30 )
		MAX-ACCESS			 read-write
		STATUS					 current
		DESCRIPTION			 " -- "
		::=  { hsdpaQosEntry  14 }


	hsdpaSpi6Weight		 OBJECT-TYPE
		SYNTAX					 Integer32( 10 .. 30 )
		MAX-ACCESS			 read-write
		STATUS					 current
		DESCRIPTION			 " -- "
		::=  { hsdpaQosEntry  15 }


	hsdpaSpi7Weight		 OBJECT-TYPE
		SYNTAX					 Integer32( 10 .. 30 )
		MAX-ACCESS			 read-write
		STATUS					 current
		DESCRIPTION			 " -- "
		::=  { hsdpaQosEntry  16 }


	hsdpaSpi8Weight		 OBJECT-TYPE
		SYNTAX					 Integer32( 10 .. 30 )
		MAX-ACCESS			 read-write
		STATUS					 current
		DESCRIPTION			 " -- "
		::=  { hsdpaQosEntry  17 }


	hsdpaSpi9Weight		 OBJECT-TYPE
		SYNTAX					 Integer32( 10 .. 30 )
		MAX-ACCESS			 read-write
		STATUS					 current
		DESCRIPTION			 " -- "
		::=  { hsdpaQosEntry  18 }


	hsdpaSpi10Weight		 OBJECT-TYPE
		SYNTAX					 Integer32( 10 .. 30 )
		MAX-ACCESS			 read-write
		STATUS					 current
		DESCRIPTION			 " -- "
		::=  { hsdpaQosEntry  19 }


	hsdpaSpi11Weight		 OBJECT-TYPE
		SYNTAX					 Integer32( 10 .. 30 )
		MAX-ACCESS			 read-write
		STATUS					 current
		DESCRIPTION			 " -- "
		::=  { hsdpaQosEntry  20 }


	hsdpaSpi12Weight		 OBJECT-TYPE
		SYNTAX					 Integer32( 10 .. 30 )
		MAX-ACCESS			 read-write
		STATUS					 current
		DESCRIPTION			 " -- "
		::=  { hsdpaQosEntry  21 }


	hsdpaSpi13Weight		 OBJECT-TYPE
		SYNTAX					 Integer32( 10 .. 30 )
		MAX-ACCESS			 read-write
		STATUS					 current
		DESCRIPTION			 " -- "
		::=  { hsdpaQosEntry  22 }


	hsdpaSpi14Weight		 OBJECT-TYPE
		SYNTAX					 Integer32( 10 .. 30 )
		MAX-ACCESS			 read-write
		STATUS					 current
		DESCRIPTION			 " -- "
		::=  { hsdpaQosEntry  23 }


	hsdpaSpi15Weight		 OBJECT-TYPE
		SYNTAX					 Integer32( 10 .. 30 )
		MAX-ACCESS			 read-write
		STATUS					 current
		DESCRIPTION			 " -- "
		::=  { hsdpaQosEntry  24 }


	hsdpaSpi16Weight		 OBJECT-TYPE
		SYNTAX					 Integer32( 10 .. 30 )
		MAX-ACCESS			 read-write
		STATUS					 current
		DESCRIPTION			 " -- "
		::=  { hsdpaQosEntry  25 }


	hsdpaFlowCtrlAlgorithmNode		 OBJECT IDENTIFIER
		::=  { hsdpaAlgorithmNode  3 }


	hsdpaSimpleFlowCtrlTable		 OBJECT-TYPE
		SYNTAX					 SEQUENCE  OF	 HsdpaSimpleFlowCtrlEntry
		MAX-ACCESS			 not-accessible
		STATUS					 current
		DESCRIPTION			 " -- "
		::=  { hsdpaFlowCtrlAlgorithmNode  1 }


	hsdpaSimpleFlowCtrlEntry		 OBJECT-TYPE
		SYNTAX					 HsdpaSimpleFlowCtrlEntry
		MAX-ACCESS			 not-accessible
		STATUS					 current
		DESCRIPTION			 " -- "
		INDEX						{ hsdpaSFCtrlLcId }
		::=  { hsdpaSimpleFlowCtrlTable  1 }


	HsdpaSimpleFlowCtrlEntry		 ::=  SEQUENCE {
		hsdpaSFCtrlLcId					Integer32,
		hsdpaSFCRowStatus					RowStatus,
		hsdpaSFCBLThresholdLow					Unsigned32,
		hsdpaSFCBLThresholdHigh					Unsigned32,
		hsdpaSFCUuRateType					INTEGER,
		hsdpaSFCMaxPeriodTime					Integer32,
		hsdpaSFCUuAvgRateWin					Integer32,
		hsdpaSFCGbrMultiple					Integer32,
		hsdpaSFCTotalIubMultiple					Integer32,
		hsdpaSFCQueIubUuMultiple					Integer32,
		hsdpaSFCExtPDUNum					Integer32,
		hsdpaSFCIubDelay					Integer32,
		hsdpaSFCThHighDelta					INTEGER,
		hsdpaSFCBEHighDelta					INTEGER,
		hsdpaSFCMinThHigh					Integer32,
		hsdpaSFCMinThLow					Integer32,
		hsdpaSFCMacehsExtPDUNum					Integer32,
		hsdpaSFCMacehsPduBitLen					Integer32,
		hsdpaSFCEFACHBLThresholdLow					Unsigned32,
		hsdpaSFCEFACHBLThresholdHigh					Unsigned32,
		hsdpaSFCMinMacPduNum					Integer32,
		hsdpaSFCWaitDataThreshold					Integer32
		}


	hsdpaSFCtrlLcId		 OBJECT-TYPE
		SYNTAX					 Integer32( 0 .. 11 )
		MAX-ACCESS			 not-accessible
		STATUS					 current
		DESCRIPTION			 " -- "
		::=  { hsdpaSimpleFlowCtrlEntry  1 }


	hsdpaSFCRowStatus		 OBJECT-TYPE
		SYNTAX					 RowStatus
		MAX-ACCESS			 read-only
		STATUS					 current
		DESCRIPTION			 " -- "
		::=  { hsdpaSimpleFlowCtrlEntry  2 }


	hsdpaSFCBLThresholdLow		 OBJECT-TYPE
		SYNTAX					 Unsigned32( 0 .. 4294967295 )
		MAX-ACCESS			 read-write
		STATUS					 current
		DESCRIPTION			 " -- "
		::=  { hsdpaSimpleFlowCtrlEntry  3 }


	hsdpaSFCBLThresholdHigh		 OBJECT-TYPE
		SYNTAX					 Unsigned32( 0 .. 4294967295 )
		MAX-ACCESS			 read-write
		STATUS					 current
		DESCRIPTION			 " -- "
		::=  { hsdpaSimpleFlowCtrlEntry  4 }


	hsdpaSFCUuRateType		 OBJECT-TYPE
		SYNTAX					 INTEGER{ averageRate(0),instantRate(1)  }
		MAX-ACCESS			 read-write
		STATUS					 current
		DESCRIPTION			 " -- "
		::=  { hsdpaSimpleFlowCtrlEntry  5 }


	hsdpaSFCMaxPeriodTime		 OBJECT-TYPE
		SYNTAX					 Integer32( 5 .. 50 )
		MAX-ACCESS			 read-write
		STATUS					 current
		DESCRIPTION			 " -- "
		::=  { hsdpaSimpleFlowCtrlEntry  6 }


	hsdpaSFCUuAvgRateWin		 OBJECT-TYPE
		SYNTAX					 Integer32( 4 .. 128 )
		MAX-ACCESS			 read-write
		STATUS					 current
		DESCRIPTION			 " -- "
		::=  { hsdpaSimpleFlowCtrlEntry  7 }


	hsdpaSFCGbrMultiple		 OBJECT-TYPE
		SYNTAX					 Integer32( 8 .. 30 )
		MAX-ACCESS			 read-write
		STATUS					 current
		DESCRIPTION			 " -- "
		::=  { hsdpaSimpleFlowCtrlEntry  8 }


	hsdpaSFCTotalIubMultiple		 OBJECT-TYPE
		SYNTAX					 Integer32( 10 .. 15 )
		MAX-ACCESS			 read-write
		STATUS					 current
		DESCRIPTION			 " -- "
		::=  { hsdpaSimpleFlowCtrlEntry  9 }


	hsdpaSFCQueIubUuMultiple		 OBJECT-TYPE
		SYNTAX					 Integer32( 10 .. 20 )
		MAX-ACCESS			 read-write
		STATUS					 current
		DESCRIPTION			 " -- "
		::=  { hsdpaSimpleFlowCtrlEntry  10 }


	hsdpaSFCExtPDUNum		 OBJECT-TYPE
		SYNTAX					 Integer32( 0 .. 2 )
		MAX-ACCESS			 read-write
		STATUS					 current
		DESCRIPTION			 " -- "
		::=  { hsdpaSimpleFlowCtrlEntry  11 }


	hsdpaSFCIubDelay		 OBJECT-TYPE
		SYNTAX					 Integer32( 3 .. 5 )
		MAX-ACCESS			 read-write
		STATUS					 current
		DESCRIPTION			 " -- "
		::=  { hsdpaSimpleFlowCtrlEntry  12 }


	hsdpaSFCThHighDelta		 OBJECT-TYPE
		SYNTAX					 INTEGER{ val6(6),val8(8),val12(12),val15(15)  }
		MAX-ACCESS			 read-write
		STATUS					 current
		DESCRIPTION			 " -- "
		::=  { hsdpaSimpleFlowCtrlEntry  13 }


	hsdpaSFCBEHighDelta		 OBJECT-TYPE
		SYNTAX					 INTEGER{ val1(1),val2(2),val3(3)  }
		MAX-ACCESS			 read-write
		STATUS					 current
		DESCRIPTION			 " -- "
		::=  { hsdpaSimpleFlowCtrlEntry  14 }


	hsdpaSFCMinThHigh		 OBJECT-TYPE
		SYNTAX					 Integer32( 0 .. 5120 )
		MAX-ACCESS			 read-write
		STATUS					 current
		DESCRIPTION			 " -- "
		::=  { hsdpaSimpleFlowCtrlEntry  15 }


	hsdpaSFCMinThLow		 OBJECT-TYPE
		SYNTAX					 Integer32( 0 .. 5120 )
		MAX-ACCESS			 read-write
		STATUS					 current
		DESCRIPTION			 " -- "
		::=  { hsdpaSimpleFlowCtrlEntry  16 }


	hsdpaSFCMacehsExtPDUNum		 OBJECT-TYPE
		SYNTAX					 Integer32( 0 .. 255 )
		MAX-ACCESS			 read-write
		STATUS					 current
		DESCRIPTION			 " -- "
		::=  { hsdpaSimpleFlowCtrlEntry  17 }


	hsdpaSFCMacehsPduBitLen		 OBJECT-TYPE
		SYNTAX					 Integer32( 16 .. 12040 )
		MAX-ACCESS			 read-write
		STATUS					 current
		DESCRIPTION			 " -- "
		::=  { hsdpaSimpleFlowCtrlEntry  18 }


	hsdpaSFCEFACHBLThresholdLow		 OBJECT-TYPE
		SYNTAX					 Unsigned32( 0 .. 19456 )
		MAX-ACCESS			 read-write
		STATUS					 current
		DESCRIPTION			 " -- "
		::=  { hsdpaSimpleFlowCtrlEntry  19 }


	hsdpaSFCEFACHBLThresholdHigh		 OBJECT-TYPE
		SYNTAX					 Unsigned32( 0 .. 19456 )
		MAX-ACCESS			 read-write
		STATUS					 current
		DESCRIPTION			 " -- "
		::=  { hsdpaSimpleFlowCtrlEntry  20 }


	hsdpaSFCMinMacPduNum		 OBJECT-TYPE
		SYNTAX					 Integer32( 0 .. 255 )
		MAX-ACCESS			 read-write
		STATUS					 current
		DESCRIPTION			 " -- "
		::=  { hsdpaSimpleFlowCtrlEntry  21 }


	hsdpaSFCWaitDataThreshold		 OBJECT-TYPE
		SYNTAX					 Integer32( 20 .. 255 )
		MAX-ACCESS			 read-write
		STATUS					 current
		DESCRIPTION			 " -- "
		::=  { hsdpaSimpleFlowCtrlEntry  22 }


	hsdpaTfrcAlgorithmNode		 OBJECT IDENTIFIER
		::=  { hsdpaAlgorithmNode  4 }


	hsdpaTfrcAlgorithmTable		 OBJECT-TYPE
		SYNTAX					 SEQUENCE  OF	 HsdpaTfrcAlgorithmEntry
		MAX-ACCESS			 not-accessible
		STATUS					 current
		DESCRIPTION			 " -- "
		::=  { hsdpaTfrcAlgorithmNode  1 }


	hsdpaTfrcAlgorithmEntry		 OBJECT-TYPE
		SYNTAX					 HsdpaTfrcAlgorithmEntry
		MAX-ACCESS			 not-accessible
		STATUS					 current
		DESCRIPTION			 " -- "
		INDEX						{ hsdpaTfrcLcId }
		::=  { hsdpaTfrcAlgorithmTable  1 }


	HsdpaTfrcAlgorithmEntry		 ::=  SEQUENCE {
		hsdpaTfrcLcId					Integer32,
		hsdpaTfrcRowStatus					RowStatus,
		hsdpaTfrcTfrcMode					INTEGER,
		hsdpaTfrcGranularity					INTEGER,
		hsdpaTfrcCtrlChSdmaDegree					INTEGER
		}


	hsdpaTfrcLcId		 OBJECT-TYPE
		SYNTAX					 Integer32( 0 .. 11 )
		MAX-ACCESS			 not-accessible
		STATUS					 current
		DESCRIPTION			 " -- "
		::=  { hsdpaTfrcAlgorithmEntry  1 }


	hsdpaTfrcRowStatus		 OBJECT-TYPE
		SYNTAX					 RowStatus
		MAX-ACCESS			 read-only
		STATUS					 current
		DESCRIPTION			 " -- "
		::=  { hsdpaTfrcAlgorithmEntry  2 }


	hsdpaTfrcTfrcMode		 OBJECT-TYPE
		SYNTAX					 INTEGER{ tdcdPartialTd(0),tdcdPartialCd(1),pureTd(2),allTd(3)  }
		MAX-ACCESS			 read-write
		STATUS					 current
		DESCRIPTION			 " -- "
		::=  { hsdpaTfrcAlgorithmEntry  3 }


	hsdpaTfrcGranularity		 OBJECT-TYPE
		SYNTAX					 INTEGER{ val2(2),val4(4),val8(8),val16(16)  }
		MAX-ACCESS			 read-write
		STATUS					 current
		DESCRIPTION			 " -- "
		::=  { hsdpaTfrcAlgorithmEntry  4 }


	hsdpaTfrcCtrlChSdmaDegree		 OBJECT-TYPE
		SYNTAX					 INTEGER{ noSDMA(1),twoDegree(2),threeDegree(3),fourDegree(4),fiveDegree(5),sixDegree(6),sevenDegree(7),eightDegree(8)  }
		MAX-ACCESS			 read-write
		STATUS					 current
		DESCRIPTION			 " -- "
		::=  { hsdpaTfrcAlgorithmEntry  5 }


	hsdpaCqiPwrCtrlNode		 OBJECT IDENTIFIER
		::=  { hsdpaAlgorithmNode  5 }


	hsdpaCqiPwrCtrlTable		 OBJECT-TYPE
		SYNTAX					 SEQUENCE  OF	 HsdpaCqiPwrCtrlEntry
		MAX-ACCESS			 not-accessible
		STATUS					 current
		DESCRIPTION			 " -- "
		::=  { hsdpaCqiPwrCtrlNode  1 }


	hsdpaCqiPwrCtrlEntry		 OBJECT-TYPE
		SYNTAX					 HsdpaCqiPwrCtrlEntry
		MAX-ACCESS			 not-accessible
		STATUS					 current
		DESCRIPTION			 " -- "
		INDEX						{ hsdpaCqiPwrCtrlLcd }
		::=  { hsdpaCqiPwrCtrlTable  1 }


	HsdpaCqiPwrCtrlEntry		 ::=  SEQUENCE {
		hsdpaCqiPwrCtrlLcd					Integer32,
		hsdpaCqiPwrCtrlRowStatus					RowStatus,
		hsdpaCqiPwrCtrlPcSwitch					INTEGER,
		hsdpaCqiPwrCtrlDownThreshold					Unsigned32,
		hsdpaCqiPwrCtrlDownThresholdQpsk					Unsigned32,
		hsdpaCqiPwrCtrlUpThreshold					Unsigned32,
		hsdpaCqiPwrCtrlWinStep					Unsigned32,
		hsdpaCqiPwrCtrlWinLength					Unsigned32,
		hsdpaCqiPwrCtrlDownStep					INTEGER,
		hsdpaCqiPwrCtrlDownStepQpsk					INTEGER,
		hsdpaCqiPwrCtrlUpStepHigh					INTEGER,
		hsdpaCqiPwrCtrlUpStepLow					INTEGER
		}


	hsdpaCqiPwrCtrlLcd		 OBJECT-TYPE
		SYNTAX					 Integer32( 0 .. 11 )
		MAX-ACCESS			 not-accessible
		STATUS					 current
		DESCRIPTION			 " -- "
		::=  { hsdpaCqiPwrCtrlEntry  1 }


	hsdpaCqiPwrCtrlRowStatus		 OBJECT-TYPE
		SYNTAX					 RowStatus
		MAX-ACCESS			 read-only
		STATUS					 current
		DESCRIPTION			 " -- "
		::=  { hsdpaCqiPwrCtrlEntry  2 }


	hsdpaCqiPwrCtrlPcSwitch		 OBJECT-TYPE
		SYNTAX					 INTEGER{ off(0),on(1)  }
		MAX-ACCESS			 read-write
		STATUS					 current
		DESCRIPTION			 " -- "
		::=  { hsdpaCqiPwrCtrlEntry  3 }


	hsdpaCqiPwrCtrlDownThreshold		 OBJECT-TYPE
		SYNTAX					 Unsigned32( 80 .. 100 )
		MAX-ACCESS			 read-write
		STATUS					 current
		DESCRIPTION			 " -- "
		::=  { hsdpaCqiPwrCtrlEntry  4 }


	hsdpaCqiPwrCtrlDownThresholdQpsk		 OBJECT-TYPE
		SYNTAX					 Unsigned32( 40 .. 50 )
		MAX-ACCESS			 read-write
		STATUS					 current
		DESCRIPTION			 " -- "
		::=  { hsdpaCqiPwrCtrlEntry  5 }


	hsdpaCqiPwrCtrlUpThreshold		 OBJECT-TYPE
		SYNTAX					 Unsigned32( 0 .. 10 )
		MAX-ACCESS			 read-write
		STATUS					 current
		DESCRIPTION			 " -- "
		::=  { hsdpaCqiPwrCtrlEntry  6 }


	hsdpaCqiPwrCtrlWinStep		 OBJECT-TYPE
		SYNTAX					 Unsigned32( 1 .. 15 )
		MAX-ACCESS			 read-write
		STATUS					 current
		DESCRIPTION			 " -- "
		::=  { hsdpaCqiPwrCtrlEntry  7 }


	hsdpaCqiPwrCtrlWinLength		 OBJECT-TYPE
		SYNTAX					 Unsigned32( 1 .. 15 )
		MAX-ACCESS			 read-write
		STATUS					 current
		DESCRIPTION			 " -- "
		::=  { hsdpaCqiPwrCtrlEntry  8 }


	hsdpaCqiPwrCtrlDownStep		 OBJECT-TYPE
		SYNTAX					 INTEGER{ s0dot5dB(0),s1dB(1),s2dB(2),s3dB(3)  }
		MAX-ACCESS			 read-write
		STATUS					 current
		DESCRIPTION			 " -- "
		::=  { hsdpaCqiPwrCtrlEntry  9 }


	hsdpaCqiPwrCtrlDownStepQpsk		 OBJECT-TYPE
		SYNTAX					 INTEGER{ s0dot5dB(0),s1dB(1),s2dB(2),s3dB(3)  }
		MAX-ACCESS			 read-write
		STATUS					 current
		DESCRIPTION			 " -- "
		::=  { hsdpaCqiPwrCtrlEntry  10 }


	hsdpaCqiPwrCtrlUpStepHigh		 OBJECT-TYPE
		SYNTAX					 INTEGER{ s0dot5dB(0),s1dB(1),s2dB(2),s3dB(3)  }
		MAX-ACCESS			 read-write
		STATUS					 current
		DESCRIPTION			 " -- "
		::=  { hsdpaCqiPwrCtrlEntry  11 }


	hsdpaCqiPwrCtrlUpStepLow		 OBJECT-TYPE
		SYNTAX					 INTEGER{ s0dot5dB(0),s1dB(1),s2dB(2),s3dB(3)  }
		MAX-ACCESS			 read-write
		STATUS					 current
		DESCRIPTION			 " -- "
		::=  { hsdpaCqiPwrCtrlEntry  12 }


	hsdpaSpsSchedNode		 OBJECT IDENTIFIER
		::=  { hsdpaAlgorithmNode  6 }


	hsdpaSpsSchedTable		 OBJECT-TYPE
		SYNTAX					 SEQUENCE  OF	 HsdpaSpsSchedEntry
		MAX-ACCESS			 not-accessible
		STATUS					 current
		DESCRIPTION			 " -- "
		::=  { hsdpaSpsSchedNode  1 }


	hsdpaSpsSchedEntry		 OBJECT-TYPE
		SYNTAX					 HsdpaSpsSchedEntry
		MAX-ACCESS			 not-accessible
		STATUS					 current
		DESCRIPTION			 " -- "
		INDEX						{ hsdpaSpsSchedLcId }
		::=  { hsdpaSpsSchedTable  1 }


	HsdpaSpsSchedEntry		 ::=  SEQUENCE {
		hsdpaSpsSchedLcId					Integer32,
		hsdpaSpsSchedRowStatus					RowStatus,
		hsdpaSpsSchedStateTransWin					Integer32,
		hsdpaSpsSchedActivePktTh					Integer32,
		hsdpaSpsSchedSilentPktTh					Integer32,
		hsdpaSpsSchedDynamicSDThFactor					Integer32,
		hsdpaSpsSchedCPCAlphaIndex					Integer32,
		hsdpaSpsSchedResrcBlkTsCfgIndex					Integer32,
		hsdpaSpsSchedResrcBlkCfgIndex					Integer32
		}


	hsdpaSpsSchedLcId		 OBJECT-TYPE
		SYNTAX					 Integer32( 0 .. 11 )
		MAX-ACCESS			 not-accessible
		STATUS					 current
		DESCRIPTION			 " -- "
		::=  { hsdpaSpsSchedEntry  1 }


	hsdpaSpsSchedRowStatus		 OBJECT-TYPE
		SYNTAX					 RowStatus
		MAX-ACCESS			 read-only
		STATUS					 current
		DESCRIPTION			 " -- "
		::=  { hsdpaSpsSchedEntry  2 }


	hsdpaSpsSchedStateTransWin		 OBJECT-TYPE
		SYNTAX					 Integer32( 4 .. 40 )
		MAX-ACCESS			 read-write
		STATUS					 current
		DESCRIPTION			 " -- "
		::=  { hsdpaSpsSchedEntry  3 }


	hsdpaSpsSchedActivePktTh		 OBJECT-TYPE
		SYNTAX					 Integer32( 2 .. 8 )
		MAX-ACCESS			 read-write
		STATUS					 current
		DESCRIPTION			 " -- "
		::=  { hsdpaSpsSchedEntry  4 }


	hsdpaSpsSchedSilentPktTh		 OBJECT-TYPE
		SYNTAX					 Integer32( 0 .. 2 )
		MAX-ACCESS			 read-write
		STATUS					 current
		DESCRIPTION			 " -- "
		::=  { hsdpaSpsSchedEntry  5 }


	hsdpaSpsSchedDynamicSDThFactor		 OBJECT-TYPE
		SYNTAX					 Integer32( 1 .. 100 )
		MAX-ACCESS			 read-write
		STATUS					 current
		DESCRIPTION			 " -- "
		::=  { hsdpaSpsSchedEntry  6 }


	hsdpaSpsSchedCPCAlphaIndex		 OBJECT-TYPE
		SYNTAX					 Integer32( 0 .. 2 )
		MAX-ACCESS			 read-write
		STATUS					 current
		DESCRIPTION			 " -- "
		::=  { hsdpaSpsSchedEntry  7 }


	hsdpaSpsSchedResrcBlkTsCfgIndex		 OBJECT-TYPE
		SYNTAX					 Integer32( 0 .. 1 )
		MAX-ACCESS			 read-write
		STATUS					 current
		DESCRIPTION			 " -- "
		::=  { hsdpaSpsSchedEntry  8 }


	hsdpaSpsSchedResrcBlkCfgIndex		 OBJECT-TYPE
		SYNTAX					 Integer32( 0 .. 3 )
		MAX-ACCESS			 read-write
		STATUS					 current
		DESCRIPTION			 " -- "
		::=  { hsdpaSpsSchedEntry  9 }


	hsdpaEFACHSchedNode		 OBJECT IDENTIFIER
		::=  { hsdpaAlgorithmNode  7 }


	hsdpaEFACHSchedTable		 OBJECT-TYPE
		SYNTAX					 SEQUENCE  OF	 HsdpaEFACHSchedEntry
		MAX-ACCESS			 not-accessible
		STATUS					 current
		DESCRIPTION			 " -- "
		::=  { hsdpaEFACHSchedNode  1 }


	hsdpaEFACHSchedEntry		 OBJECT-TYPE
		SYNTAX					 HsdpaEFACHSchedEntry
		MAX-ACCESS			 not-accessible
		STATUS					 current
		DESCRIPTION			 " -- "
		INDEX						{ hsdpaEFACHSchedLcId }
		::=  { hsdpaEFACHSchedTable  1 }


	HsdpaEFACHSchedEntry		 ::=  SEQUENCE {
		hsdpaEFACHSchedLcId					Integer32,
		hsdpaEFACHSchedRowStatus					RowStatus,
		hsdpaEFACHSchedMaxTxNum					Integer32,
		hsdpaEFACHSchedMF					INTEGER,
		hsdpaEFACHSchedCodeRate					Integer32,
		hsdpaEFACHSchedOrderSendNum					Integer32
		}


	hsdpaEFACHSchedLcId		 OBJECT-TYPE
		SYNTAX					 Integer32( 0 .. 11 )
		MAX-ACCESS			 not-accessible
		STATUS					 current
		DESCRIPTION			 " -- "
		::=  { hsdpaEFACHSchedEntry  1 }


	hsdpaEFACHSchedRowStatus		 OBJECT-TYPE
		SYNTAX					 RowStatus
		MAX-ACCESS			 read-only
		STATUS					 current
		DESCRIPTION			 " -- "
		::=  { hsdpaEFACHSchedEntry  2 }


	hsdpaEFACHSchedMaxTxNum		 OBJECT-TYPE
		SYNTAX					 Integer32( 1 .. 5 )
		MAX-ACCESS			 read-write
		STATUS					 current
		DESCRIPTION			 " -- "
		::=  { hsdpaEFACHSchedEntry  3 }


	hsdpaEFACHSchedMF		 OBJECT-TYPE
		SYNTAX					 INTEGER{ qpsk(0),m16QAM(1),m64QAM(2)  }
		MAX-ACCESS			 read-write
		STATUS					 current
		DESCRIPTION			 " -- "
		::=  { hsdpaEFACHSchedEntry  4 }


	hsdpaEFACHSchedCodeRate		 OBJECT-TYPE
		SYNTAX					 Integer32( 2 .. 8 )
		MAX-ACCESS			 read-write
		STATUS					 current
		DESCRIPTION			 " -- "
		::=  { hsdpaEFACHSchedEntry  5 }


	hsdpaEFACHSchedOrderSendNum		 OBJECT-TYPE
		SYNTAX					 Integer32( 1 .. 6 )
		MAX-ACCESS			 read-write
		STATUS					 current
		DESCRIPTION			 " -- "
		::=  { hsdpaEFACHSchedEntry  6 }


	hsdpaCongestCtrlNode		 OBJECT IDENTIFIER
		::=  { hsdpaAlgorithmNode  8 }


	hsdpaCongestCtrlTable		 OBJECT-TYPE
		SYNTAX					 SEQUENCE  OF	 HsdpaCongestCtrlEntry
		MAX-ACCESS			 not-accessible
		STATUS					 current
		DESCRIPTION			 " -- "
		::=  { hsdpaCongestCtrlNode  1 }


	hsdpaCongestCtrlEntry		 OBJECT-TYPE
		SYNTAX					 HsdpaCongestCtrlEntry
		MAX-ACCESS			 not-accessible
		STATUS					 current
		DESCRIPTION			 " -- "
		INDEX						{ hsdpaCongestCtrlLcId }
		::=  { hsdpaCongestCtrlTable  1 }


	HsdpaCongestCtrlEntry		 ::=  SEQUENCE {
		hsdpaCongestCtrlLcId					Integer32,
		hsdpaCongestCtrlRowStatus					RowStatus,
		hsdpaCongestCtrlDecreasePara					Integer32,
		hsdpaCongestCtrlIncreasePara					Integer32,
		hsdpaCongestCtrlDetTimerTh					Integer32,
		hsdpaCongestCtrlFSNDetTimerTh					Integer32,
		hsdpaCongestCtrlAvoidTimerTh					Integer32,
		hsdpaCongestCtrlRestoreTimerTh					Integer32,
		hsdpaCongestCtrlRestoreCounterTh					Integer32,
		hsdpaCongestCtrlCongestTh					Integer32,
		hsdpaCongestCtrlConFrameNum					Integer32,
		hsdpaCongestCtrlCongAlarmTh					Unsigned32,
		hsdpaCongestCtrlDeCongAlarmTh					Unsigned32
		}


	hsdpaCongestCtrlLcId		 OBJECT-TYPE
		SYNTAX					 Integer32( 0 .. 11 )
		MAX-ACCESS			 not-accessible
		STATUS					 current
		DESCRIPTION			 " -- "
		::=  { hsdpaCongestCtrlEntry  1 }


	hsdpaCongestCtrlRowStatus		 OBJECT-TYPE
		SYNTAX					 RowStatus
		MAX-ACCESS			 read-only
		STATUS					 current
		DESCRIPTION			 " -- "
		::=  { hsdpaCongestCtrlEntry  2 }


	hsdpaCongestCtrlDecreasePara		 OBJECT-TYPE
		SYNTAX					 Integer32( 2 .. 8 )
		MAX-ACCESS			 read-write
		STATUS					 current
		DESCRIPTION			 " -- "
		::=  { hsdpaCongestCtrlEntry  3 }


	hsdpaCongestCtrlIncreasePara		 OBJECT-TYPE
		SYNTAX					 Integer32( 2 .. 16 )
		MAX-ACCESS			 read-write
		STATUS					 current
		DESCRIPTION			 " -- "
		::=  { hsdpaCongestCtrlEntry  4 }


	hsdpaCongestCtrlDetTimerTh		 OBJECT-TYPE
		SYNTAX					 Integer32( 3 .. 40 )
		MAX-ACCESS			 read-write
		STATUS					 current
		DESCRIPTION			 " -- "
		::=  { hsdpaCongestCtrlEntry  5 }


	hsdpaCongestCtrlFSNDetTimerTh		 OBJECT-TYPE
		SYNTAX					 Integer32( 3 .. 20 )
		MAX-ACCESS			 read-write
		STATUS					 current
		DESCRIPTION			 " -- "
		::=  { hsdpaCongestCtrlEntry  6 }


	hsdpaCongestCtrlAvoidTimerTh		 OBJECT-TYPE
		SYNTAX					 Integer32( 20 .. 100 )
		MAX-ACCESS			 read-write
		STATUS					 current
		DESCRIPTION			 " -- "
		::=  { hsdpaCongestCtrlEntry  7 }


	hsdpaCongestCtrlRestoreTimerTh		 OBJECT-TYPE
		SYNTAX					 Integer32( 8 .. 15 )
		MAX-ACCESS			 read-write
		STATUS					 current
		DESCRIPTION			 " -- "
		::=  { hsdpaCongestCtrlEntry  8 }


	hsdpaCongestCtrlRestoreCounterTh		 OBJECT-TYPE
		SYNTAX					 Integer32( 1 .. 8 )
		MAX-ACCESS			 read-write
		STATUS					 current
		DESCRIPTION			 " -- "
		::=  { hsdpaCongestCtrlEntry  9 }


	hsdpaCongestCtrlCongestTh		 OBJECT-TYPE
		SYNTAX					 Integer32( 1 .. 8 )
		MAX-ACCESS			 read-write
		STATUS					 current
		DESCRIPTION			 " -- "
		::=  { hsdpaCongestCtrlEntry  10 }


	hsdpaCongestCtrlConFrameNum		 OBJECT-TYPE
		SYNTAX					 Integer32( 5 .. 20 )
		MAX-ACCESS			 read-write
		STATUS					 current
		DESCRIPTION			 " -- "
		::=  { hsdpaCongestCtrlEntry  11 }


	hsdpaCongestCtrlCongAlarmTh		 OBJECT-TYPE
		SYNTAX					 Unsigned32( 6000 .. 90000 )
		MAX-ACCESS			 read-write
		STATUS					 current
		DESCRIPTION			 " -- "
		::=  { hsdpaCongestCtrlEntry  12 }


	hsdpaCongestCtrlDeCongAlarmTh		 OBJECT-TYPE
		SYNTAX					 Unsigned32( 6000 .. 90000 )
		MAX-ACCESS			 read-write
		STATUS					 current
		DESCRIPTION			 " -- "
		::=  { hsdpaCongestCtrlEntry  13 }


	hsdpaCellSelectNode		 OBJECT IDENTIFIER
		::=  { hsdpaAlgorithmNode  9 }


	hsdpaCellSelectTable		 OBJECT-TYPE
		SYNTAX					 SEQUENCE  OF	 HsdpaCellSelectEntry
		MAX-ACCESS			 not-accessible
		STATUS					 current
		DESCRIPTION			 " -- "
		::=  { hsdpaCellSelectNode  1 }


	hsdpaCellSelectEntry		 OBJECT-TYPE
		SYNTAX					 HsdpaCellSelectEntry
		MAX-ACCESS			 not-accessible
		STATUS					 current
		DESCRIPTION			 " -- "
		INDEX						{ hsdpaCellSelectLcId }
		::=  { hsdpaCellSelectTable  1 }


	HsdpaCellSelectEntry		 ::=  SEQUENCE {
		hsdpaCellSelectLcId					Integer32,
		hsdpaCellSelectRowStatus					RowStatus,
		hsdpaCellSelectNotSchedTime					Integer32
		}


	hsdpaCellSelectLcId		 OBJECT-TYPE
		SYNTAX					 Integer32( 0 .. 11 )
		MAX-ACCESS			 not-accessible
		STATUS					 current
		DESCRIPTION			 " -- "
		::=  { hsdpaCellSelectEntry  1 }


	hsdpaCellSelectRowStatus		 OBJECT-TYPE
		SYNTAX					 RowStatus
		MAX-ACCESS			 read-only
		STATUS					 current
		DESCRIPTION			 " -- "
		::=  { hsdpaCellSelectEntry  2 }


	hsdpaCellSelectNotSchedTime		 OBJECT-TYPE
		SYNTAX					 Integer32( 1 .. 65535 )
		MAX-ACCESS			 read-write
		STATUS					 current
		DESCRIPTION			 " -- "
		::=  { hsdpaCellSelectEntry  3 }


	hsdpaCommSchedNode		 OBJECT IDENTIFIER
		::=  { hsdpaAlgorithmNode  10 }


	hsdpaCommSchedTable		 OBJECT-TYPE
		SYNTAX					 SEQUENCE  OF	 HsdpaCommSchedEntry
		MAX-ACCESS			 not-accessible
		STATUS					 current
		DESCRIPTION			 " -- "
		::=  { hsdpaCommSchedNode  1 }


	hsdpaCommSchedEntry		 OBJECT-TYPE
		SYNTAX					 HsdpaCommSchedEntry
		MAX-ACCESS			 not-accessible
		STATUS					 current
		DESCRIPTION			 " -- "
		INDEX						{ hsdpaCommSchedLcId }
		::=  { hsdpaCommSchedTable  1 }


	HsdpaCommSchedEntry		 ::=  SEQUENCE {
		hsdpaCommSchedLcId					Integer32,
		hsdpaCommSchedRowStatus					RowStatus,
		hsdpaCommSchedDpchPreemptPolicy					INTEGER
		}


	hsdpaCommSchedLcId		 OBJECT-TYPE
		SYNTAX					 Integer32( 0 .. 11 )
		MAX-ACCESS			 not-accessible
		STATUS					 current
		DESCRIPTION			 " -- "
		::=  { hsdpaCommSchedEntry  1 }


	hsdpaCommSchedRowStatus		 OBJECT-TYPE
		SYNTAX					 RowStatus
		MAX-ACCESS			 read-only
		STATUS					 current
		DESCRIPTION			 " -- "
		::=  { hsdpaCommSchedEntry  2 }


	hsdpaCommSchedDpchPreemptPolicy		 OBJECT-TYPE
		SYNTAX					 INTEGER{ vru(0),timeSlot(1)  }
		MAX-ACCESS			 read-write
		STATUS					 current
		DESCRIPTION			 " -- "
		::=  { hsdpaCommSchedEntry  3 }


	hsdpaTsRandomNode		 OBJECT IDENTIFIER
		::=  { hsdpaAlgorithmNode  11 }


	hsdpaTsRandomTable		 OBJECT-TYPE
		SYNTAX					 SEQUENCE  OF	 HsdpaTsRandomEntry
		MAX-ACCESS			 not-accessible
		STATUS					 current
		DESCRIPTION			 " -- "
		::=  { hsdpaTsRandomNode  1 }


	hsdpaTsRandomEntry		 OBJECT-TYPE
		SYNTAX					 HsdpaTsRandomEntry
		MAX-ACCESS			 not-accessible
		STATUS					 current
		DESCRIPTION			 " -- "
		INDEX						{ hsdpaTsRandomLcId }
		::=  { hsdpaTsRandomTable  1 }


	HsdpaTsRandomEntry		 ::=  SEQUENCE {
		hsdpaTsRandomLcId					Integer32,
		hsdpaTsRandomRowStatus					RowStatus,
		hsdpaTsRandomSwitch					INTEGER
		}


	hsdpaTsRandomLcId		 OBJECT-TYPE
		SYNTAX					 Integer32( 0 .. 11 )
		MAX-ACCESS			 not-accessible
		STATUS					 current
		DESCRIPTION			 " -- "
		::=  { hsdpaTsRandomEntry  1 }


	hsdpaTsRandomRowStatus		 OBJECT-TYPE
		SYNTAX					 RowStatus
		MAX-ACCESS			 read-only
		STATUS					 current
		DESCRIPTION			 " -- "
		::=  { hsdpaTsRandomEntry  2 }


	hsdpaTsRandomSwitch		 OBJECT-TYPE
		SYNTAX					 INTEGER{ off(0),on(1)  }
		MAX-ACCESS			 read-write
		STATUS					 current
		DESCRIPTION			 " -- "
		::=  { hsdpaTsRandomEntry  3 }


	hsdpaHarqNode		 OBJECT IDENTIFIER
		::=  { machs  2 }


	hsdpaHarqTable		 OBJECT-TYPE
		SYNTAX					 SEQUENCE  OF	 HsdpaHarqEntry
		MAX-ACCESS			 not-accessible
		STATUS					 current
		DESCRIPTION			 " -- "
		::=  { hsdpaHarqNode  1 }


	hsdpaHarqEntry		 OBJECT-TYPE
		SYNTAX					 HsdpaHarqEntry
		MAX-ACCESS			 not-accessible
		STATUS					 current
		DESCRIPTION			 " -- "
		INDEX						{ hsdpaHarqLcId }
		::=  { hsdpaHarqTable  1 }


	HsdpaHarqEntry		 ::=  SEQUENCE {
		hsdpaHarqLcId					Integer32,
		hsdpaHarqRowStatus					RowStatus,
		hsdpaHarqMaxTxNum					Unsigned32,
		hsdpaHarqRvQpsk1					Unsigned32,
		hsdpaHarqRv16Qam1					Unsigned32,
		hsdpaHarqRvQpsk2					Unsigned32,
		hsdpaHarqRv16Qam2					Unsigned32,
		hsdpaHarqRvQpsk3					Unsigned32,
		hsdpaHarqRv16Qam3					Unsigned32,
		hsdpaHarqRvQpsk4					Unsigned32,
		hsdpaHarqRv16Qam4					Unsigned32,
		hsdpaHarqRvQpsk5					Unsigned32,
		hsdpaHarqRv16Qam5					Unsigned32,
		hsdpaHarqRvQpsk6					Unsigned32,
		hsdpaHarqRv16Qam6					Unsigned32,
		hsdpaHarqRvQpsk7					Unsigned32,
		hsdpaHarqRv16Qam7					Unsigned32,
		hsdpaHarqRvQpsk8					Unsigned32,
		hsdpaHarqRv16Qam8					Unsigned32,
		hsdpaHarqRv64Qam1					Unsigned32,
		hsdpaHarqRvQpsk1New					Unsigned32,
		hsdpaHarqRv16Qam1New					Unsigned32,
		hsdpaHarqRv64Qam2					Unsigned32,
		hsdpaHarqRvQpsk2New					Unsigned32,
		hsdpaHarqRv16Qam2New					Unsigned32,
		hsdpaHarqRv64Qam3					Unsigned32,
		hsdpaHarqRvQpsk3New					Unsigned32,
		hsdpaHarqRv16Qam3New					Unsigned32,
		hsdpaHarqRv64Qam4					Unsigned32,
		hsdpaHarqRvQpsk4New					Unsigned32,
		hsdpaHarqRv16Qam4New					Unsigned32,
		hsdpaHarqRv64Qam5					Unsigned32,
		hsdpaHarqRvQpsk5New					Unsigned32,
		hsdpaHarqRv16Qam5New					Unsigned32,
		hsdpaHarqRv64Qam6					Unsigned32,
		hsdpaHarqRvQpsk6New					Unsigned32,
		hsdpaHarqRv16Qam6New					Unsigned32,
		hsdpaHarqRv64Qam7					Unsigned32,
		hsdpaHarqRvQpsk7New					Unsigned32,
		hsdpaHarqRv16Qam7New					Unsigned32,
		hsdpaHarqRv64Qam8					Unsigned32,
		hsdpaHarqRvQpsk8New					Unsigned32,
		hsdpaHarqRv16Qam8New					Unsigned32
		}


	hsdpaHarqLcId		 OBJECT-TYPE
		SYNTAX					 Integer32( 0 .. 11 )
		MAX-ACCESS			 not-accessible
		STATUS					 current
		DESCRIPTION			 " -- "
		::=  { hsdpaHarqEntry  1 }


	hsdpaHarqRowStatus		 OBJECT-TYPE
		SYNTAX					 RowStatus
		MAX-ACCESS			 read-only
		STATUS					 current
		DESCRIPTION			 " -- "
		::=  { hsdpaHarqEntry  2 }


	hsdpaHarqMaxTxNum		 OBJECT-TYPE
		SYNTAX					 Unsigned32( 1 .. 8 )
		MAX-ACCESS			 read-write
		STATUS					 current
		DESCRIPTION			 " -- "
		::=  { hsdpaHarqEntry  3 }


	hsdpaHarqRvQpsk1		 OBJECT-TYPE
		SYNTAX					 Unsigned32( 0 .. 7 )
		MAX-ACCESS			 read-write
		STATUS					 current
		DESCRIPTION			 " -- "
		::=  { hsdpaHarqEntry  4 }


	hsdpaHarqRv16Qam1		 OBJECT-TYPE
		SYNTAX					 Unsigned32( 0 .. 7 )
		MAX-ACCESS			 read-write
		STATUS					 current
		DESCRIPTION			 " -- "
		::=  { hsdpaHarqEntry  5 }


	hsdpaHarqRvQpsk2		 OBJECT-TYPE
		SYNTAX					 Unsigned32( 0 .. 7 )
		MAX-ACCESS			 read-write
		STATUS					 current
		DESCRIPTION			 " -- "
		::=  { hsdpaHarqEntry  6 }


	hsdpaHarqRv16Qam2		 OBJECT-TYPE
		SYNTAX					 Unsigned32( 0 .. 7 )
		MAX-ACCESS			 read-write
		STATUS					 current
		DESCRIPTION			 " -- "
		::=  { hsdpaHarqEntry  7 }


	hsdpaHarqRvQpsk3		 OBJECT-TYPE
		SYNTAX					 Unsigned32( 0 .. 7 )
		MAX-ACCESS			 read-write
		STATUS					 current
		DESCRIPTION			 " -- "
		::=  { hsdpaHarqEntry  8 }


	hsdpaHarqRv16Qam3		 OBJECT-TYPE
		SYNTAX					 Unsigned32( 0 .. 7 )
		MAX-ACCESS			 read-write
		STATUS					 current
		DESCRIPTION			 " -- "
		::=  { hsdpaHarqEntry  9 }


	hsdpaHarqRvQpsk4		 OBJECT-TYPE
		SYNTAX					 Unsigned32( 0 .. 7 )
		MAX-ACCESS			 read-write
		STATUS					 current
		DESCRIPTION			 " -- "
		::=  { hsdpaHarqEntry  10 }


	hsdpaHarqRv16Qam4		 OBJECT-TYPE
		SYNTAX					 Unsigned32( 0 .. 7 )
		MAX-ACCESS			 read-write
		STATUS					 current
		DESCRIPTION			 " -- "
		::=  { hsdpaHarqEntry  11 }


	hsdpaHarqRvQpsk5		 OBJECT-TYPE
		SYNTAX					 Unsigned32( 0 .. 7 )
		MAX-ACCESS			 read-write
		STATUS					 current
		DESCRIPTION			 " -- "
		::=  { hsdpaHarqEntry  12 }


	hsdpaHarqRv16Qam5		 OBJECT-TYPE
		SYNTAX					 Unsigned32( 0 .. 7 )
		MAX-ACCESS			 read-write
		STATUS					 current
		DESCRIPTION			 " -- "
		::=  { hsdpaHarqEntry  13 }


	hsdpaHarqRvQpsk6		 OBJECT-TYPE
		SYNTAX					 Unsigned32( 0 .. 7 )
		MAX-ACCESS			 read-write
		STATUS					 current
		DESCRIPTION			 " -- "
		::=  { hsdpaHarqEntry  14 }


	hsdpaHarqRv16Qam6		 OBJECT-TYPE
		SYNTAX					 Unsigned32( 0 .. 7 )
		MAX-ACCESS			 read-write
		STATUS					 current
		DESCRIPTION			 " -- "
		::=  { hsdpaHarqEntry  15 }


	hsdpaHarqRvQpsk7		 OBJECT-TYPE
		SYNTAX					 Unsigned32( 0 .. 7 )
		MAX-ACCESS			 read-write
		STATUS					 current
		DESCRIPTION			 " -- "
		::=  { hsdpaHarqEntry  16 }


	hsdpaHarqRv16Qam7		 OBJECT-TYPE
		SYNTAX					 Unsigned32( 0 .. 7 )
		MAX-ACCESS			 read-write
		STATUS					 current
		DESCRIPTION			 " -- "
		::=  { hsdpaHarqEntry  17 }


	hsdpaHarqRvQpsk8		 OBJECT-TYPE
		SYNTAX					 Unsigned32( 0 .. 7 )
		MAX-ACCESS			 read-write
		STATUS					 current
		DESCRIPTION			 " -- "
		::=  { hsdpaHarqEntry  18 }


	hsdpaHarqRv16Qam8		 OBJECT-TYPE
		SYNTAX					 Unsigned32( 0 .. 7 )
		MAX-ACCESS			 read-write
		STATUS					 current
		DESCRIPTION			 " -- "
		::=  { hsdpaHarqEntry  19 }


	hsdpaHarqRv64Qam1		 OBJECT-TYPE
		SYNTAX					 Unsigned32( 0 .. 7 )
		MAX-ACCESS			 read-write
		STATUS					 current
		DESCRIPTION			 " -- "
		::=  { hsdpaHarqEntry  20 }


	hsdpaHarqRvQpsk1New		 OBJECT-TYPE
		SYNTAX					 Unsigned32( 0 .. 3 )
		MAX-ACCESS			 read-write
		STATUS					 current
		DESCRIPTION			 " -- "
		::=  { hsdpaHarqEntry  21 }


	hsdpaHarqRv16Qam1New		 OBJECT-TYPE
		SYNTAX					 Unsigned32( 0 .. 3 )
		MAX-ACCESS			 read-write
		STATUS					 current
		DESCRIPTION			 " -- "
		::=  { hsdpaHarqEntry  22 }


	hsdpaHarqRv64Qam2		 OBJECT-TYPE
		SYNTAX					 Unsigned32( 0 .. 7 )
		MAX-ACCESS			 read-write
		STATUS					 current
		DESCRIPTION			 " -- "
		::=  { hsdpaHarqEntry  23 }


	hsdpaHarqRvQpsk2New		 OBJECT-TYPE
		SYNTAX					 Unsigned32( 0 .. 3 )
		MAX-ACCESS			 read-write
		STATUS					 current
		DESCRIPTION			 " -- "
		::=  { hsdpaHarqEntry  24 }


	hsdpaHarqRv16Qam2New		 OBJECT-TYPE
		SYNTAX					 Unsigned32( 0 .. 3 )
		MAX-ACCESS			 read-write
		STATUS					 current
		DESCRIPTION			 " -- "
		::=  { hsdpaHarqEntry  25 }


	hsdpaHarqRv64Qam3		 OBJECT-TYPE
		SYNTAX					 Unsigned32( 0 .. 7 )
		MAX-ACCESS			 read-write
		STATUS					 current
		DESCRIPTION			 " -- "
		::=  { hsdpaHarqEntry  26 }


	hsdpaHarqRvQpsk3New		 OBJECT-TYPE
		SYNTAX					 Unsigned32( 0 .. 3 )
		MAX-ACCESS			 read-write
		STATUS					 current
		DESCRIPTION			 " -- "
		::=  { hsdpaHarqEntry  27 }


	hsdpaHarqRv16Qam3New		 OBJECT-TYPE
		SYNTAX					 Unsigned32( 0 .. 3 )
		MAX-ACCESS			 read-write
		STATUS					 current
		DESCRIPTION			 " -- "
		::=  { hsdpaHarqEntry  28 }


	hsdpaHarqRv64Qam4		 OBJECT-TYPE
		SYNTAX					 Unsigned32( 0 .. 7 )
		MAX-ACCESS			 read-write
		STATUS					 current
		DESCRIPTION			 " -- "
		::=  { hsdpaHarqEntry  29 }


	hsdpaHarqRvQpsk4New		 OBJECT-TYPE
		SYNTAX					 Unsigned32( 0 .. 3 )
		MAX-ACCESS			 read-write
		STATUS					 current
		DESCRIPTION			 " -- "
		::=  { hsdpaHarqEntry  30 }


	hsdpaHarqRv16Qam4New		 OBJECT-TYPE
		SYNTAX					 Unsigned32( 0 .. 3 )
		MAX-ACCESS			 read-write
		STATUS					 current
		DESCRIPTION			 " -- "
		::=  { hsdpaHarqEntry  31 }


	hsdpaHarqRv64Qam5		 OBJECT-TYPE
		SYNTAX					 Unsigned32( 0 .. 7 )
		MAX-ACCESS			 read-write
		STATUS					 current
		DESCRIPTION			 " -- "
		::=  { hsdpaHarqEntry  32 }


	hsdpaHarqRvQpsk5New		 OBJECT-TYPE
		SYNTAX					 Unsigned32( 0 .. 3 )
		MAX-ACCESS			 read-write
		STATUS					 current
		DESCRIPTION			 " -- "
		::=  { hsdpaHarqEntry  33 }


	hsdpaHarqRv16Qam5New		 OBJECT-TYPE
		SYNTAX					 Unsigned32( 0 .. 3 )
		MAX-ACCESS			 read-write
		STATUS					 current
		DESCRIPTION			 " -- "
		::=  { hsdpaHarqEntry  34 }


	hsdpaHarqRv64Qam6		 OBJECT-TYPE
		SYNTAX					 Unsigned32( 0 .. 7 )
		MAX-ACCESS			 read-write
		STATUS					 current
		DESCRIPTION			 " -- "
		::=  { hsdpaHarqEntry  35 }


	hsdpaHarqRvQpsk6New		 OBJECT-TYPE
		SYNTAX					 Unsigned32( 0 .. 3 )
		MAX-ACCESS			 read-write
		STATUS					 current
		DESCRIPTION			 " -- "
		::=  { hsdpaHarqEntry  36 }


	hsdpaHarqRv16Qam6New		 OBJECT-TYPE
		SYNTAX					 Unsigned32( 0 .. 3 )
		MAX-ACCESS			 read-write
		STATUS					 current
		DESCRIPTION			 " -- "
		::=  { hsdpaHarqEntry  37 }


	hsdpaHarqRv64Qam7		 OBJECT-TYPE
		SYNTAX					 Unsigned32( 0 .. 7 )
		MAX-ACCESS			 read-write
		STATUS					 current
		DESCRIPTION			 " -- "
		::=  { hsdpaHarqEntry  38 }


	hsdpaHarqRvQpsk7New		 OBJECT-TYPE
		SYNTAX					 Unsigned32( 0 .. 3 )
		MAX-ACCESS			 read-write
		STATUS					 current
		DESCRIPTION			 " -- "
		::=  { hsdpaHarqEntry  39 }


	hsdpaHarqRv16Qam7New		 OBJECT-TYPE
		SYNTAX					 Unsigned32( 0 .. 3 )
		MAX-ACCESS			 read-write
		STATUS					 current
		DESCRIPTION			 " -- "
		::=  { hsdpaHarqEntry  40 }


	hsdpaHarqRv64Qam8		 OBJECT-TYPE
		SYNTAX					 Unsigned32( 0 .. 7 )
		MAX-ACCESS			 read-write
		STATUS					 current
		DESCRIPTION			 " -- "
		::=  { hsdpaHarqEntry  41 }


	hsdpaHarqRvQpsk8New		 OBJECT-TYPE
		SYNTAX					 Unsigned32( 0 .. 3 )
		MAX-ACCESS			 read-write
		STATUS					 current
		DESCRIPTION			 " -- "
		::=  { hsdpaHarqEntry  42 }


	hsdpaHarqRv16Qam8New		 OBJECT-TYPE
		SYNTAX					 Unsigned32( 0 .. 3 )
		MAX-ACCESS			 read-write
		STATUS					 current
		DESCRIPTION			 " -- "
		::=  { hsdpaHarqEntry  43 }


	hsupaAlgorithmNode		 OBJECT IDENTIFIER
		::=  { machs  3 }


	hsupaAlgorithmTable		 OBJECT-TYPE
		SYNTAX					 SEQUENCE  OF	 HsupaAlgorithmEntry
		MAX-ACCESS			 not-accessible
		STATUS					 current
		DESCRIPTION			 " -- "
		::=  { hsupaAlgorithmNode  1 }


	hsupaAlgorithmEntry		 OBJECT-TYPE
		SYNTAX					 HsupaAlgorithmEntry
		MAX-ACCESS			 not-accessible
		STATUS					 current
		DESCRIPTION			 " -- "
		INDEX						{ hsupaAlgorithmLcId }
		::=  { hsupaAlgorithmTable  1 }


	HsupaAlgorithmEntry		 ::=  SEQUENCE {
		hsupaAlgorithmLcId					Integer32,
		hsupaAlgorithmRowStatus					RowStatus,
		hsupaSchedAlgorithm					INTEGER,
		huspaMBRCfgSwitch					INTEGER
		}


	hsupaAlgorithmLcId		 OBJECT-TYPE
		SYNTAX					 Integer32( 0 .. 11 )
		MAX-ACCESS			 not-accessible
		STATUS					 current
		DESCRIPTION			 " -- "
		::=  { hsupaAlgorithmEntry  1 }


	hsupaAlgorithmRowStatus		 OBJECT-TYPE
		SYNTAX					 RowStatus
		MAX-ACCESS			 read-only
		STATUS					 current
		DESCRIPTION			 " -- "
		::=  { hsupaAlgorithmEntry  2 }


	hsupaSchedAlgorithm		 OBJECT-TYPE
		SYNTAX					 INTEGER{ pf(0),maxci(1),roundRobin(2),qos(3)  }
		MAX-ACCESS			 read-write
		STATUS					 current
		DESCRIPTION			 " -- "
		::=  { hsupaAlgorithmEntry  3 }


	huspaMBRCfgSwitch		 OBJECT-TYPE
		SYNTAX					 INTEGER{ off(0),on(1)  }
		MAX-ACCESS			 read-write
		STATUS					 current
		DESCRIPTION			 " -- "
		::=  { hsupaAlgorithmEntry  4 }


	hsupaSchedAlgorithmNode		 OBJECT IDENTIFIER
		::=  { hsupaAlgorithmNode  2 }


	hsupaPFTable		 OBJECT-TYPE
		SYNTAX					 SEQUENCE  OF	 HsupaPFEntry
		MAX-ACCESS			 not-accessible
		STATUS					 current
		DESCRIPTION			 " -- "
		::=  { hsupaSchedAlgorithmNode  1 }


	hsupaPFEntry		 OBJECT-TYPE
		SYNTAX					 HsupaPFEntry
		MAX-ACCESS			 not-accessible
		STATUS					 current
		DESCRIPTION			 " -- "
		INDEX						{ hsupaPFLcId }
		::=  { hsupaPFTable  1 }


	HsupaPFEntry		 ::=  SEQUENCE {
		hsupaPFLcId					Integer32,
		hsupaPFRowStatus					RowStatus,
		hsupaPFTcSlideWindowSize					Integer32,
		hsupaPFInitPF					Integer32,
		hsupaPFA					Integer32
		}


	hsupaPFLcId		 OBJECT-TYPE
		SYNTAX					 Integer32( 0 .. 11 )
		MAX-ACCESS			 not-accessible
		STATUS					 current
		DESCRIPTION			 " -- "
		::=  { hsupaPFEntry  1 }


	hsupaPFRowStatus		 OBJECT-TYPE
		SYNTAX					 RowStatus
		MAX-ACCESS			 read-only
		STATUS					 current
		DESCRIPTION			 " -- "
		::=  { hsupaPFEntry  2 }


	hsupaPFTcSlideWindowSize		 OBJECT-TYPE
		SYNTAX					 Integer32( 1 .. 65535 )
		MAX-ACCESS			 read-write
		STATUS					 current
		DESCRIPTION			 " -- "
		::=  { hsupaPFEntry  3 }


	hsupaPFInitPF		 OBJECT-TYPE
		SYNTAX					 Integer32( 1 .. 65535 )
		MAX-ACCESS			 read-write
		STATUS					 current
		DESCRIPTION			 " -- "
		::=  { hsupaPFEntry  4 }


	hsupaPFA		 OBJECT-TYPE
		SYNTAX					 Integer32( 0 .. 3 )
		MAX-ACCESS			 read-write
		STATUS					 current
		DESCRIPTION			 " -- "
		::=  { hsupaPFEntry  5 }


	hsupaMAXCITable		 OBJECT-TYPE
		SYNTAX					 SEQUENCE  OF	 HsupaMAXCIEntry
		MAX-ACCESS			 not-accessible
		STATUS					 current
		DESCRIPTION			 " -- "
		::=  { hsupaSchedAlgorithmNode  2 }


	hsupaMAXCIEntry		 OBJECT-TYPE
		SYNTAX					 HsupaMAXCIEntry
		MAX-ACCESS			 not-accessible
		STATUS					 current
		DESCRIPTION			 " -- "
		INDEX						{ hsupaMaxCILcId }
		::=  { hsupaMAXCITable  1 }


	HsupaMAXCIEntry		 ::=  SEQUENCE {
		hsupaMaxCILcId					Integer32,
		hsupaMaxCIRowStatus					RowStatus,
		hsupaMaxCITmR					Integer32
		}


	hsupaMaxCILcId		 OBJECT-TYPE
		SYNTAX					 Integer32( 0 .. 11 )
		MAX-ACCESS			 not-accessible
		STATUS					 current
		DESCRIPTION			 " -- "
		::=  { hsupaMAXCIEntry  1 }


	hsupaMaxCIRowStatus		 OBJECT-TYPE
		SYNTAX					 RowStatus
		MAX-ACCESS			 read-only
		STATUS					 current
		DESCRIPTION			 " -- "
		::=  { hsupaMAXCIEntry  2 }


	hsupaMaxCITmR		 OBJECT-TYPE
		SYNTAX					 Integer32( 1 .. 65535 )
		MAX-ACCESS			 read-write
		STATUS					 current
		DESCRIPTION			 " -- "
		::=  { hsupaMAXCIEntry  3 }


	hsupaQosTable		 OBJECT-TYPE
		SYNTAX					 SEQUENCE  OF	 HsupaQosEntry
		MAX-ACCESS			 not-accessible
		STATUS					 current
		DESCRIPTION			 " -- "
		::=  { hsupaSchedAlgorithmNode  3 }


	hsupaQosEntry		 OBJECT-TYPE
		SYNTAX					 HsupaQosEntry
		MAX-ACCESS			 not-accessible
		STATUS					 current
		DESCRIPTION			 " -- "
		INDEX						{ hsupaQosLcId }
		::=  { hsupaQosTable  1 }


	HsupaQosEntry		 ::=  SEQUENCE {
		hsupaQosLcId					Integer32,
		hsupaQosRowStatus					RowStatus,
		hsupaQosGamaBufferA					Integer32,
		hsupaQosGamaMaxK					Integer32,
		hsupaQosGamaMin					Unsigned32,
		hsupaQosSDLMin					Unsigned32,
		hsupaQosSDLMax					Unsigned32,
		hsupaQosMaxReTxThreshold					Integer32,
		hsupaQosCSPIDivPointFirst					Integer32,
		hsupaQosCSPIDivPointSecond					Integer32,
		hsupaQosNewAccSetBThreshold					Integer32,
		hsupaQosCongWaitTime					Integer32,
		hsupaQosCongJudgeThreshold					Integer32,
		hsupaQosCRFactor					Integer32,
		hsupaQosPFA					Integer32,
		hsupaQosQueWeightA					Integer32,
		hsupaQosTcSlideWinSize					Integer32,
		hsupaQosInitPF					Integer32,
		hsupaQosQueWeightXBitmap					Integer32
		}


	hsupaQosLcId		 OBJECT-TYPE
		SYNTAX					 Integer32( 0 .. 11 )
		MAX-ACCESS			 not-accessible
		STATUS					 current
		DESCRIPTION			 " -- "
		::=  { hsupaQosEntry  1 }


	hsupaQosRowStatus		 OBJECT-TYPE
		SYNTAX					 RowStatus
		MAX-ACCESS			 read-only
		STATUS					 current
		DESCRIPTION			 " -- "
		::=  { hsupaQosEntry  2 }


	hsupaQosGamaBufferA		 OBJECT-TYPE
		SYNTAX					 Integer32( 1 .. 100 )
		MAX-ACCESS			 read-write
		STATUS					 current
		DESCRIPTION			 " -- "
		::=  { hsupaQosEntry  3 }


	hsupaQosGamaMaxK		 OBJECT-TYPE
		SYNTAX					 Integer32( 1 .. 1000 )
		MAX-ACCESS			 read-write
		STATUS					 current
		DESCRIPTION			 " -- "
		::=  { hsupaQosEntry  4 }


	hsupaQosGamaMin		 OBJECT-TYPE
		SYNTAX					 Unsigned32( 1 .. 100 )
		MAX-ACCESS			 read-write
		STATUS					 current
		DESCRIPTION			 " -- "
		::=  { hsupaQosEntry  5 }


	hsupaQosSDLMin		 OBJECT-TYPE
		SYNTAX					 Unsigned32( 1 .. 100 )
		MAX-ACCESS			 read-write
		STATUS					 current
		DESCRIPTION			 " -- "
		::=  { hsupaQosEntry  6 }


	hsupaQosSDLMax		 OBJECT-TYPE
		SYNTAX					 Unsigned32( 100 .. 33000 )
		MAX-ACCESS			 read-write
		STATUS					 current
		DESCRIPTION			 " -- "
		::=  { hsupaQosEntry  7 }


	hsupaQosMaxReTxThreshold		 OBJECT-TYPE
		SYNTAX					 Integer32( 0 .. 600 )
		MAX-ACCESS			 read-write
		STATUS					 current
		DESCRIPTION			 " -- "
		::=  { hsupaQosEntry  8 }


	hsupaQosCSPIDivPointFirst		 OBJECT-TYPE
		SYNTAX					 Integer32( 0 .. 15 )
		MAX-ACCESS			 read-write
		STATUS					 current
		DESCRIPTION			 " -- "
		::=  { hsupaQosEntry  9 }


	hsupaQosCSPIDivPointSecond		 OBJECT-TYPE
		SYNTAX					 Integer32( 0 .. 15 )
		MAX-ACCESS			 read-write
		STATUS					 current
		DESCRIPTION			 " -- "
		::=  { hsupaQosEntry  10 }


	hsupaQosNewAccSetBThreshold		 OBJECT-TYPE
		SYNTAX					 Integer32( 5 .. 200 )
		MAX-ACCESS			 read-write
		STATUS					 current
		DESCRIPTION			 " -- "
		::=  { hsupaQosEntry  11 }


	hsupaQosCongWaitTime		 OBJECT-TYPE
		SYNTAX					 Integer32( 5 .. 200 )
		MAX-ACCESS			 read-write
		STATUS					 current
		DESCRIPTION			 " -- "
		::=  { hsupaQosEntry  12 }


	hsupaQosCongJudgeThreshold		 OBJECT-TYPE
		SYNTAX					 Integer32( 5 .. 200 )
		MAX-ACCESS			 read-write
		STATUS					 current
		DESCRIPTION			 " -- "
		::=  { hsupaQosEntry  13 }


	hsupaQosCRFactor		 OBJECT-TYPE
		SYNTAX					 Integer32( 1 .. 64 )
		MAX-ACCESS			 read-write
		STATUS					 current
		DESCRIPTION			 " -- "
		::=  { hsupaQosEntry  14 }


	hsupaQosPFA		 OBJECT-TYPE
		SYNTAX					 Integer32( 0 .. 3 )
		MAX-ACCESS			 read-write
		STATUS					 current
		DESCRIPTION			 " -- "
		::=  { hsupaQosEntry  15 }


	hsupaQosQueWeightA		 OBJECT-TYPE
		SYNTAX					 Integer32( 10 .. 40 )
		MAX-ACCESS			 read-write
		STATUS					 current
		DESCRIPTION			 " -- "
		::=  { hsupaQosEntry  16 }


	hsupaQosTcSlideWinSize		 OBJECT-TYPE
		SYNTAX					 Integer32( 1 .. 65535 )
		MAX-ACCESS			 read-write
		STATUS					 current
		DESCRIPTION			 " -- "
		::=  { hsupaQosEntry  17 }


	hsupaQosInitPF		 OBJECT-TYPE
		SYNTAX					 Integer32( 1 .. 65535 )
		MAX-ACCESS			 read-write
		STATUS					 current
		DESCRIPTION			 " -- "
		::=  { hsupaQosEntry  18 }


	hsupaQosQueWeightXBitmap		 OBJECT-TYPE
		SYNTAX					 Integer32( 0 .. 65535 )
		MAX-ACCESS			 read-write
		STATUS					 current
		DESCRIPTION			 " -- "
		::=  { hsupaQosEntry  19 }


	hsupaTfrcAlgorithmNode		 OBJECT IDENTIFIER
		::=  { hsupaAlgorithmNode  3 }


	hsupaTfrcAlgorithmTable		 OBJECT-TYPE
		SYNTAX					 SEQUENCE  OF	 HsupaTfrcAlgorithmEntry
		MAX-ACCESS			 not-accessible
		STATUS					 current
		DESCRIPTION			 " -- "
		::=  { hsupaTfrcAlgorithmNode  1 }


	hsupaTfrcAlgorithmEntry		 OBJECT-TYPE
		SYNTAX					 HsupaTfrcAlgorithmEntry
		MAX-ACCESS			 not-accessible
		STATUS					 current
		DESCRIPTION			 " -- "
		INDEX						{ hsupaTfrcLcId }
		::=  { hsupaTfrcAlgorithmTable  1 }


	HsupaTfrcAlgorithmEntry		 ::=  SEQUENCE {
		hsupaTfrcLcId					Integer32,
		hsupaTfrcRowStatus					RowStatus,
		hsupaTfrcTfrcMode					INTEGER,
		hsupaTfrcGranularity					INTEGER,
		hsupaTfrcTpcModifySwitch					INTEGER,
		hsupaTfrcTpcGap					Integer32,
		hsupaTfrcTpcThreshold					Integer32,
		hsupaTfrcTpcReceiveSwitch					INTEGER,
		hsupaTfrcTpcPreTTINum					Integer32,
		hsupaTfrcPwCtrlType					INTEGER,
		hsupaTfrcNonSdPcDelta					Integer32,
		hsupaTfrcDpchPcDelta					Integer32,
		hsupaTfrcNonSdInitSnplIndex					Integer32,
		hsupaTfrcOlpcSwitch					INTEGER,
		hsupaTfrcPuchFMFactor					Integer32,
		hsupaTfrcDpchFMFactor					Integer32,
		hsupaTfrcCrriAllocMode					INTEGER,
		hsupaTfrcCtrlChSdmaDegree					INTEGER,
		hsupaTfrcFastPuchFMFactor					Integer32,
		hsupaTfrcDeltaSich					Integer32
		}


	hsupaTfrcLcId		 OBJECT-TYPE
		SYNTAX					 Integer32( 0 .. 11 )
		MAX-ACCESS			 not-accessible
		STATUS					 current
		DESCRIPTION			 " -- "
		::=  { hsupaTfrcAlgorithmEntry  1 }


	hsupaTfrcRowStatus		 OBJECT-TYPE
		SYNTAX					 RowStatus
		MAX-ACCESS			 read-only
		STATUS					 current
		DESCRIPTION			 " -- "
		::=  { hsupaTfrcAlgorithmEntry  2 }


	hsupaTfrcTfrcMode		 OBJECT-TYPE
		SYNTAX					 INTEGER{ pureTd(0),pureCd(1),tdcd(2)  }
		MAX-ACCESS			 read-write
		STATUS					 current
		DESCRIPTION			 " -- "
		::=  { hsupaTfrcAlgorithmEntry  3 }


	hsupaTfrcGranularity		 OBJECT-TYPE
		SYNTAX					 INTEGER{ val1(1),val2(2),val4(4),val8(8),val16(16)  }
		MAX-ACCESS			 read-write
		STATUS					 current
		DESCRIPTION			 " -- "
		::=  { hsupaTfrcAlgorithmEntry  4 }


	hsupaTfrcTpcModifySwitch		 OBJECT-TYPE
		SYNTAX					 INTEGER{ off(0),on(1)  }
		MAX-ACCESS			 read-write
		STATUS					 current
		DESCRIPTION			 " -- "
		::=  { hsupaTfrcAlgorithmEntry  5 }


	hsupaTfrcTpcGap		 OBJECT-TYPE
		SYNTAX					 Integer32( 1 .. 255 )
		MAX-ACCESS			 read-write
		STATUS					 current
		DESCRIPTION			 " -- "
		::=  { hsupaTfrcAlgorithmEntry  6 }


	hsupaTfrcTpcThreshold		 OBJECT-TYPE
		SYNTAX					 Integer32( 0 .. 5 )
		MAX-ACCESS			 read-write
		STATUS					 current
		DESCRIPTION			 " -- "
		::=  { hsupaTfrcAlgorithmEntry  7 }


	hsupaTfrcTpcReceiveSwitch		 OBJECT-TYPE
		SYNTAX					 INTEGER{ off(0),on(1)  }
		MAX-ACCESS			 read-write
		STATUS					 current
		DESCRIPTION			 " -- "
		::=  { hsupaTfrcAlgorithmEntry  8 }


	hsupaTfrcTpcPreTTINum		 OBJECT-TYPE
		SYNTAX					 Integer32( 0 .. 3 )
		MAX-ACCESS			 read-write
		STATUS					 current
		DESCRIPTION			 " -- "
		::=  { hsupaTfrcAlgorithmEntry  9 }


	hsupaTfrcPwCtrlType		 OBJECT-TYPE
		SYNTAX					 INTEGER{ rotpebase(0),uph(1),iotpebase(2),rotsir(3),iotsir(4)  }
		MAX-ACCESS			 read-write
		STATUS					 current
		DESCRIPTION			 " -- "
		::=  { hsupaTfrcAlgorithmEntry  10 }


	hsupaTfrcNonSdPcDelta		 OBJECT-TYPE
		SYNTAX					 Integer32( 0 .. 3 )
		MAX-ACCESS			 read-write
		STATUS					 current
		DESCRIPTION			 " -- "
		::=  { hsupaTfrcAlgorithmEntry  11 }


	hsupaTfrcDpchPcDelta		 OBJECT-TYPE
		SYNTAX					 Integer32( 0 .. 3 )
		MAX-ACCESS			 read-write
		STATUS					 current
		DESCRIPTION			 " -- "
		::=  { hsupaTfrcAlgorithmEntry  12 }


	hsupaTfrcNonSdInitSnplIndex		 OBJECT-TYPE
		SYNTAX					 Integer32( 2 .. 27 )
		MAX-ACCESS			 read-write
		STATUS					 current
		DESCRIPTION			 " -- "
		::=  { hsupaTfrcAlgorithmEntry  13 }


	hsupaTfrcOlpcSwitch		 OBJECT-TYPE
		SYNTAX					 INTEGER{ off(0),on(1)  }
		MAX-ACCESS			 read-write
		STATUS					 current
		DESCRIPTION			 " -- "
		::=  { hsupaTfrcAlgorithmEntry  14 }


	hsupaTfrcPuchFMFactor		 OBJECT-TYPE
		SYNTAX					 Integer32( 1 .. 32 )
		MAX-ACCESS			 read-write
		STATUS					 current
		DESCRIPTION			 " -- "
		::=  { hsupaTfrcAlgorithmEntry  15 }


	hsupaTfrcDpchFMFactor		 OBJECT-TYPE
		SYNTAX					 Integer32( 1 .. 32 )
		MAX-ACCESS			 read-write
		STATUS					 current
		DESCRIPTION			 " -- "
		::=  { hsupaTfrcAlgorithmEntry  16 }


	hsupaTfrcCrriAllocMode		 OBJECT-TYPE
		SYNTAX					 INTEGER{ ascending(0),descending(1)  }
		MAX-ACCESS			 read-write
		STATUS					 current
		DESCRIPTION			 " -- "
		::=  { hsupaTfrcAlgorithmEntry  17 }


	hsupaTfrcCtrlChSdmaDegree		 OBJECT-TYPE
		SYNTAX					 INTEGER{ noSDMA(1),twoDegree(2),threeDegree(3),fourDegree(4),fiveDegree(5),sixDegree(6),sevenDegree(7),eightDegree(8)  }
		MAX-ACCESS			 read-write
		STATUS					 current
		DESCRIPTION			 " -- "
		::=  { hsupaTfrcAlgorithmEntry  18 }


	hsupaTfrcFastPuchFMFactor		 OBJECT-TYPE
		SYNTAX					 Integer32( 1 .. 16 )
		MAX-ACCESS			 read-write
		STATUS					 current
		DESCRIPTION			 " -- "
		::=  { hsupaTfrcAlgorithmEntry  19 }


	hsupaTfrcDeltaSich		 OBJECT-TYPE
		SYNTAX					 Integer32( -60 .. 60 )
		MAX-ACCESS			 read-write
		STATUS					 current
		DESCRIPTION			 " -- "
		::=  { hsupaTfrcAlgorithmEntry  20 }


	hsupaSpsSchedNode		 OBJECT IDENTIFIER
		::=  { hsupaAlgorithmNode  4 }


	hsupaSpsSchedTable		 OBJECT-TYPE
		SYNTAX					 SEQUENCE  OF	 HsupaSpsSchedEntry
		MAX-ACCESS			 not-accessible
		STATUS					 current
		DESCRIPTION			 " -- "
		::=  { hsupaSpsSchedNode  1 }


	hsupaSpsSchedEntry		 OBJECT-TYPE
		SYNTAX					 HsupaSpsSchedEntry
		MAX-ACCESS			 not-accessible
		STATUS					 current
		DESCRIPTION			 " -- "
		INDEX						{ hsupaSpsSchedLcId }
		::=  { hsupaSpsSchedTable  1 }


	HsupaSpsSchedEntry		 ::=  SEQUENCE {
		hsupaSpsSchedLcId					Integer32,
		hsupaSpsSchedRowStatus					RowStatus,
		hsupaSpsSchedSilentTransCntTh					Integer32,
		hsupaSpsSchedActiveTransPktTh					Integer32,
		hsupaSpsSchedDynamicSDThFactor					Integer32,
		hsupaSpsSchedDeltaQPSK					Integer32,
		hsupaSpsSchedDelta16QAM					Integer32,
		hsupaSpsSchedTimerQPSK					Integer32,
		hsupaSpsSchedTimer16QAM					Integer32,
		hsupaSpsSchedResrcBlkTsCfgIndex					Integer32,
		hsupaSpsSchedResrcBlkCfgIndex					Integer32,
		hsupaSpsSchedCodeRate					Integer32,
		hsupaSpsSchedAllocPuchDetectCntTh					Integer32,
		hsupaSpsSchedRelPuchDetectCntTh					Integer32
		}


	hsupaSpsSchedLcId		 OBJECT-TYPE
		SYNTAX					 Integer32( 0 .. 11 )
		MAX-ACCESS			 not-accessible
		STATUS					 current
		DESCRIPTION			 " -- "
		::=  { hsupaSpsSchedEntry  1 }


	hsupaSpsSchedRowStatus		 OBJECT-TYPE
		SYNTAX					 RowStatus
		MAX-ACCESS			 read-only
		STATUS					 current
		DESCRIPTION			 " -- "
		::=  { hsupaSpsSchedEntry  2 }


	hsupaSpsSchedSilentTransCntTh		 OBJECT-TYPE
		SYNTAX					 Integer32( 1 .. 6 )
		MAX-ACCESS			 read-write
		STATUS					 current
		DESCRIPTION			 " -- "
		::=  { hsupaSpsSchedEntry  3 }


	hsupaSpsSchedActiveTransPktTh		 OBJECT-TYPE
		SYNTAX					 Integer32( 12 .. 40 )
		MAX-ACCESS			 read-write
		STATUS					 current
		DESCRIPTION			 " -- "
		::=  { hsupaSpsSchedEntry  4 }


	hsupaSpsSchedDynamicSDThFactor		 OBJECT-TYPE
		SYNTAX					 Integer32( 1 .. 100 )
		MAX-ACCESS			 read-write
		STATUS					 current
		DESCRIPTION			 " -- "
		::=  { hsupaSpsSchedEntry  5 }


	hsupaSpsSchedDeltaQPSK		 OBJECT-TYPE
		SYNTAX					 Integer32( 10 .. 30 )
		MAX-ACCESS			 read-write
		STATUS					 current
		DESCRIPTION			 " -- "
		::=  { hsupaSpsSchedEntry  6 }


	hsupaSpsSchedDelta16QAM		 OBJECT-TYPE
		SYNTAX					 Integer32( 0 .. 15 )
		MAX-ACCESS			 read-write
		STATUS					 current
		DESCRIPTION			 " -- "
		::=  { hsupaSpsSchedEntry  7 }


	hsupaSpsSchedTimerQPSK		 OBJECT-TYPE
		SYNTAX					 Integer32( 80 .. 100 )
		MAX-ACCESS			 read-write
		STATUS					 current
		DESCRIPTION			 " -- "
		::=  { hsupaSpsSchedEntry  8 }


	hsupaSpsSchedTimer16QAM		 OBJECT-TYPE
		SYNTAX					 Integer32( 80 .. 100 )
		MAX-ACCESS			 read-write
		STATUS					 current
		DESCRIPTION			 " -- "
		::=  { hsupaSpsSchedEntry  9 }


	hsupaSpsSchedResrcBlkTsCfgIndex		 OBJECT-TYPE
		SYNTAX					 Integer32( 0 .. 1 )
		MAX-ACCESS			 read-write
		STATUS					 current
		DESCRIPTION			 " -- "
		::=  { hsupaSpsSchedEntry  10 }


	hsupaSpsSchedResrcBlkCfgIndex		 OBJECT-TYPE
		SYNTAX					 Integer32( 0 .. 3 )
		MAX-ACCESS			 read-write
		STATUS					 current
		DESCRIPTION			 " -- "
		::=  { hsupaSpsSchedEntry  11 }


	hsupaSpsSchedCodeRate		 OBJECT-TYPE
		SYNTAX					 Integer32( 55 .. 1000 )
		MAX-ACCESS			 read-write
		STATUS					 current
		DESCRIPTION			 " -- "
		::=  { hsupaSpsSchedEntry  12 }


	hsupaSpsSchedAllocPuchDetectCntTh		 OBJECT-TYPE
		SYNTAX					 Integer32( 1 .. 10 )
		MAX-ACCESS			 read-write
		STATUS					 current
		DESCRIPTION			 " -- "
		::=  { hsupaSpsSchedEntry  13 }


	hsupaSpsSchedRelPuchDetectCntTh		 OBJECT-TYPE
		SYNTAX					 Integer32( 1 .. 10 )
		MAX-ACCESS			 read-write
		STATUS					 current
		DESCRIPTION			 " -- "
		::=  { hsupaSpsSchedEntry  14 }


	hsupaCellSelectNode		 OBJECT IDENTIFIER
		::=  { hsupaAlgorithmNode  5 }


	hsupaCellSelectTable		 OBJECT-TYPE
		SYNTAX					 SEQUENCE  OF	 HsupaCellSelectEntry
		MAX-ACCESS			 not-accessible
		STATUS					 current
		DESCRIPTION			 " -- "
		::=  { hsupaCellSelectNode  1 }


	hsupaCellSelectEntry		 OBJECT-TYPE
		SYNTAX					 HsupaCellSelectEntry
		MAX-ACCESS			 not-accessible
		STATUS					 current
		DESCRIPTION			 " -- "
		INDEX						{ hsupaCellSelectLcId }
		::=  { hsupaCellSelectTable  1 }


	HsupaCellSelectEntry		 ::=  SEQUENCE {
		hsupaCellSelectLcId					Integer32,
		hsupaCellSelectRowStatus					RowStatus,
		hsupaCellSelectSchedNum					Integer32,
		hsupaCellSelectNotSchedTime					Integer32
		}


	hsupaCellSelectLcId		 OBJECT-TYPE
		SYNTAX					 Integer32( 0 .. 11 )
		MAX-ACCESS			 not-accessible
		STATUS					 current
		DESCRIPTION			 " -- "
		::=  { hsupaCellSelectEntry  1 }


	hsupaCellSelectRowStatus		 OBJECT-TYPE
		SYNTAX					 RowStatus
		MAX-ACCESS			 read-only
		STATUS					 current
		DESCRIPTION			 " -- "
		::=  { hsupaCellSelectEntry  2 }


	hsupaCellSelectSchedNum		 OBJECT-TYPE
		SYNTAX					 Integer32( 1 .. 8 )
		MAX-ACCESS			 read-write
		STATUS					 current
		DESCRIPTION			 " -- "
		::=  { hsupaCellSelectEntry  3 }


	hsupaCellSelectNotSchedTime		 OBJECT-TYPE
		SYNTAX					 Integer32( 1 .. 65535 )
		MAX-ACCESS			 read-write
		STATUS					 current
		DESCRIPTION			 " -- "
		::=  { hsupaCellSelectEntry  4 }


	hsupaCommSchedNode		 OBJECT IDENTIFIER
		::=  { hsupaAlgorithmNode  6 }


	hsupaCommSchedTable		 OBJECT-TYPE
		SYNTAX					 SEQUENCE  OF	 HsupaCommSchedEntry
		MAX-ACCESS			 not-accessible
		STATUS					 current
		DESCRIPTION			 " -- "
		::=  { hsupaCommSchedNode  1 }


	hsupaCommSchedEntry		 OBJECT-TYPE
		SYNTAX					 HsupaCommSchedEntry
		MAX-ACCESS			 not-accessible
		STATUS					 current
		DESCRIPTION			 " -- "
		INDEX						{ hsupaCommSchedLcId }
		::=  { hsupaCommSchedTable  1 }


	HsupaCommSchedEntry		 ::=  SEQUENCE {
		hsupaCommSchedLcId					Integer32,
		hsupaCommSchedRowStatus					RowStatus,
		hsupaCommSchedRcvRucchSchedTh					Integer32,
		hsupaCommSchedDpchPreemptPolicy					INTEGER,
		hsupaForceSchedTh					Integer32
		}


	hsupaCommSchedLcId		 OBJECT-TYPE
		SYNTAX					 Integer32( 0 .. 11 )
		MAX-ACCESS			 not-accessible
		STATUS					 current
		DESCRIPTION			 " -- "
		::=  { hsupaCommSchedEntry  1 }


	hsupaCommSchedRowStatus		 OBJECT-TYPE
		SYNTAX					 RowStatus
		MAX-ACCESS			 read-only
		STATUS					 current
		DESCRIPTION			 " -- "
		::=  { hsupaCommSchedEntry  2 }


	hsupaCommSchedRcvRucchSchedTh		 OBJECT-TYPE
		SYNTAX					 Integer32( 10 .. 240 )
		MAX-ACCESS			 read-write
		STATUS					 current
		DESCRIPTION			 " -- "
		::=  { hsupaCommSchedEntry  3 }


	hsupaCommSchedDpchPreemptPolicy		 OBJECT-TYPE
		SYNTAX					 INTEGER{ vru(0),timeSlot(1)  }
		MAX-ACCESS			 read-write
		STATUS					 current
		DESCRIPTION			 " -- "
		::=  { hsupaCommSchedEntry  4 }


	hsupaForceSchedTh		 OBJECT-TYPE
		SYNTAX					 Integer32( 10 .. 255 )
		MAX-ACCESS			 read-write
		STATUS					 current
		DESCRIPTION			 " -- "
		::=  { hsupaCommSchedEntry  5 }


	hsupaCongestCtrlNode		 OBJECT IDENTIFIER
		::=  { hsupaAlgorithmNode  7 }


	hsupaCongestCtrlTable		 OBJECT-TYPE
		SYNTAX					 SEQUENCE  OF	 HsupaCongestCtrlEntry
		MAX-ACCESS			 not-accessible
		STATUS					 current
		DESCRIPTION			 " -- "
		::=  { hsupaCongestCtrlNode  1 }


	hsupaCongestCtrlEntry		 OBJECT-TYPE
		SYNTAX					 HsupaCongestCtrlEntry
		MAX-ACCESS			 not-accessible
		STATUS					 current
		DESCRIPTION			 " -- "
		INDEX						{ hsupaCongestCtrlLcId }
		::=  { hsupaCongestCtrlTable  1 }


	HsupaCongestCtrlEntry		 ::=  SEQUENCE {
		hsupaCongestCtrlLcId					Integer32,
		hsupaCongestCtrlRowStatus					RowStatus,
		hsupaCongestCtrlDecreasePara					Integer32,
		hsupaCongestCtrlIncreasePara					Integer32,
		hsupaCongestCtrlDeCongTh					Integer32,
		hsupaCongestCtrlRestoreTimerTh					Integer32,
		hsupaCongestCtrlRestoreCounterTh					Integer32,
		hsupaCongestCtrlWinLength					Integer32
		}


	hsupaCongestCtrlLcId		 OBJECT-TYPE
		SYNTAX					 Integer32( 0 .. 11 )
		MAX-ACCESS			 not-accessible
		STATUS					 current
		DESCRIPTION			 " -- "
		::=  { hsupaCongestCtrlEntry  1 }


	hsupaCongestCtrlRowStatus		 OBJECT-TYPE
		SYNTAX					 RowStatus
		MAX-ACCESS			 read-only
		STATUS					 current
		DESCRIPTION			 " -- "
		::=  { hsupaCongestCtrlEntry  2 }


	hsupaCongestCtrlDecreasePara		 OBJECT-TYPE
		SYNTAX					 Integer32( 2 .. 8 )
		MAX-ACCESS			 read-write
		STATUS					 current
		DESCRIPTION			 " -- "
		::=  { hsupaCongestCtrlEntry  3 }


	hsupaCongestCtrlIncreasePara		 OBJECT-TYPE
		SYNTAX					 Integer32( 2 .. 16 )
		MAX-ACCESS			 read-write
		STATUS					 current
		DESCRIPTION			 " -- "
		::=  { hsupaCongestCtrlEntry  4 }


	hsupaCongestCtrlDeCongTh		 OBJECT-TYPE
		SYNTAX					 Integer32( 2 .. 64 )
		MAX-ACCESS			 read-write
		STATUS					 current
		DESCRIPTION			 " -- "
		::=  { hsupaCongestCtrlEntry  5 }


	hsupaCongestCtrlRestoreTimerTh		 OBJECT-TYPE
		SYNTAX					 Integer32( 8 .. 15 )
		MAX-ACCESS			 read-write
		STATUS					 current
		DESCRIPTION			 " -- "
		::=  { hsupaCongestCtrlEntry  6 }


	hsupaCongestCtrlRestoreCounterTh		 OBJECT-TYPE
		SYNTAX					 Integer32( 2 .. 8 )
		MAX-ACCESS			 read-write
		STATUS					 current
		DESCRIPTION			 " -- "
		::=  { hsupaCongestCtrlEntry  7 }


	hsupaCongestCtrlWinLength		 OBJECT-TYPE
		SYNTAX					 Integer32( 2 .. 20 )
		MAX-ACCESS			 read-write
		STATUS					 current
		DESCRIPTION			 " -- "
		::=  { hsupaCongestCtrlEntry  8 }


	alcap		 OBJECT IDENTIFIER
		::=  { hl  4 }


	alcapTotalPaths		 OBJECT-TYPE
		SYNTAX					 Unsigned32( 0 .. 4294967295 )
		MAX-ACCESS			 read-only
		STATUS					 current
		DESCRIPTION			 " -- "
		::=  { alcap  1 }


	alcapTotalLinks		 OBJECT-TYPE
		SYNTAX					 Unsigned32( 0 .. 4294967295 )
		MAX-ACCESS			 read-only
		STATUS					 current
		DESCRIPTION			 " -- "
		::=  { alcap  2 }


	alcapTotalConns		 OBJECT-TYPE
		SYNTAX					 Unsigned32( 0 .. 4294967295 )
		MAX-ACCESS			 read-only
		STATUS					 current
		DESCRIPTION			 " -- "
		::=  { alcap  3 }


	alcapInRouteAddr		 OBJECT-TYPE
		SYNTAX					 DisplayString( SIZE ( 40 .. 40 ) )
		MAX-ACCESS			 read-only
		STATUS					 current
		DESCRIPTION			 " -- "
		::=  { alcap  4 }


	tdPl		 OBJECT IDENTIFIER
		::=  { tdsSuperNodeB  3 }


	sjm1		 OBJECT IDENTIFIER
		::=  { tdPl  1 }


	sjm1Table		 OBJECT-TYPE
		SYNTAX					 SEQUENCE  OF	 Sjm1Entry
		MAX-ACCESS			 not-accessible
		STATUS					 current
		DESCRIPTION			 " -- "
		::=  { sjm1  1 }


	sjm1Entry		 OBJECT-TYPE
		SYNTAX					 Sjm1Entry
		MAX-ACCESS			 not-accessible
		STATUS					 current
		DESCRIPTION			 " -- "
		INDEX						{ sjm1LocalCellId }
		::=  { sjm1Table  1 }


	Sjm1Entry		 ::=  SEQUENCE {
		sjm1LocalCellId					Integer32,
		sjm1RowStatus					RowStatus,
		sjm1ThresholdCC					Integer32,
		sjm1ThresholdFC					Integer32,
		sjm1ThresholdPP					Integer32,
		sjm1AveragePeriodMatrixISCP					Integer32,
		sjm1ThreshIrtPiip					Integer32,
		sjm1ThreshIrtPeak					Integer32,
		sjm1ThresholdAcd					Integer32,
		sjm1ThresholdAcdIntraf					Integer32,
		sjm1ThresholdAcdSNR					Integer32,
		sjm1BfThreshold					Integer32,
		sjm1TotalVruNum					INTEGER,
		sjm1HighSpeedAlgorithmSwitch					INTEGER,
		sjm1FreqShiftSwitch					INTEGER,
		sjm1RoundSwitch					INTEGER,
		sjm1RoundPeriod					Integer32,
		sjm1RecursionFactor					Integer32,
		sjm1MaxPuchRscp					Integer32,
		sjm1MinPuchRscp					Integer32,
		sjm1PuchDeltaSnr					Integer32,
		sjm1IscpPathThreshold					Integer32,
		sjm1RnAlgorithmSwitch					INTEGER,
		sjm1SnrLowThresholdQpsk					Integer32,
		sjm1SnrHighThresholdQpsk					Integer32,
		sjm1SnrLowThreshold16Qam					Integer32,
		sjm1SnrHighThreshold16Qam					Integer32,
		sjm1CoFreqAlgorithmSwitch					INTEGER,
		sjm1RnMatrixWindowAcd					Integer32,
		sjm1ThresholdPPNotSmartAnt					Integer32,
		sjm1SichAcdSwitch					INTEGER,
		sjm1SichAcdThreshold					Integer32,
		sjm1WinPwrActThFactor					INTEGER,
		sjm1DasIscpPathMaxThreshold					Integer32,
		sjm1DasIscpPathMinThreshold					Integer32,
		sjm1WinPwrAcdThFactor					Integer32,
		sjm1PeakPosThreshold					Integer32,
		sjm1SyncDlRxPowerTh					Integer32,
		sjm1SyncDlDetectTimesTh					Integer32,
		sjm1CoFreqAlgorithmSwitchNotSmartAnt					INTEGER,
		sjm1RoundSwitchSmartAnt					INTEGER,
		sjm1IscpRptTypeSwitchNotSmartAnt					INTEGER,
		sjm1IscpRptTypeSwitchSmartAnt					INTEGER
		}


	sjm1LocalCellId		 OBJECT-TYPE
		SYNTAX					 Integer32( 0 .. 11 )
		MAX-ACCESS			 not-accessible
		STATUS					 current
		DESCRIPTION			 " -- "
		::=  { sjm1Entry  1 }


	sjm1RowStatus		 OBJECT-TYPE
		SYNTAX					 RowStatus
		MAX-ACCESS			 read-only
		STATUS					 current
		DESCRIPTION			 " -- "
		::=  { sjm1Entry  2 }


	sjm1ThresholdCC		 OBJECT-TYPE
		SYNTAX					 Integer32( 0 .. 65535 )
		MAX-ACCESS			 read-write
		STATUS					 current
		DESCRIPTION			 " -- "
		::=  { sjm1Entry  3 }


	sjm1ThresholdFC		 OBJECT-TYPE
		SYNTAX					 Integer32( 0 .. 65535 )
		MAX-ACCESS			 read-write
		STATUS					 current
		DESCRIPTION			 " -- "
		::=  { sjm1Entry  4 }


	sjm1ThresholdPP		 OBJECT-TYPE
		SYNTAX					 Integer32( 1 .. 22 )
		MAX-ACCESS			 read-write
		STATUS					 current
		DESCRIPTION			 " -- "
		::=  { sjm1Entry  5 }


	sjm1AveragePeriodMatrixISCP		 OBJECT-TYPE
		SYNTAX					 Integer32( 1 .. 32 )
		MAX-ACCESS			 read-write
		STATUS					 current
		DESCRIPTION			 " -- "
		::=  { sjm1Entry  6 }


	sjm1ThreshIrtPiip		 OBJECT-TYPE
		SYNTAX					 Integer32( 0 .. 16 )
		MAX-ACCESS			 read-write
		STATUS					 current
		DESCRIPTION			 " -- "
		::=  { sjm1Entry  7 }


	sjm1ThreshIrtPeak		 OBJECT-TYPE
		SYNTAX					 Integer32( 0 .. 16 )
		MAX-ACCESS			 read-write
		STATUS					 current
		DESCRIPTION			 " -- "
		::=  { sjm1Entry  8 }


	sjm1ThresholdAcd		 OBJECT-TYPE
		SYNTAX					 Integer32( 128 .. 256 )
		MAX-ACCESS			 read-write
		STATUS					 current
		DESCRIPTION			 " -- "
		::=  { sjm1Entry  9 }


	sjm1ThresholdAcdIntraf		 OBJECT-TYPE
		SYNTAX					 Integer32( 512 .. 2047 )
		MAX-ACCESS			 read-write
		STATUS					 current
		DESCRIPTION			 " -- "
		::=  { sjm1Entry  10 }


	sjm1ThresholdAcdSNR		 OBJECT-TYPE
		SYNTAX					 Integer32( 128 .. 2560 )
		MAX-ACCESS			 read-write
		STATUS					 current
		DESCRIPTION			 " -- "
		::=  { sjm1Entry  11 }


	sjm1BfThreshold		 OBJECT-TYPE
		SYNTAX					 Integer32( 0 .. 32767 )
		MAX-ACCESS			 read-write
		STATUS					 current
		DESCRIPTION			 " -- "
		::=  { sjm1Entry  12 }


	sjm1TotalVruNum		 OBJECT-TYPE
		SYNTAX					 INTEGER{ val16(16),val20(20),val24(24),val28(28),val32(32),val36(36),val40(40)  }
		MAX-ACCESS			 read-write
		STATUS					 current
		DESCRIPTION			 " -- "
		::=  { sjm1Entry  13 }


	sjm1HighSpeedAlgorithmSwitch		 OBJECT-TYPE
		SYNTAX					 INTEGER{ off(0),on(1)  }
		MAX-ACCESS			 read-write
		STATUS					 current
		DESCRIPTION			 " -- "
		::=  { sjm1Entry  14 }


	sjm1FreqShiftSwitch		 OBJECT-TYPE
		SYNTAX					 INTEGER{ off(0),on(1)  }
		MAX-ACCESS			 read-write
		STATUS					 current
		DESCRIPTION			 " -- "
		::=  { sjm1Entry  15 }


	sjm1RoundSwitch		 OBJECT-TYPE
		SYNTAX					 INTEGER{ off(0),on(1)  }
		MAX-ACCESS			 read-write
		STATUS					 current
		DESCRIPTION			 " -- "
		::=  { sjm1Entry  16 }


	sjm1RoundPeriod		 OBJECT-TYPE
		SYNTAX					 Integer32( 1 .. 8191 )
		MAX-ACCESS			 read-write
		STATUS					 current
		DESCRIPTION			 " -- "
		::=  { sjm1Entry  17 }


	sjm1RecursionFactor		 OBJECT-TYPE
		SYNTAX					 Integer32( 0 .. 5 )
		MAX-ACCESS			 read-write
		STATUS					 current
		DESCRIPTION			 " -- "
		::=  { sjm1Entry  18 }


	sjm1MaxPuchRscp		 OBJECT-TYPE
		SYNTAX					 Integer32( -125 .. -50 )
		MAX-ACCESS			 read-write
		STATUS					 current
		DESCRIPTION			 " -- "
		::=  { sjm1Entry  19 }


	sjm1MinPuchRscp		 OBJECT-TYPE
		SYNTAX					 Integer32( -125 .. -50 )
		MAX-ACCESS			 read-write
		STATUS					 current
		DESCRIPTION			 " -- "
		::=  { sjm1Entry  20 }


	sjm1PuchDeltaSnr		 OBJECT-TYPE
		SYNTAX					 Integer32( -10 .. 25 )
		MAX-ACCESS			 read-write
		STATUS					 current
		DESCRIPTION			 " -- "
		::=  { sjm1Entry  21 }


	sjm1IscpPathThreshold		 OBJECT-TYPE
		SYNTAX					 Integer32( 0 .. 60 )
		MAX-ACCESS			 read-write
		STATUS					 current
		DESCRIPTION			 " -- "
		::=  { sjm1Entry  22 }


	sjm1RnAlgorithmSwitch		 OBJECT-TYPE
		SYNTAX					 INTEGER{ off(0),on(1)  }
		MAX-ACCESS			 read-write
		STATUS					 current
		DESCRIPTION			 " -- "
		::=  { sjm1Entry  23 }


	sjm1SnrLowThresholdQpsk		 OBJECT-TYPE
		SYNTAX					 Integer32( 2 .. 256 )
		MAX-ACCESS			 read-write
		STATUS					 current
		DESCRIPTION			 " -- "
		::=  { sjm1Entry  24 }


	sjm1SnrHighThresholdQpsk		 OBJECT-TYPE
		SYNTAX					 Integer32( 256 .. 2560 )
		MAX-ACCESS			 read-write
		STATUS					 current
		DESCRIPTION			 " -- "
		::=  { sjm1Entry  25 }


	sjm1SnrLowThreshold16Qam		 OBJECT-TYPE
		SYNTAX					 Integer32( 25 .. 5120 )
		MAX-ACCESS			 read-write
		STATUS					 current
		DESCRIPTION			 " -- "
		::=  { sjm1Entry  26 }


	sjm1SnrHighThreshold16Qam		 OBJECT-TYPE
		SYNTAX					 Integer32( 256 .. 8192 )
		MAX-ACCESS			 read-write
		STATUS					 current
		DESCRIPTION			 " -- "
		::=  { sjm1Entry  27 }


	sjm1CoFreqAlgorithmSwitch		 OBJECT-TYPE
		SYNTAX					 INTEGER{ off(0),on(1)  }
		MAX-ACCESS			 read-write
		STATUS					 current
		DESCRIPTION			 " -- "
		::=  { sjm1Entry  28 }


	sjm1RnMatrixWindowAcd		 OBJECT-TYPE
		SYNTAX					 Integer32( -8 .. 2 )
		MAX-ACCESS			 read-write
		STATUS					 current
		DESCRIPTION			 " -- "
		::=  { sjm1Entry  29 }


	sjm1ThresholdPPNotSmartAnt		 OBJECT-TYPE
		SYNTAX					 Integer32( 1 .. 22 )
		MAX-ACCESS			 read-write
		STATUS					 current
		DESCRIPTION			 " -- "
		::=  { sjm1Entry  30 }


	sjm1SichAcdSwitch		 OBJECT-TYPE
		SYNTAX					 INTEGER{ off(0),on(1)  }
		MAX-ACCESS			 read-write
		STATUS					 current
		DESCRIPTION			 " -- "
		::=  { sjm1Entry  31 }


	sjm1SichAcdThreshold		 OBJECT-TYPE
		SYNTAX					 Integer32( 0 .. 255 )
		MAX-ACCESS			 read-write
		STATUS					 current
		DESCRIPTION			 " -- "
		::=  { sjm1Entry  32 }


	sjm1WinPwrActThFactor		 OBJECT-TYPE
		SYNTAX					 INTEGER{ val0(0),val0dot5(1),val1(2),val1dot5(3),val2(4),val2dot5(5),val3(6),val3dot5(7),val4(8),val4dot5(9),val5(10),val5dot5(11),val6(12),val6dot5(13),val7(14),val7dot5(15)  }
		MAX-ACCESS			 read-write
		STATUS					 current
		DESCRIPTION			 " -- "
		::=  { sjm1Entry  33 }


	sjm1DasIscpPathMaxThreshold		 OBJECT-TYPE
		SYNTAX					 Integer32( -120 .. -50 )
		MAX-ACCESS			 read-write
		STATUS					 current
		DESCRIPTION			 " -- "
		::=  { sjm1Entry  34 }


	sjm1DasIscpPathMinThreshold		 OBJECT-TYPE
		SYNTAX					 Integer32( -120 .. -50 )
		MAX-ACCESS			 read-write
		STATUS					 current
		DESCRIPTION			 " -- "
		::=  { sjm1Entry  35 }


	sjm1WinPwrAcdThFactor		 OBJECT-TYPE
		SYNTAX					 Integer32( 0 .. 32767 )
		MAX-ACCESS			 read-write
		STATUS					 current
		DESCRIPTION			 " -- "
		::=  { sjm1Entry  36 }


	sjm1PeakPosThreshold		 OBJECT-TYPE
		SYNTAX					 Integer32( 1 .. 16 )
		MAX-ACCESS			 read-write
		STATUS					 current
		DESCRIPTION			 " -- "
		::=  { sjm1Entry  37 }


	sjm1SyncDlRxPowerTh		 OBJECT-TYPE
		SYNTAX					 Integer32( -120 .. -50 )
		MAX-ACCESS			 read-write
		STATUS					 current
		DESCRIPTION			 " -- "
		::=  { sjm1Entry  38 }


	sjm1SyncDlDetectTimesTh		 OBJECT-TYPE
		SYNTAX					 Integer32( 0 .. 20 )
		MAX-ACCESS			 read-write
		STATUS					 current
		DESCRIPTION			 " -- "
		::=  { sjm1Entry  39 }


	sjm1CoFreqAlgorithmSwitchNotSmartAnt		 OBJECT-TYPE
		SYNTAX					 INTEGER{ off(0),on(1)  }
		MAX-ACCESS			 read-write
		STATUS					 current
		DESCRIPTION			 " -- "
		::=  { sjm1Entry  40 }


	sjm1RoundSwitchSmartAnt		 OBJECT-TYPE
		SYNTAX					 INTEGER{ off(0),on(1)  }
		MAX-ACCESS			 read-write
		STATUS					 current
		DESCRIPTION			 " -- "
		::=  { sjm1Entry  41 }


	sjm1IscpRptTypeSwitchNotSmartAnt		 OBJECT-TYPE
		SYNTAX					 INTEGER{ type0(0),type1(1),type2(2)  }
		MAX-ACCESS			 read-write
		STATUS					 current
		DESCRIPTION			 " -- "
		::=  { sjm1Entry  42 }


	sjm1IscpRptTypeSwitchSmartAnt		 OBJECT-TYPE
		SYNTAX					 INTEGER{ type0(0),type1(1),type2(2)  }
		MAX-ACCESS			 read-write
		STATUS					 current
		DESCRIPTION			 " -- "
		::=  { sjm1Entry  43 }


	sd		 OBJECT IDENTIFIER
		::=  { tdPl  2 }


	sdTable		 OBJECT-TYPE
		SYNTAX					 SEQUENCE  OF	 SdEntry
		MAX-ACCESS			 not-accessible
		STATUS					 current
		DESCRIPTION			 " -- "
		::=  { sd  1 }


	sdEntry		 OBJECT-TYPE
		SYNTAX					 SdEntry
		MAX-ACCESS			 not-accessible
		STATUS					 current
		DESCRIPTION			 " -- "
		INDEX						{ sdLocalCellId }
		::=  { sdTable  1 }


	SdEntry		 ::=  SEQUENCE {
		sdLocalCellId					Integer32,
		sdRowStatus					RowStatus,
		sdForgettingFactorP					Integer32,
		sdDWCMode					Integer32,
		sdZeroSettingNum					Integer32,
		sdCarrToIntDesRACHI					Integer32,
		sdAverPeriodRACHInt					Integer32,
		sdPeakAverageDiffThres					Integer32,
		sdPeakSideDiffThres					Integer32,
		sdCountThreshold					Integer32,
		sdDeltaTimeDiff					Integer32,
		sdPeakSideDiffCollThres					Integer32,
		sdPeakAverDiffRelThres					Integer32,
		sdUpptsShortAverFactor					Integer32,
		sdUpptsLongAverFactor					INTEGER,
		sdPeakSideDiffCollThresNotSmartAnt					Integer32,
		sdSyncUlThreshold					Integer32
		}


	sdLocalCellId		 OBJECT-TYPE
		SYNTAX					 Integer32( 0 .. 11 )
		MAX-ACCESS			 not-accessible
		STATUS					 current
		DESCRIPTION			 " -- "
		::=  { sdEntry  1 }


	sdRowStatus		 OBJECT-TYPE
		SYNTAX					 RowStatus
		MAX-ACCESS			 read-only
		STATUS					 current
		DESCRIPTION			 " -- "
		::=  { sdEntry  2 }


	sdForgettingFactorP		 OBJECT-TYPE
		SYNTAX					 Integer32( 0 .. 8 )
		MAX-ACCESS			 read-write
		STATUS					 current
		DESCRIPTION			 " -- "
		::=  { sdEntry  3 }


	sdDWCMode		 OBJECT-TYPE
		SYNTAX					 Integer32( 0|1|2 )
		MAX-ACCESS			 read-write
		STATUS					 current
		DESCRIPTION			 " -- "
		::=  { sdEntry  4 }


	sdZeroSettingNum		 OBJECT-TYPE
		SYNTAX					 Integer32( 0 .. 96 )
		MAX-ACCESS			 read-write
		STATUS					 current
		DESCRIPTION			 " -- "
		::=  { sdEntry  5 }


	sdCarrToIntDesRACHI		 OBJECT-TYPE
		SYNTAX					 Integer32( 0 .. 127 )
		MAX-ACCESS			 read-write
		STATUS					 current
		DESCRIPTION			 " -- "
		::=  { sdEntry  6 }


	sdAverPeriodRACHInt		 OBJECT-TYPE
		SYNTAX					 Integer32( 1 .. 127 )
		MAX-ACCESS			 read-write
		STATUS					 current
		DESCRIPTION			 " -- "
		::=  { sdEntry  7 }


	sdPeakAverageDiffThres		 OBJECT-TYPE
		SYNTAX					 Integer32( 0 .. 10 )
		MAX-ACCESS			 read-write
		STATUS					 current
		DESCRIPTION			 " -- "
		::=  { sdEntry  8 }


	sdPeakSideDiffThres		 OBJECT-TYPE
		SYNTAX					 Integer32( 0 .. 4 )
		MAX-ACCESS			 read-write
		STATUS					 current
		DESCRIPTION			 " -- "
		::=  { sdEntry  9 }


	sdCountThreshold		 OBJECT-TYPE
		SYNTAX					 Integer32( 1 .. 15 )
		MAX-ACCESS			 read-write
		STATUS					 current
		DESCRIPTION			 " -- "
		::=  { sdEntry  10 }


	sdDeltaTimeDiff		 OBJECT-TYPE
		SYNTAX					 Integer32( 0 .. 16 )
		MAX-ACCESS			 read-write
		STATUS					 current
		DESCRIPTION			 " -- "
		::=  { sdEntry  11 }


	sdPeakSideDiffCollThres		 OBJECT-TYPE
		SYNTAX					 Integer32( 1 .. 9 )
		MAX-ACCESS			 read-write
		STATUS					 current
		DESCRIPTION			 " -- "
		::=  { sdEntry  12 }


	sdPeakAverDiffRelThres		 OBJECT-TYPE
		SYNTAX					 Integer32( 0 .. 10 )
		MAX-ACCESS			 read-write
		STATUS					 current
		DESCRIPTION			 " -- "
		::=  { sdEntry  13 }


	sdUpptsShortAverFactor		 OBJECT-TYPE
		SYNTAX					 Integer32( 1 .. 8 )
		MAX-ACCESS			 read-write
		STATUS					 current
		DESCRIPTION			 " -- "
		::=  { sdEntry  14 }


	sdUpptsLongAverFactor		 OBJECT-TYPE
		SYNTAX					 INTEGER{ val1(1),val2(2),val4(4),val8(8),val16(16)  }
		MAX-ACCESS			 read-write
		STATUS					 current
		DESCRIPTION			 " -- "
		::=  { sdEntry  15 }


	sdPeakSideDiffCollThresNotSmartAnt		 OBJECT-TYPE
		SYNTAX					 Integer32( 1 .. 9 )
		MAX-ACCESS			 read-write
		STATUS					 current
		DESCRIPTION			 " -- "
		::=  { sdEntry  16 }


	sdSyncUlThreshold		 OBJECT-TYPE
		SYNTAX					 Integer32( -110 .. -80 )
		MAX-ACCESS			 read-write
		STATUS					 current
		DESCRIPTION			 " -- "
		::=  { sdEntry  17 }


	fc		 OBJECT IDENTIFIER
		::=  { tdPl  3 }


	fcTable		 OBJECT-TYPE
		SYNTAX					 SEQUENCE  OF	 FcEntry
		MAX-ACCESS			 not-accessible
		STATUS					 current
		DESCRIPTION			 " -- "
		::=  { fc  1 }


	fcEntry		 OBJECT-TYPE
		SYNTAX					 FcEntry
		MAX-ACCESS			 not-accessible
		STATUS					 current
		DESCRIPTION			 " -- "
		INDEX						{ fcLocalCellId }
		::=  { fcTable  1 }


	FcEntry		 ::=  SEQUENCE {
		fcLocalCellId					Integer32,
		fcRowStatus					RowStatus,
		fcDdlbfOnSwitchAttrib					INTEGER,
		fcDlpcOnSwitchAttrib					INTEGER,
		fcOlscOnSwitchAttrib					INTEGER,
		fcDoNothingULSC					Integer32,
		fcThresholdDoNothingULSC					Integer32,
		fcPeriodofOuterLoopULSC					Integer32,
		fcCIREndThreshold					Integer32,
		fcCIRStartThreshold					Integer32,
		fcMinRxpUlpc					Integer32,
		fcScchDlpcStep					Integer32,
		fcSichSirTargetNack					Integer32,
		fcScchInitTxp					Integer32,
		fcPdschInitTxp					Integer32,
		fcUlpcForgettingFactorforMean					Integer32,
		fcUlpcLinearPredictionDelay					Integer32,
		fcUlscForgettingFactorforMean					Integer32,
		fcUlscLinearPredictionDelay					Integer32,
		fcDiffDb					Integer32,
		fcPresyncSubFrame					Integer32,
		fcBfAlgorithmType					INTEGER,
		fcSnrAdjustFactor					Integer32,
		fcCombinationThreshold					Integer32,
		fcPhaseRotateSwitch					INTEGER,
		fcScchInitTxaOffset					Integer32,
		fcScchInitTxaOffsetAbound					Integer32,
		fcHichAckNackOffset					Integer32,
		fcAgchPwrGap					Integer32,
		fcAgchDpchOffsetTxa					Integer32,
		fcAgchDpchOffsetAbundanceTxa					Integer32,
		fcHichDpchOffsetTxaUser0					Integer32,
		fcHichDpchOffsetTxaUser1					Integer32,
		fcHichDpchOffsetTxaUser2					Integer32,
		fcHichDpchOffsetTxaUser3					Integer32,
		fcHichDlpcSwitch					INTEGER,
		fcMaxRxpUlpc					Integer32,
		fcMaxSnrUlss					Integer32,
		fcMinCIRThreshold					Integer32,
		fcHichDpchOffsetAbundanceTxa					Integer32,
		fcSichUlpcAbnormalThreshold					Integer32,
		fcBfThreshold					Integer32,
		fcSichSdmaIsolation					Integer32,
		fcPdschSdmaIsolation					Integer32,
		fcPuchSdmaIsolation					Integer32,
		fcPccpchPowerOffset					Integer32,
		fcPdschOffsetDelta					Integer32,
		fcPdschPCStep					Integer32,
		fcPdschModulationDelta					Integer32,
		fcPdschQpskAboud					Integer32,
		fcCommRntiScchDelta					Integer32,
		fcPdschPwrThresholdQpsk16Qam					Integer32,
		fcPdschPwrThreshold16QamQpsk					Integer32,
		fcScchInitPwrRecursionFactor1					Integer32,
		fcScchInitPwrRecursionFactor2					Integer32,
		fcScchRecursionAverageOffsetTxa					Integer32,
		fcModulationChangePeriod					Integer32,
		fcScchBfGapThreshold					Integer32,
		fcPdschPwrGap					Integer32,
		fcScchPwrGap					Integer32,
		fcVruMinTxaDl					Integer32,
		fcSsStep					Integer32,
		fcScchInitSirTarget					Integer32,
		fcSpsHspdschDlpcSwitch					INTEGER,
		fcAgchSdmaIsolation					Integer32,
		fcRxPowerFactor					Integer32,
		fcDTXAlgorithmSwitch					INTEGER,
		fcDTXPowerControlDelay					Integer32,
		fcDTXPowerGap					Integer32,
		fcDTXOffsetTxa					Integer32,
		fcSichOlpcSwitch					INTEGER,
		fcSichSirTargetUpStep					Integer32,
		fcSichSirTargetMax					Integer32,
		fcSichSirTargetMin					Integer32,
		fcSichBlerTarget					Integer32,
		fcSichErrorDetectProbability					Integer32,
		fcCarrierSlotIscpMaxThreshold					Integer32,
		fcCarrierSlotIscpMinThreshold					Integer32,
		fcCarrierSlotNoUserIscpMaxThresholdOffset					Integer32,
		fcTpcCombSwitch					INTEGER,
		fcUlDTXAlgorithmSwitch					INTEGER,
		fcUlDTXRxpDelta					Integer32,
		fcUlDTXAlgorithm					INTEGER,
		fcMaxRtwbUlpc					Integer32,
		fcUlssSnrFlag					INTEGER,
		fcSignalingTxaOffset					Integer32,
		fcAveSnrUlpc					Integer32,
		fcAveRxpUlpc					Integer32
		}


	fcLocalCellId		 OBJECT-TYPE
		SYNTAX					 Integer32( 0 .. 11 )
		MAX-ACCESS			 not-accessible
		STATUS					 current
		DESCRIPTION			 " -- "
		::=  { fcEntry  1 }


	fcRowStatus		 OBJECT-TYPE
		SYNTAX					 RowStatus
		MAX-ACCESS			 read-only
		STATUS					 current
		DESCRIPTION			 " -- "
		::=  { fcEntry  2 }


	fcDdlbfOnSwitchAttrib		 OBJECT-TYPE
		SYNTAX					 INTEGER{ off(0),on(1)  }
		MAX-ACCESS			 read-write
		STATUS					 current
		DESCRIPTION			 " -- "
		::=  { fcEntry  3 }


	fcDlpcOnSwitchAttrib		 OBJECT-TYPE
		SYNTAX					 INTEGER{ off(0),on(1)  }
		MAX-ACCESS			 read-write
		STATUS					 current
		DESCRIPTION			 " -- "
		::=  { fcEntry  4 }


	fcOlscOnSwitchAttrib		 OBJECT-TYPE
		SYNTAX					 INTEGER{ off(0),on(1)  }
		MAX-ACCESS			 read-write
		STATUS					 current
		DESCRIPTION			 " -- "
		::=  { fcEntry  5 }


	fcDoNothingULSC		 OBJECT-TYPE
		SYNTAX					 Integer32( 0 .. 1 )
		MAX-ACCESS			 read-write
		STATUS					 current
		DESCRIPTION			 " -- "
		::=  { fcEntry  6 }


	fcThresholdDoNothingULSC		 OBJECT-TYPE
		SYNTAX					 Integer32( 0 .. 255 )
		MAX-ACCESS			 read-write
		STATUS					 current
		DESCRIPTION			 " -- "
		::=  { fcEntry  7 }


	fcPeriodofOuterLoopULSC		 OBJECT-TYPE
		SYNTAX					 Integer32( 0 .. 255 )
		MAX-ACCESS			 read-write
		STATUS					 current
		DESCRIPTION			 " -- "
		::=  { fcEntry  8 }


	fcCIREndThreshold		 OBJECT-TYPE
		SYNTAX					 Integer32( 0 .. 255 )
		MAX-ACCESS			 read-write
		STATUS					 current
		DESCRIPTION			 " -- "
		::=  { fcEntry  9 }


	fcCIRStartThreshold		 OBJECT-TYPE
		SYNTAX					 Integer32( 0 .. 255 )
		MAX-ACCESS			 read-write
		STATUS					 current
		DESCRIPTION			 " -- "
		::=  { fcEntry  10 }


	fcMinRxpUlpc		 OBJECT-TYPE
		SYNTAX					 Integer32( -140 .. -110 )
		MAX-ACCESS			 read-write
		STATUS					 current
		DESCRIPTION			 " -- "
		::=  { fcEntry  11 }


	fcScchDlpcStep		 OBJECT-TYPE
		SYNTAX					 Integer32( 0 .. 2 )
		MAX-ACCESS			 read-write
		STATUS					 current
		DESCRIPTION			 " -- "
		::=  { fcEntry  12 }


	fcSichSirTargetNack		 OBJECT-TYPE
		SYNTAX					 Integer32( 0 .. 255 )
		MAX-ACCESS			 read-write
		STATUS					 current
		DESCRIPTION			 " -- "
		::=  { fcEntry  13 }


	fcScchInitTxp		 OBJECT-TYPE
		SYNTAX					 Integer32( -300 .. 0 )
		MAX-ACCESS			 read-write
		STATUS					 current
		DESCRIPTION			 " -- "
		::=  { fcEntry  14 }


	fcPdschInitTxp		 OBJECT-TYPE
		SYNTAX					 Integer32( -300 .. 0 )
		MAX-ACCESS			 read-write
		STATUS					 current
		DESCRIPTION			 " -- "
		::=  { fcEntry  15 }


	fcUlpcForgettingFactorforMean		 OBJECT-TYPE
		SYNTAX					 Integer32( 0 .. 32767 )
		MAX-ACCESS			 read-write
		STATUS					 current
		DESCRIPTION			 " -- "
		::=  { fcEntry  16 }


	fcUlpcLinearPredictionDelay		 OBJECT-TYPE
		SYNTAX					 Integer32( 1 .. 4 )
		MAX-ACCESS			 read-write
		STATUS					 current
		DESCRIPTION			 " -- "
		::=  { fcEntry  17 }


	fcUlscForgettingFactorforMean		 OBJECT-TYPE
		SYNTAX					 Integer32( 0 .. 32767 )
		MAX-ACCESS			 read-write
		STATUS					 current
		DESCRIPTION			 " -- "
		::=  { fcEntry  18 }


	fcUlscLinearPredictionDelay		 OBJECT-TYPE
		SYNTAX					 Integer32( 1 .. 4 )
		MAX-ACCESS			 read-write
		STATUS					 current
		DESCRIPTION			 " -- "
		::=  { fcEntry  19 }


	fcDiffDb		 OBJECT-TYPE
		SYNTAX					 Integer32( 11 .. 36 )
		MAX-ACCESS			 read-write
		STATUS					 current
		DESCRIPTION			 " -- "
		::=  { fcEntry  20 }


	fcPresyncSubFrame		 OBJECT-TYPE
		SYNTAX					 Integer32( 0 .. 255 )
		MAX-ACCESS			 read-write
		STATUS					 current
		DESCRIPTION			 " -- "
		::=  { fcEntry  21 }


	fcBfAlgorithmType		 OBJECT-TYPE
		SYNTAX					 INTEGER{ ebb(0),gob(1),selfAdaptive(2)  }
		MAX-ACCESS			 read-write
		STATUS					 current
		DESCRIPTION			 " -- "
		::=  { fcEntry  22 }


	fcSnrAdjustFactor		 OBJECT-TYPE
		SYNTAX					 Integer32( -6 .. 6 )
		MAX-ACCESS			 read-write
		STATUS					 current
		DESCRIPTION			 " -- "
		::=  { fcEntry  23 }


	fcCombinationThreshold		 OBJECT-TYPE
		SYNTAX					 Integer32( 0 .. 10 )
		MAX-ACCESS			 read-write
		STATUS					 current
		DESCRIPTION			 " -- "
		::=  { fcEntry  24 }


	fcPhaseRotateSwitch		 OBJECT-TYPE
		SYNTAX					 INTEGER{ off(0),on(1)  }
		MAX-ACCESS			 read-write
		STATUS					 current
		DESCRIPTION			 " -- "
		::=  { fcEntry  25 }


	fcScchInitTxaOffset		 OBJECT-TYPE
		SYNTAX					 Integer32( 0 .. 6 )
		MAX-ACCESS			 read-write
		STATUS					 current
		DESCRIPTION			 " -- "
		::=  { fcEntry  26 }


	fcScchInitTxaOffsetAbound		 OBJECT-TYPE
		SYNTAX					 Integer32( 0 .. 3 )
		MAX-ACCESS			 read-write
		STATUS					 current
		DESCRIPTION			 " -- "
		::=  { fcEntry  27 }


	fcHichAckNackOffset		 OBJECT-TYPE
		SYNTAX					 Integer32( 8 .. 18 )
		MAX-ACCESS			 read-write
		STATUS					 current
		DESCRIPTION			 " -- "
		::=  { fcEntry  28 }


	fcAgchPwrGap		 OBJECT-TYPE
		SYNTAX					 Integer32( 0 .. 255 )
		MAX-ACCESS			 read-write
		STATUS					 current
		DESCRIPTION			 " -- "
		::=  { fcEntry  29 }


	fcAgchDpchOffsetTxa		 OBJECT-TYPE
		SYNTAX					 Integer32( 0 .. 6 )
		MAX-ACCESS			 read-write
		STATUS					 current
		DESCRIPTION			 " -- "
		::=  { fcEntry  30 }


	fcAgchDpchOffsetAbundanceTxa		 OBJECT-TYPE
		SYNTAX					 Integer32( 0 .. 3 )
		MAX-ACCESS			 read-write
		STATUS					 current
		DESCRIPTION			 " -- "
		::=  { fcEntry  31 }


	fcHichDpchOffsetTxaUser0		 OBJECT-TYPE
		SYNTAX					 Integer32( -160 .. 150 )
		MAX-ACCESS			 read-write
		STATUS					 current
		DESCRIPTION			 " -- "
		::=  { fcEntry  32 }


	fcHichDpchOffsetTxaUser1		 OBJECT-TYPE
		SYNTAX					 Integer32( -160 .. 150 )
		MAX-ACCESS			 read-write
		STATUS					 current
		DESCRIPTION			 " -- "
		::=  { fcEntry  33 }


	fcHichDpchOffsetTxaUser2		 OBJECT-TYPE
		SYNTAX					 Integer32( -160 .. 150 )
		MAX-ACCESS			 read-write
		STATUS					 current
		DESCRIPTION			 " -- "
		::=  { fcEntry  34 }


	fcHichDpchOffsetTxaUser3		 OBJECT-TYPE
		SYNTAX					 Integer32( -160 .. 150 )
		MAX-ACCESS			 read-write
		STATUS					 current
		DESCRIPTION			 " -- "
		::=  { fcEntry  35 }


	fcHichDlpcSwitch		 OBJECT-TYPE
		SYNTAX					 INTEGER{ off(0),on(1)  }
		MAX-ACCESS			 read-write
		STATUS					 current
		DESCRIPTION			 " -- "
		::=  { fcEntry  36 }


	fcMaxRxpUlpc		 OBJECT-TYPE
		SYNTAX					 Integer32( -110 .. -60 )
		MAX-ACCESS			 read-write
		STATUS					 current
		DESCRIPTION			 " -- "
		::=  { fcEntry  37 }


	fcMaxSnrUlss		 OBJECT-TYPE
		SYNTAX					 Integer32( -3 .. 21 )
		MAX-ACCESS			 read-write
		STATUS					 current
		DESCRIPTION			 " -- "
		::=  { fcEntry  38 }


	fcMinCIRThreshold		 OBJECT-TYPE
		SYNTAX					 Integer32( -30 .. 25 )
		MAX-ACCESS			 read-write
		STATUS					 current
		DESCRIPTION			 " -- "
		::=  { fcEntry  39 }


	fcHichDpchOffsetAbundanceTxa		 OBJECT-TYPE
		SYNTAX					 Integer32( -16 .. 15 )
		MAX-ACCESS			 read-write
		STATUS					 current
		DESCRIPTION			 " -- "
		::=  { fcEntry  40 }


	fcSichUlpcAbnormalThreshold		 OBJECT-TYPE
		SYNTAX					 Integer32( 0 .. 255 )
		MAX-ACCESS			 read-write
		STATUS					 current
		DESCRIPTION			 " -- "
		::=  { fcEntry  41 }


	fcBfThreshold		 OBJECT-TYPE
		SYNTAX					 Integer32( 0 .. 100 )
		MAX-ACCESS			 read-write
		STATUS					 current
		DESCRIPTION			 " -- "
		::=  { fcEntry  42 }


	fcSichSdmaIsolation		 OBJECT-TYPE
		SYNTAX					 Integer32( 10 .. 40 )
		MAX-ACCESS			 read-write
		STATUS					 current
		DESCRIPTION			 " -- "
		::=  { fcEntry  43 }


	fcPdschSdmaIsolation		 OBJECT-TYPE
		SYNTAX					 Integer32( 10 .. 40 )
		MAX-ACCESS			 read-write
		STATUS					 current
		DESCRIPTION			 " -- "
		::=  { fcEntry  44 }


	fcPuchSdmaIsolation		 OBJECT-TYPE
		SYNTAX					 Integer32( 10 .. 40 )
		MAX-ACCESS			 read-write
		STATUS					 current
		DESCRIPTION			 " -- "
		::=  { fcEntry  45 }


	fcPccpchPowerOffset		 OBJECT-TYPE
		SYNTAX					 Integer32( -10 .. 0 )
		MAX-ACCESS			 read-write
		STATUS					 current
		DESCRIPTION			 " -- "
		::=  { fcEntry  46 }


	fcPdschOffsetDelta		 OBJECT-TYPE
		SYNTAX					 Integer32( 0 .. 3 )
		MAX-ACCESS			 read-write
		STATUS					 current
		DESCRIPTION			 " -- "
		::=  { fcEntry  47 }


	fcPdschPCStep		 OBJECT-TYPE
		SYNTAX					 Integer32( 10 .. 80 )
		MAX-ACCESS			 read-write
		STATUS					 current
		DESCRIPTION			 " -- "
		::=  { fcEntry  48 }


	fcPdschModulationDelta		 OBJECT-TYPE
		SYNTAX					 Integer32( 1 .. 8 )
		MAX-ACCESS			 read-write
		STATUS					 current
		DESCRIPTION			 " -- "
		::=  { fcEntry  49 }


	fcPdschQpskAboud		 OBJECT-TYPE
		SYNTAX					 Integer32( 0 .. 3 )
		MAX-ACCESS			 read-write
		STATUS					 current
		DESCRIPTION			 " -- "
		::=  { fcEntry  50 }


	fcCommRntiScchDelta		 OBJECT-TYPE
		SYNTAX					 Integer32( 0 .. 3 )
		MAX-ACCESS			 read-write
		STATUS					 current
		DESCRIPTION			 " -- "
		::=  { fcEntry  51 }


	fcPdschPwrThresholdQpsk16Qam		 OBJECT-TYPE
		SYNTAX					 Integer32( 100 .. 300 )
		MAX-ACCESS			 read-write
		STATUS					 current
		DESCRIPTION			 " -- "
		::=  { fcEntry  52 }


	fcPdschPwrThreshold16QamQpsk		 OBJECT-TYPE
		SYNTAX					 Integer32( 0 .. 150 )
		MAX-ACCESS			 read-write
		STATUS					 current
		DESCRIPTION			 " -- "
		::=  { fcEntry  53 }


	fcScchInitPwrRecursionFactor1		 OBJECT-TYPE
		SYNTAX					 Integer32( 0 .. 100 )
		MAX-ACCESS			 read-write
		STATUS					 current
		DESCRIPTION			 " -- "
		::=  { fcEntry  54 }


	fcScchInitPwrRecursionFactor2		 OBJECT-TYPE
		SYNTAX					 Integer32( 0 .. 100 )
		MAX-ACCESS			 read-write
		STATUS					 current
		DESCRIPTION			 " -- "
		::=  { fcEntry  55 }


	fcScchRecursionAverageOffsetTxa		 OBJECT-TYPE
		SYNTAX					 Integer32( 1 .. 3 )
		MAX-ACCESS			 read-write
		STATUS					 current
		DESCRIPTION			 " -- "
		::=  { fcEntry  56 }


	fcModulationChangePeriod		 OBJECT-TYPE
		SYNTAX					 Integer32( 80 .. 100 )
		MAX-ACCESS			 read-write
		STATUS					 current
		DESCRIPTION			 " -- "
		::=  { fcEntry  57 }


	fcScchBfGapThreshold		 OBJECT-TYPE
		SYNTAX					 Integer32( 1 .. 255 )
		MAX-ACCESS			 read-write
		STATUS					 current
		DESCRIPTION			 " -- "
		::=  { fcEntry  58 }


	fcPdschPwrGap		 OBJECT-TYPE
		SYNTAX					 Integer32( 1 .. 64 )
		MAX-ACCESS			 read-write
		STATUS					 current
		DESCRIPTION			 " -- "
		::=  { fcEntry  59 }


	fcScchPwrGap		 OBJECT-TYPE
		SYNTAX					 Integer32( 1 .. 64 )
		MAX-ACCESS			 read-write
		STATUS					 current
		DESCRIPTION			 " -- "
		::=  { fcEntry  60 }


	fcVruMinTxaDl		 OBJECT-TYPE
		SYNTAX					 Integer32( 9 .. 65535 )
		MAX-ACCESS			 read-write
		STATUS					 current
		DESCRIPTION			 " -- "
		::=  { fcEntry  61 }


	fcSsStep		 OBJECT-TYPE
		SYNTAX					 Integer32( 1 .. 8 )
		MAX-ACCESS			 read-write
		STATUS					 current
		DESCRIPTION			 " -- "
		::=  { fcEntry  62 }


	fcScchInitSirTarget		 OBJECT-TYPE
		SYNTAX					 Integer32( 8 .. 10 )
		MAX-ACCESS			 read-write
		STATUS					 current
		DESCRIPTION			 " -- "
		::=  { fcEntry  63 }


	fcSpsHspdschDlpcSwitch		 OBJECT-TYPE
		SYNTAX					 INTEGER{ off(0),on(1)  }
		MAX-ACCESS			 read-write
		STATUS					 current
		DESCRIPTION			 " -- "
		::=  { fcEntry  64 }


	fcAgchSdmaIsolation		 OBJECT-TYPE
		SYNTAX					 Integer32( 10 .. 40 )
		MAX-ACCESS			 read-write
		STATUS					 current
		DESCRIPTION			 " -- "
		::=  { fcEntry  65 }


	fcRxPowerFactor		 OBJECT-TYPE
		SYNTAX					 Integer32( 0 .. 32768 )
		MAX-ACCESS			 read-write
		STATUS					 current
		DESCRIPTION			 " -- "
		::=  { fcEntry  66 }


	fcDTXAlgorithmSwitch		 OBJECT-TYPE
		SYNTAX					 INTEGER{ off(0),on(1)  }
		MAX-ACCESS			 read-write
		STATUS					 current
		DESCRIPTION			 " -- "
		::=  { fcEntry  67 }


	fcDTXPowerControlDelay		 OBJECT-TYPE
		SYNTAX					 Integer32( 0 .. 7 )
		MAX-ACCESS			 read-write
		STATUS					 current
		DESCRIPTION			 " -- "
		::=  { fcEntry  68 }


	fcDTXPowerGap		 OBJECT-TYPE
		SYNTAX					 Integer32( 1 .. 255 )
		MAX-ACCESS			 read-write
		STATUS					 current
		DESCRIPTION			 " -- "
		::=  { fcEntry  69 }


	fcDTXOffsetTxa		 OBJECT-TYPE
		SYNTAX					 Integer32( -6 .. 9 )
		MAX-ACCESS			 read-write
		STATUS					 current
		DESCRIPTION			 " -- "
		::=  { fcEntry  70 }


	fcSichOlpcSwitch		 OBJECT-TYPE
		SYNTAX					 INTEGER{ off(0),on(1)  }
		MAX-ACCESS			 read-write
		STATUS					 current
		DESCRIPTION			 " -- "
		::=  { fcEntry  71 }


	fcSichSirTargetUpStep		 OBJECT-TYPE
		SYNTAX					 Integer32( 1 .. 31 )
		MAX-ACCESS			 read-write
		STATUS					 current
		DESCRIPTION			 " -- "
		::=  { fcEntry  72 }


	fcSichSirTargetMax		 OBJECT-TYPE
		SYNTAX					 Integer32( 0 .. 255 )
		MAX-ACCESS			 read-write
		STATUS					 current
		DESCRIPTION			 " -- "
		::=  { fcEntry  73 }


	fcSichSirTargetMin		 OBJECT-TYPE
		SYNTAX					 Integer32( 0 .. 255 )
		MAX-ACCESS			 read-write
		STATUS					 current
		DESCRIPTION			 " -- "
		::=  { fcEntry  74 }


	fcSichBlerTarget		 OBJECT-TYPE
		SYNTAX					 Integer32( 0 .. 255 )
		MAX-ACCESS			 read-write
		STATUS					 current
		DESCRIPTION			 " -- "
		::=  { fcEntry  75 }


	fcSichErrorDetectProbability		 OBJECT-TYPE
		SYNTAX					 Integer32( 0 .. 100 )
		MAX-ACCESS			 read-write
		STATUS					 current
		DESCRIPTION			 " -- "
		::=  { fcEntry  76 }


	fcCarrierSlotIscpMaxThreshold		 OBJECT-TYPE
		SYNTAX					 Integer32( -100 .. -45 )
		MAX-ACCESS			 read-write
		STATUS					 current
		DESCRIPTION			 " -- "
		::=  { fcEntry  77 }


	fcCarrierSlotIscpMinThreshold		 OBJECT-TYPE
		SYNTAX					 Integer32( -145 .. -110 )
		MAX-ACCESS			 read-write
		STATUS					 current
		DESCRIPTION			 " -- "
		::=  { fcEntry  78 }


	fcCarrierSlotNoUserIscpMaxThresholdOffset		 OBJECT-TYPE
		SYNTAX					 Integer32( 0 .. 15 )
		MAX-ACCESS			 read-write
		STATUS					 current
		DESCRIPTION			 " -- "
		::=  { fcEntry  79 }


	fcTpcCombSwitch		 OBJECT-TYPE
		SYNTAX					 INTEGER{ off(0),on(1)  }
		MAX-ACCESS			 read-write
		STATUS					 current
		DESCRIPTION			 " -- "
		::=  { fcEntry  80 }


	fcUlDTXAlgorithmSwitch		 OBJECT-TYPE
		SYNTAX					 INTEGER{ off(0),on(1)  }
		MAX-ACCESS			 read-write
		STATUS					 current
		DESCRIPTION			 " -- "
		::=  { fcEntry  81 }


	fcUlDTXRxpDelta		 OBJECT-TYPE
		SYNTAX					 Integer32( -30 .. 40 )
		MAX-ACCESS			 read-write
		STATUS					 current
		DESCRIPTION			 " -- "
		::=  { fcEntry  82 }


	fcUlDTXAlgorithm		 OBJECT-TYPE
		SYNTAX					 INTEGER{ a(0),b(1)  }
		MAX-ACCESS			 read-write
		STATUS					 current
		DESCRIPTION			 " -- "
		::=  { fcEntry  83 }


	fcMaxRtwbUlpc		 OBJECT-TYPE
		SYNTAX					 Integer32( -120 .. -50 )
		MAX-ACCESS			 read-write
		STATUS					 current
		DESCRIPTION			 " -- "
		::=  { fcEntry  84 }


	fcUlssSnrFlag		 OBJECT-TYPE
		SYNTAX					 INTEGER{ off(0),on(1)  }
		MAX-ACCESS			 read-write
		STATUS					 current
		DESCRIPTION			 " -- "
		::=  { fcEntry  85 }


	fcSignalingTxaOffset		 OBJECT-TYPE
		SYNTAX					 Integer32( 0 .. 24 )
		MAX-ACCESS			 read-write
		STATUS					 current
		DESCRIPTION			 " -- "
		::=  { fcEntry  86 }


	fcAveSnrUlpc		 OBJECT-TYPE
		SYNTAX					 Integer32( -3 .. 21 )
		MAX-ACCESS			 read-write
		STATUS					 current
		DESCRIPTION			 " -- "
		::=  { fcEntry  87 }


	fcAveRxpUlpc		 OBJECT-TYPE
		SYNTAX					 Integer32( -120 .. -50 )
		MAX-ACCESS			 read-write
		STATUS					 current
		DESCRIPTION			 " -- "
		::=  { fcEntry  88 }


	cc		 OBJECT IDENTIFIER
		::=  { tdPl  4 }


	ccTable		 OBJECT-TYPE
		SYNTAX					 SEQUENCE  OF	 CcEntry
		MAX-ACCESS			 not-accessible
		STATUS					 current
		DESCRIPTION			 " -- "
		::=  { cc  1 }


	ccEntry		 OBJECT-TYPE
		SYNTAX					 CcEntry
		MAX-ACCESS			 not-accessible
		STATUS					 current
		DESCRIPTION			 " -- "
		INDEX						{ ccLocalCellId }
		::=  { ccTable  1 }


	CcEntry		 ::=  SEQUENCE {
		ccLocalCellId					Integer32,
		ccRowStatus					RowStatus,
		ccStepUpEhich					INTEGER,
		ccBlerTarget					Integer32,
		ccHichFmAckUser0					Integer32,
		ccHichFmNackUser0					Integer32,
		ccHichFmAckUser1					Integer32,
		ccHichFmNackUser1					Integer32,
		ccHichFmAckUser2					Integer32,
		ccHichFmNackUser2					Integer32,
		ccHichFmAckUser3					Integer32,
		ccHichFmNackUser3					Integer32,
		ccPreOutSyncSwitch					INTEGER,
		ccBlerStatisticWindowSize					Integer32,
		ccOlpcGlideStep					Integer32,
		ccErrorThreshold					Integer32,
		ccOlpcControlPeriod					Integer32,
		ccOlpcBlerTarget					Integer32,
		ccOlpcRecursionFactor					Integer32,
		ccDeltaUpThreshold					Integer32,
		ccDeltaDownThreshold					Integer32,
		ccDeltaUpStep					Integer32,
		ccDeltaDownStep					Integer32,
		ccOlpcBlerTargetVoIP					Integer32,
		ccRachErrorRatioPeriod					Integer32,
		ccFpachNumThreshold					Integer32,
		ccRachErrorRatio					Integer32,
		ccSpbSnrMin					Integer32
		}


	ccLocalCellId		 OBJECT-TYPE
		SYNTAX					 Integer32( 0 .. 11 )
		MAX-ACCESS			 not-accessible
		STATUS					 current
		DESCRIPTION			 " -- "
		::=  { ccEntry  1 }


	ccRowStatus		 OBJECT-TYPE
		SYNTAX					 RowStatus
		MAX-ACCESS			 read-only
		STATUS					 current
		DESCRIPTION			 " -- "
		::=  { ccEntry  2 }


	ccStepUpEhich		 OBJECT-TYPE
		SYNTAX					 INTEGER{ db1(0),db2(1),db3(2)  }
		MAX-ACCESS			 read-write
		STATUS					 current
		DESCRIPTION			 " -- "
		::=  { ccEntry  3 }


	ccBlerTarget		 OBJECT-TYPE
		SYNTAX					 Integer32( 1 .. 100 )
		MAX-ACCESS			 read-write
		STATUS					 current
		DESCRIPTION			 " -- "
		::=  { ccEntry  4 }


	ccHichFmAckUser0		 OBJECT-TYPE
		SYNTAX					 Integer32( 1 .. 100 )
		MAX-ACCESS			 read-write
		STATUS					 current
		DESCRIPTION			 " -- "
		::=  { ccEntry  5 }


	ccHichFmNackUser0		 OBJECT-TYPE
		SYNTAX					 Integer32( 1 .. 100 )
		MAX-ACCESS			 read-write
		STATUS					 current
		DESCRIPTION			 " -- "
		::=  { ccEntry  6 }


	ccHichFmAckUser1		 OBJECT-TYPE
		SYNTAX					 Integer32( 1 .. 100 )
		MAX-ACCESS			 read-write
		STATUS					 current
		DESCRIPTION			 " -- "
		::=  { ccEntry  7 }


	ccHichFmNackUser1		 OBJECT-TYPE
		SYNTAX					 Integer32( 1 .. 100 )
		MAX-ACCESS			 read-write
		STATUS					 current
		DESCRIPTION			 " -- "
		::=  { ccEntry  8 }


	ccHichFmAckUser2		 OBJECT-TYPE
		SYNTAX					 Integer32( 1 .. 100 )
		MAX-ACCESS			 read-write
		STATUS					 current
		DESCRIPTION			 " -- "
		::=  { ccEntry  9 }


	ccHichFmNackUser2		 OBJECT-TYPE
		SYNTAX					 Integer32( 1 .. 100 )
		MAX-ACCESS			 read-write
		STATUS					 current
		DESCRIPTION			 " -- "
		::=  { ccEntry  10 }


	ccHichFmAckUser3		 OBJECT-TYPE
		SYNTAX					 Integer32( 1 .. 100 )
		MAX-ACCESS			 read-write
		STATUS					 current
		DESCRIPTION			 " -- "
		::=  { ccEntry  11 }


	ccHichFmNackUser3		 OBJECT-TYPE
		SYNTAX					 Integer32( 1 .. 100 )
		MAX-ACCESS			 read-write
		STATUS					 current
		DESCRIPTION			 " -- "
		::=  { ccEntry  12 }


	ccPreOutSyncSwitch		 OBJECT-TYPE
		SYNTAX					 INTEGER{ off(0),on(1)  }
		MAX-ACCESS			 read-write
		STATUS					 current
		DESCRIPTION			 " -- "
		::=  { ccEntry  13 }


	ccBlerStatisticWindowSize		 OBJECT-TYPE
		SYNTAX					 Integer32( 1 .. 50 )
		MAX-ACCESS			 read-write
		STATUS					 current
		DESCRIPTION			 " -- "
		::=  { ccEntry  14 }


	ccOlpcGlideStep		 OBJECT-TYPE
		SYNTAX					 Integer32( 1 .. 50 )
		MAX-ACCESS			 read-write
		STATUS					 current
		DESCRIPTION			 " -- "
		::=  { ccEntry  15 }


	ccErrorThreshold		 OBJECT-TYPE
		SYNTAX					 Integer32( 1 .. 50 )
		MAX-ACCESS			 read-write
		STATUS					 current
		DESCRIPTION			 " -- "
		::=  { ccEntry  16 }


	ccOlpcControlPeriod		 OBJECT-TYPE
		SYNTAX					 Integer32( 4 .. 200 )
		MAX-ACCESS			 read-write
		STATUS					 current
		DESCRIPTION			 " -- "
		::=  { ccEntry  17 }


	ccOlpcBlerTarget		 OBJECT-TYPE
		SYNTAX					 Integer32( 0 .. 100 )
		MAX-ACCESS			 read-write
		STATUS					 current
		DESCRIPTION			 " -- "
		::=  { ccEntry  18 }


	ccOlpcRecursionFactor		 OBJECT-TYPE
		SYNTAX					 Integer32( 0 .. 100 )
		MAX-ACCESS			 read-write
		STATUS					 current
		DESCRIPTION			 " -- "
		::=  { ccEntry  19 }


	ccDeltaUpThreshold		 OBJECT-TYPE
		SYNTAX					 Integer32( 0 .. 99 )
		MAX-ACCESS			 read-write
		STATUS					 current
		DESCRIPTION			 " -- "
		::=  { ccEntry  20 }


	ccDeltaDownThreshold		 OBJECT-TYPE
		SYNTAX					 Integer32( -10 .. 0 )
		MAX-ACCESS			 read-write
		STATUS					 current
		DESCRIPTION			 " -- "
		::=  { ccEntry  21 }


	ccDeltaUpStep		 OBJECT-TYPE
		SYNTAX					 Integer32( 0 .. 100 )
		MAX-ACCESS			 read-write
		STATUS					 current
		DESCRIPTION			 " -- "
		::=  { ccEntry  22 }


	ccDeltaDownStep		 OBJECT-TYPE
		SYNTAX					 Integer32( 0 .. 100 )
		MAX-ACCESS			 read-write
		STATUS					 current
		DESCRIPTION			 " -- "
		::=  { ccEntry  23 }


	ccOlpcBlerTargetVoIP		 OBJECT-TYPE
		SYNTAX					 Integer32( 0 .. 100 )
		MAX-ACCESS			 read-write
		STATUS					 current
		DESCRIPTION			 " -- "
		::=  { ccEntry  24 }


	ccRachErrorRatioPeriod		 OBJECT-TYPE
		SYNTAX					 Integer32( 0 .. 65535 )
		MAX-ACCESS			 read-write
		STATUS					 current
		DESCRIPTION			 " -- "
		::=  { ccEntry  25 }


	ccFpachNumThreshold		 OBJECT-TYPE
		SYNTAX					 Integer32( 1 .. 65535 )
		MAX-ACCESS			 read-write
		STATUS					 current
		DESCRIPTION			 " -- "
		::=  { ccEntry  26 }


	ccRachErrorRatio		 OBJECT-TYPE
		SYNTAX					 Integer32( 1 .. 100 )
		MAX-ACCESS			 read-write
		STATUS					 current
		DESCRIPTION			 " -- "
		::=  { ccEntry  27 }


	ccSpbSnrMin		 OBJECT-TYPE
		SYNTAX					 Integer32( -3 .. 21 )
		MAX-ACCESS			 read-write
		STATUS					 current
		DESCRIPTION			 " -- "
		::=  { ccEntry  28 }


	timeSlot		 OBJECT IDENTIFIER
		::=  { tdPl  5 }


	timeSlotTypeTable		 OBJECT-TYPE
		SYNTAX					 SEQUENCE  OF	 TimeSlotTypeEntry
		MAX-ACCESS			 not-accessible
		STATUS					 current
		DESCRIPTION			 " -- "
		::=  { timeSlot  1 }


	timeSlotTypeEntry		 OBJECT-TYPE
		SYNTAX					 TimeSlotTypeEntry
		MAX-ACCESS			 not-accessible
		STATUS					 current
		DESCRIPTION			 " -- "
		INDEX						{ timeSlotTypeIndex }
		::=  { timeSlotTypeTable  1 }


	TimeSlotTypeEntry		 ::=  SEQUENCE {
		timeSlotTypeIndex					Integer32,
		timeSlotTypeRowStatus					RowStatus,
		timeSlotTypeCellId					Integer32,
		timeSlotTypeCellFreq					Unsigned32,
		timeSlotTypeNeighCell1					Unsigned32,
		timeSlotTypeNeighCell2					Unsigned32,
		timeSlotTypeNeighCell3					Unsigned32,
		timeSlotTypeNeighCell4					Unsigned32,
		timeSlotTypeNeighCell5					Unsigned32,
		timeSlotTypeNeighCell6					Unsigned32,
		timeSlotTypeNeighCell7					Unsigned32,
		timeSlotTypeNeighCell8					Unsigned32,
		timeSlotTypeNeighCell9					Unsigned32,
		timeSlotTypeNeighCell10					Unsigned32,
		timeSlotTypeNeighCell11					Unsigned32,
		timeSlotTypeNeighCell12					Unsigned32,
		timeSlotTypeNeighCell13					Unsigned32,
		timeSlotTypeNeighCell14					Unsigned32,
		timeSlotTypeNeighCell15					Unsigned32,
		timeSlotTypeNeighCell16					Unsigned32,
		timeSlotTypeNeighCell17					Unsigned32,
		timeSlotTypeNeighCell18					Unsigned32,
		timeSlotTypeNeighCell19					Unsigned32,
		timeSlotTypeNeighCell20					Unsigned32,
		timeSlotTypeNeighCell21					Unsigned32,
		timeSlotTypeNeighCell22					Unsigned32,
		timeSlotTypeNeighCell23					Unsigned32,
		timeSlotTypeNeighCell24					Unsigned32,
		timeSlotTypeNeighCell25					Unsigned32,
		timeSlotTypeNeighCell26					Unsigned32,
		timeSlotTypeNeighCell27					Unsigned32,
		timeSlotTypeNeighCell28					Unsigned32,
		timeSlotTypeNeighCell29					Unsigned32,
		timeSlotTypeNeighCell30					Unsigned32,
		timeSlotTypeNeighCell31					Unsigned32
		}


	timeSlotTypeIndex		 OBJECT-TYPE
		SYNTAX					 Integer32( 0 .. 71 )
		MAX-ACCESS			 not-accessible
		STATUS					 current
		DESCRIPTION			 " -- "
		::=  { timeSlotTypeEntry  1 }


	timeSlotTypeRowStatus		 OBJECT-TYPE
		SYNTAX					 RowStatus
		MAX-ACCESS			 read-create
		STATUS					 current
		DESCRIPTION			 " -- "
		::=  { timeSlotTypeEntry  2 }


	timeSlotTypeCellId		 OBJECT-TYPE
		SYNTAX					 Integer32( -2147483648 .. 2147483647 )
		MAX-ACCESS			 read-create
		STATUS					 current
		DESCRIPTION			 " -- "
		::=  { timeSlotTypeEntry  3 }


	timeSlotTypeCellFreq		 OBJECT-TYPE
		SYNTAX					 Unsigned32( 0 .. 65535 )
		MAX-ACCESS			 read-create
		STATUS					 current
		DESCRIPTION			 " -- "
		::=  { timeSlotTypeEntry  4 }


	timeSlotTypeNeighCell1		 OBJECT-TYPE
		SYNTAX					 Unsigned32( 0 .. 4294967295 )
		MAX-ACCESS			 read-create
		STATUS					 current
		DESCRIPTION			 " -- "
		::=  { timeSlotTypeEntry  5 }


	timeSlotTypeNeighCell2		 OBJECT-TYPE
		SYNTAX					 Unsigned32( 0 .. 4294967295 )
		MAX-ACCESS			 read-create
		STATUS					 current
		DESCRIPTION			 " -- "
		::=  { timeSlotTypeEntry  6 }


	timeSlotTypeNeighCell3		 OBJECT-TYPE
		SYNTAX					 Unsigned32( 0 .. 4294967295 )
		MAX-ACCESS			 read-create
		STATUS					 current
		DESCRIPTION			 " -- "
		::=  { timeSlotTypeEntry  7 }


	timeSlotTypeNeighCell4		 OBJECT-TYPE
		SYNTAX					 Unsigned32( 0 .. 4294967295 )
		MAX-ACCESS			 read-create
		STATUS					 current
		DESCRIPTION			 " -- "
		::=  { timeSlotTypeEntry  8 }


	timeSlotTypeNeighCell5		 OBJECT-TYPE
		SYNTAX					 Unsigned32( 0 .. 4294967295 )
		MAX-ACCESS			 read-create
		STATUS					 current
		DESCRIPTION			 " -- "
		::=  { timeSlotTypeEntry  9 }


	timeSlotTypeNeighCell6		 OBJECT-TYPE
		SYNTAX					 Unsigned32( 0 .. 4294967295 )
		MAX-ACCESS			 read-create
		STATUS					 current
		DESCRIPTION			 " -- "
		::=  { timeSlotTypeEntry  10 }


	timeSlotTypeNeighCell7		 OBJECT-TYPE
		SYNTAX					 Unsigned32( 0 .. 4294967295 )
		MAX-ACCESS			 read-create
		STATUS					 current
		DESCRIPTION			 " -- "
		::=  { timeSlotTypeEntry  11 }


	timeSlotTypeNeighCell8		 OBJECT-TYPE
		SYNTAX					 Unsigned32( 0 .. 4294967295 )
		MAX-ACCESS			 read-create
		STATUS					 current
		DESCRIPTION			 " -- "
		::=  { timeSlotTypeEntry  12 }


	timeSlotTypeNeighCell9		 OBJECT-TYPE
		SYNTAX					 Unsigned32( 0 .. 4294967295 )
		MAX-ACCESS			 read-create
		STATUS					 current
		DESCRIPTION			 " -- "
		::=  { timeSlotTypeEntry  13 }


	timeSlotTypeNeighCell10		 OBJECT-TYPE
		SYNTAX					 Unsigned32( 0 .. 4294967295 )
		MAX-ACCESS			 read-create
		STATUS					 current
		DESCRIPTION			 " -- "
		::=  { timeSlotTypeEntry  14 }


	timeSlotTypeNeighCell11		 OBJECT-TYPE
		SYNTAX					 Unsigned32( 0 .. 4294967295 )
		MAX-ACCESS			 read-create
		STATUS					 current
		DESCRIPTION			 " -- "
		::=  { timeSlotTypeEntry  15 }


	timeSlotTypeNeighCell12		 OBJECT-TYPE
		SYNTAX					 Unsigned32( 0 .. 4294967295 )
		MAX-ACCESS			 read-create
		STATUS					 current
		DESCRIPTION			 " -- "
		::=  { timeSlotTypeEntry  16 }


	timeSlotTypeNeighCell13		 OBJECT-TYPE
		SYNTAX					 Unsigned32( 0 .. 4294967295 )
		MAX-ACCESS			 read-create
		STATUS					 current
		DESCRIPTION			 " -- "
		::=  { timeSlotTypeEntry  17 }


	timeSlotTypeNeighCell14		 OBJECT-TYPE
		SYNTAX					 Unsigned32( 0 .. 4294967295 )
		MAX-ACCESS			 read-create
		STATUS					 current
		DESCRIPTION			 " -- "
		::=  { timeSlotTypeEntry  18 }


	timeSlotTypeNeighCell15		 OBJECT-TYPE
		SYNTAX					 Unsigned32( 0 .. 4294967295 )
		MAX-ACCESS			 read-create
		STATUS					 current
		DESCRIPTION			 " -- "
		::=  { timeSlotTypeEntry  19 }


	timeSlotTypeNeighCell16		 OBJECT-TYPE
		SYNTAX					 Unsigned32( 0 .. 4294967295 )
		MAX-ACCESS			 read-create
		STATUS					 current
		DESCRIPTION			 " -- "
		::=  { timeSlotTypeEntry  20 }


	timeSlotTypeNeighCell17		 OBJECT-TYPE
		SYNTAX					 Unsigned32( 0 .. 4294967295 )
		MAX-ACCESS			 read-create
		STATUS					 current
		DESCRIPTION			 " -- "
		::=  { timeSlotTypeEntry  21 }


	timeSlotTypeNeighCell18		 OBJECT-TYPE
		SYNTAX					 Unsigned32( 0 .. 4294967295 )
		MAX-ACCESS			 read-create
		STATUS					 current
		DESCRIPTION			 " -- "
		::=  { timeSlotTypeEntry  22 }


	timeSlotTypeNeighCell19		 OBJECT-TYPE
		SYNTAX					 Unsigned32( 0 .. 4294967295 )
		MAX-ACCESS			 read-create
		STATUS					 current
		DESCRIPTION			 " -- "
		::=  { timeSlotTypeEntry  23 }


	timeSlotTypeNeighCell20		 OBJECT-TYPE
		SYNTAX					 Unsigned32( 0 .. 4294967295 )
		MAX-ACCESS			 read-create
		STATUS					 current
		DESCRIPTION			 " -- "
		::=  { timeSlotTypeEntry  24 }


	timeSlotTypeNeighCell21		 OBJECT-TYPE
		SYNTAX					 Unsigned32( 0 .. 4294967295 )
		MAX-ACCESS			 read-create
		STATUS					 current
		DESCRIPTION			 " -- "
		::=  { timeSlotTypeEntry  25 }


	timeSlotTypeNeighCell22		 OBJECT-TYPE
		SYNTAX					 Unsigned32( 0 .. 4294967295 )
		MAX-ACCESS			 read-create
		STATUS					 current
		DESCRIPTION			 " -- "
		::=  { timeSlotTypeEntry  26 }


	timeSlotTypeNeighCell23		 OBJECT-TYPE
		SYNTAX					 Unsigned32( 0 .. 4294967295 )
		MAX-ACCESS			 read-create
		STATUS					 current
		DESCRIPTION			 " -- "
		::=  { timeSlotTypeEntry  27 }


	timeSlotTypeNeighCell24		 OBJECT-TYPE
		SYNTAX					 Unsigned32( 0 .. 4294967295 )
		MAX-ACCESS			 read-create
		STATUS					 current
		DESCRIPTION			 " -- "
		::=  { timeSlotTypeEntry  28 }


	timeSlotTypeNeighCell25		 OBJECT-TYPE
		SYNTAX					 Unsigned32( 0 .. 4294967295 )
		MAX-ACCESS			 read-create
		STATUS					 current
		DESCRIPTION			 " -- "
		::=  { timeSlotTypeEntry  29 }


	timeSlotTypeNeighCell26		 OBJECT-TYPE
		SYNTAX					 Unsigned32( 0 .. 4294967295 )
		MAX-ACCESS			 read-create
		STATUS					 current
		DESCRIPTION			 " -- "
		::=  { timeSlotTypeEntry  30 }


	timeSlotTypeNeighCell27		 OBJECT-TYPE
		SYNTAX					 Unsigned32( 0 .. 4294967295 )
		MAX-ACCESS			 read-create
		STATUS					 current
		DESCRIPTION			 " -- "
		::=  { timeSlotTypeEntry  31 }


	timeSlotTypeNeighCell28		 OBJECT-TYPE
		SYNTAX					 Unsigned32( 0 .. 4294967295 )
		MAX-ACCESS			 read-create
		STATUS					 current
		DESCRIPTION			 " -- "
		::=  { timeSlotTypeEntry  32 }


	timeSlotTypeNeighCell29		 OBJECT-TYPE
		SYNTAX					 Unsigned32( 0 .. 4294967295 )
		MAX-ACCESS			 read-create
		STATUS					 current
		DESCRIPTION			 " -- "
		::=  { timeSlotTypeEntry  33 }


	timeSlotTypeNeighCell30		 OBJECT-TYPE
		SYNTAX					 Unsigned32( 0 .. 4294967295 )
		MAX-ACCESS			 read-create
		STATUS					 current
		DESCRIPTION			 " -- "
		::=  { timeSlotTypeEntry  34 }


	timeSlotTypeNeighCell31		 OBJECT-TYPE
		SYNTAX					 Unsigned32( 0 .. 4294967295 )
		MAX-ACCESS			 read-create
		STATUS					 current
		DESCRIPTION			 " -- "
		::=  { timeSlotTypeEntry  35 }


	energySaving		 OBJECT IDENTIFIER
		::=  { networkElementLayoutPlan  101 }


	closeTimeSlot		 OBJECT IDENTIFIER
		::=  { energySaving  1 }


	closeTimeSlotCommon		 OBJECT IDENTIFIER
		::=  { closeTimeSlot  1 }


	closeDownTimeSlotSwitch		 OBJECT-TYPE
		SYNTAX					 INTEGER{ off(0),on(1)  }
		MAX-ACCESS			 read-write
		STATUS					 current
		DESCRIPTION			 " -- "
		::=  { closeTimeSlotCommon  1 }


	closeDownTimeSlotStartTime		 OBJECT-TYPE
		SYNTAX					 DateAndTime
		MAX-ACCESS			 read-write
		STATUS					 current
		DESCRIPTION			 " -- "
		::=  { closeTimeSlotCommon  2 }


	closeDownTimeSlotEndTime		 OBJECT-TYPE
		SYNTAX					 DateAndTime
		MAX-ACCESS			 read-write
		STATUS					 current
		DESCRIPTION			 " -- "
		::=  { closeTimeSlotCommon  3 }


	powerManagement		 OBJECT IDENTIFIER
		::=  { energySaving  2 }


	devicePowerManagement		 OBJECT IDENTIFIER
		::=  { powerManagement  1 }


	bbuPowerManagement		 OBJECT IDENTIFIER
		::=  { devicePowerManagement  1 }


	bbuPowerOffPolicySwitch		 OBJECT-TYPE
		SYNTAX					 INTEGER{ off(0),on(1)  }
		MAX-ACCESS			 read-write
		STATUS					 current
		DESCRIPTION			 " -- "
		::=  { bbuPowerManagement  1 }


	bbuPowerOffScheduleStartTime		 OBJECT-TYPE
		SYNTAX					 DateAndTime
		MAX-ACCESS			 read-write
		STATUS					 current
		DESCRIPTION			 " -- "
		::=  { bbuPowerManagement  2 }


	bbuPowerOffScheduleEndTime		 OBJECT-TYPE
		SYNTAX					 DateAndTime
		MAX-ACCESS			 read-write
		STATUS					 current
		DESCRIPTION			 " -- "
		::=  { bbuPowerManagement  3 }


	bbuDCAEnableThreshold		 OBJECT-TYPE
		SYNTAX					 Integer32( 1 .. 3 )
		MAX-ACCESS			 read-write
		STATUS					 current
		DESCRIPTION			 " -- "
		::=  { bbuPowerManagement  4 }


	bbuWaitDCARegulateResultTimer		 OBJECT-TYPE
		SYNTAX					 Unsigned32( 0 .. 65535 )
		MAX-ACCESS			 read-write
		STATUS					 current
		DESCRIPTION			 " -- "
		::=  { bbuPowerManagement  5 }


	bbuDCARegulateSwitch		 OBJECT-TYPE
		SYNTAX					 INTEGER{ off(0),on(1)  }
		MAX-ACCESS			 read-write
		STATUS					 current
		DESCRIPTION			 " -- "
		::=  { bbuPowerManagement  6 }


	eNBPerformanceManagement		 OBJECT IDENTIFIER
		::=  { eNB  100 }


	pmCounterGrpInfo		 OBJECT IDENTIFIER
		::=  { eNBPerformanceManagement  1 }


	pmOriginCounterGrpInfo		 OBJECT IDENTIFIER
		::=  { pmCounterGrpInfo  1 }


	rrcrelatedOriginCounter		 OBJECT IDENTIFIER
		::=  { pmOriginCounterGrpInfo  1 }


	rrcConnEstabProcTable		 OBJECT-TYPE
		SYNTAX					 SEQUENCE  OF	 RrcConnEstabProcEntry
		MAX-ACCESS			 not-accessible
		STATUS					 current
		DESCRIPTION			 " -- "
		::=  { rrcrelatedOriginCounter  1 }


	rrcConnEstabProcEntry		 OBJECT-TYPE
		SYNTAX					 RrcConnEstabProcEntry
		MAX-ACCESS			 not-accessible
		STATUS					 current
		DESCRIPTION			 " -- "
		INDEX						{ rrcConnEstabProcLcId }
		::=  { rrcConnEstabProcTable  1 }


	RrcConnEstabProcEntry		 ::=  SEQUENCE {
		rrcConnEstabProcLcId					Integer32,
		rrcConnEstabProcRowStatus					RowStatus,
		rrcFailConnEstabMaxUeNum					Counter32,
		rrcFailConnEstabCellOverLoad					Counter32,
		rrcFailConnEstabCellBlock					Counter32,
		rrcFailConnEstabPucchAllocFail					Counter32,
		rrcFailConnEstabSrsAllocFail					Counter32,
		rrcFailConnEstabTpcAllocFail					Counter32,
		rrcFailConnEstabTerminalNoRsp					Counter32,
		rrcFailConnEstabPerEncodeFail					Counter32,
		rrcFailConnEstabParameterError					Counter32,
		rrcFailConnEstabAccessJudgeFail					Counter32,
		rrcFailConnEstabInstAllocFail					Counter32,
		rrcFailConnEstabOthers					Counter32,
		rrcAttConnEstabEmergency					Counter32,
		rrcSuccConnEstabEmergency					Counter32,
		rrcAttConnEstabHighPriorityAccess					Counter32,
		rrcSuccConnEstabHighPriorityAccess					Counter32,
		rrcAttConnEstabMtAccess					Counter32,
		rrcSuccConnEstabMtAccess					Counter32,
		rrcAttConnEstabMoSignalling					Counter32,
		rrcSuccConnEstabMoSignalling					Counter32,
		rrcAttConnEstabMoData					Counter32,
		rrcSuccConnEstabMoData					Counter32,
		rrcConnReleaseCsfb					Counter32,
		rrcRejectConnEstabIllegalUE					Counter32,
		rrcConnReleaseIllegalUE					Counter32,
		rrcConnReleaseRedirectionTo2GMea					Counter32,
		rrcConnReleaseRedirectionTo3GMea					Counter32,
		rrcConnReleaseRedirectionTo2GNoMea					Counter32,
		rrcConnReleaseRedirectionTo3GNoMea					Counter32,
		rrcConnReleaseRedirectionToCdma2000HrpdMea					Counter32,
		rrcConnReleaseRedirectionToCdma2000HrpdNoMea					Counter32,
		rrcConnReleaseRedirectionTo4GLoadBalance					Counter32,
		rrcConnReleaseRedirectionTo3GLoadBalance					Counter32,
		rrcConnReleaseRedirectionTo2GLoadBalance					Counter32,
		rrcConnReleaseRedirectionTo2GRemoteRip					Counter32,
		rrcConnReleaseCsfb3G					Counter32,
		rrcConnReleasePdcpNotRcvSn					Counter32,
		rrcAttConnEstabMoVolte					Counter32,
		rrcSuccConnEstabMoVolte					Counter32
		}


	rrcConnEstabProcLcId		 OBJECT-TYPE
		SYNTAX					 Integer32( 0 .. 23 )
		MAX-ACCESS			 not-accessible
		STATUS					 current
		DESCRIPTION			 " -- "
		::=  { rrcConnEstabProcEntry  1 }


	rrcConnEstabProcRowStatus		 OBJECT-TYPE
		SYNTAX					 RowStatus
		MAX-ACCESS			 read-only
		STATUS					 current
		DESCRIPTION			 " -- "
		::=  { rrcConnEstabProcEntry  2 }


	rrcFailConnEstabMaxUeNum		 OBJECT-TYPE
		SYNTAX					 Counter32
		MAX-ACCESS			 read-only
		STATUS					 current
		DESCRIPTION			 " -- "
		::=  { rrcConnEstabProcEntry  3 }


	rrcFailConnEstabCellOverLoad		 OBJECT-TYPE
		SYNTAX					 Counter32
		MAX-ACCESS			 read-only
		STATUS					 current
		DESCRIPTION			 " -- "
		::=  { rrcConnEstabProcEntry  4 }


	rrcFailConnEstabCellBlock		 OBJECT-TYPE
		SYNTAX					 Counter32
		MAX-ACCESS			 read-only
		STATUS					 current
		DESCRIPTION			 " -- "
		::=  { rrcConnEstabProcEntry  5 }


	rrcFailConnEstabPucchAllocFail		 OBJECT-TYPE
		SYNTAX					 Counter32
		MAX-ACCESS			 read-only
		STATUS					 current
		DESCRIPTION			 " -- "
		::=  { rrcConnEstabProcEntry  6 }


	rrcFailConnEstabSrsAllocFail		 OBJECT-TYPE
		SYNTAX					 Counter32
		MAX-ACCESS			 read-only
		STATUS					 current
		DESCRIPTION			 " -- "
		::=  { rrcConnEstabProcEntry  7 }


	rrcFailConnEstabTpcAllocFail		 OBJECT-TYPE
		SYNTAX					 Counter32
		MAX-ACCESS			 read-only
		STATUS					 current
		DESCRIPTION			 " -- "
		::=  { rrcConnEstabProcEntry  8 }


	rrcFailConnEstabTerminalNoRsp		 OBJECT-TYPE
		SYNTAX					 Counter32
		MAX-ACCESS			 read-only
		STATUS					 current
		DESCRIPTION			 " -- "
		::=  { rrcConnEstabProcEntry  9 }


	rrcFailConnEstabPerEncodeFail		 OBJECT-TYPE
		SYNTAX					 Counter32
		MAX-ACCESS			 read-only
		STATUS					 current
		DESCRIPTION			 " -- "
		::=  { rrcConnEstabProcEntry  10 }


	rrcFailConnEstabParameterError		 OBJECT-TYPE
		SYNTAX					 Counter32
		MAX-ACCESS			 read-only
		STATUS					 current
		DESCRIPTION			 " -- "
		::=  { rrcConnEstabProcEntry  11 }


	rrcFailConnEstabAccessJudgeFail		 OBJECT-TYPE
		SYNTAX					 Counter32
		MAX-ACCESS			 read-only
		STATUS					 current
		DESCRIPTION			 " -- "
		::=  { rrcConnEstabProcEntry  12 }


	rrcFailConnEstabInstAllocFail		 OBJECT-TYPE
		SYNTAX					 Counter32
		MAX-ACCESS			 read-only
		STATUS					 current
		DESCRIPTION			 " -- "
		::=  { rrcConnEstabProcEntry  13 }


	rrcFailConnEstabOthers		 OBJECT-TYPE
		SYNTAX					 Counter32
		MAX-ACCESS			 read-only
		STATUS					 current
		DESCRIPTION			 " -- "
		::=  { rrcConnEstabProcEntry  14 }


	rrcAttConnEstabEmergency		 OBJECT-TYPE
		SYNTAX					 Counter32
		MAX-ACCESS			 read-only
		STATUS					 current
		DESCRIPTION			 " -- "
		::=  { rrcConnEstabProcEntry  15 }


	rrcSuccConnEstabEmergency		 OBJECT-TYPE
		SYNTAX					 Counter32
		MAX-ACCESS			 read-only
		STATUS					 current
		DESCRIPTION			 " -- "
		::=  { rrcConnEstabProcEntry  16 }


	rrcAttConnEstabHighPriorityAccess		 OBJECT-TYPE
		SYNTAX					 Counter32
		MAX-ACCESS			 read-only
		STATUS					 current
		DESCRIPTION			 " -- "
		::=  { rrcConnEstabProcEntry  17 }


	rrcSuccConnEstabHighPriorityAccess		 OBJECT-TYPE
		SYNTAX					 Counter32
		MAX-ACCESS			 read-only
		STATUS					 current
		DESCRIPTION			 " -- "
		::=  { rrcConnEstabProcEntry  18 }


	rrcAttConnEstabMtAccess		 OBJECT-TYPE
		SYNTAX					 Counter32
		MAX-ACCESS			 read-only
		STATUS					 current
		DESCRIPTION			 " -- "
		::=  { rrcConnEstabProcEntry  19 }


	rrcSuccConnEstabMtAccess		 OBJECT-TYPE
		SYNTAX					 Counter32
		MAX-ACCESS			 read-only
		STATUS					 current
		DESCRIPTION			 " -- "
		::=  { rrcConnEstabProcEntry  20 }


	rrcAttConnEstabMoSignalling		 OBJECT-TYPE
		SYNTAX					 Counter32
		MAX-ACCESS			 read-only
		STATUS					 current
		DESCRIPTION			 " -- "
		::=  { rrcConnEstabProcEntry  21 }


	rrcSuccConnEstabMoSignalling		 OBJECT-TYPE
		SYNTAX					 Counter32
		MAX-ACCESS			 read-only
		STATUS					 current
		DESCRIPTION			 " -- "
		::=  { rrcConnEstabProcEntry  22 }


	rrcAttConnEstabMoData		 OBJECT-TYPE
		SYNTAX					 Counter32
		MAX-ACCESS			 read-only
		STATUS					 current
		DESCRIPTION			 " -- "
		::=  { rrcConnEstabProcEntry  23 }


	rrcSuccConnEstabMoData		 OBJECT-TYPE
		SYNTAX					 Counter32
		MAX-ACCESS			 read-only
		STATUS					 current
		DESCRIPTION			 " -- "
		::=  { rrcConnEstabProcEntry  24 }


	rrcConnReleaseCsfb		 OBJECT-TYPE
		SYNTAX					 Counter32
		MAX-ACCESS			 read-only
		STATUS					 current
		DESCRIPTION			 " -- "
		::=  { rrcConnEstabProcEntry  25 }


	rrcRejectConnEstabIllegalUE		 OBJECT-TYPE
		SYNTAX					 Counter32
		MAX-ACCESS			 read-only
		STATUS					 current
		DESCRIPTION			 " -- "
		::=  { rrcConnEstabProcEntry  26 }


	rrcConnReleaseIllegalUE		 OBJECT-TYPE
		SYNTAX					 Counter32
		MAX-ACCESS			 read-only
		STATUS					 current
		DESCRIPTION			 " -- "
		::=  { rrcConnEstabProcEntry  27 }


	rrcConnReleaseRedirectionTo2GMea		 OBJECT-TYPE
		SYNTAX					 Counter32
		MAX-ACCESS			 read-only
		STATUS					 current
		DESCRIPTION			 " -- "
		::=  { rrcConnEstabProcEntry  28 }


	rrcConnReleaseRedirectionTo3GMea		 OBJECT-TYPE
		SYNTAX					 Counter32
		MAX-ACCESS			 read-only
		STATUS					 current
		DESCRIPTION			 " -- "
		::=  { rrcConnEstabProcEntry  29 }


	rrcConnReleaseRedirectionTo2GNoMea		 OBJECT-TYPE
		SYNTAX					 Counter32
		MAX-ACCESS			 read-only
		STATUS					 current
		DESCRIPTION			 " -- "
		::=  { rrcConnEstabProcEntry  30 }


	rrcConnReleaseRedirectionTo3GNoMea		 OBJECT-TYPE
		SYNTAX					 Counter32
		MAX-ACCESS			 read-only
		STATUS					 current
		DESCRIPTION			 " -- "
		::=  { rrcConnEstabProcEntry  31 }


	rrcConnReleaseRedirectionToCdma2000HrpdMea		 OBJECT-TYPE
		SYNTAX					 Counter32
		MAX-ACCESS			 read-only
		STATUS					 current
		DESCRIPTION			 " -- "
		::=  { rrcConnEstabProcEntry  32 }


	rrcConnReleaseRedirectionToCdma2000HrpdNoMea		 OBJECT-TYPE
		SYNTAX					 Counter32
		MAX-ACCESS			 read-only
		STATUS					 current
		DESCRIPTION			 " -- "
		::=  { rrcConnEstabProcEntry  33 }


	rrcConnReleaseRedirectionTo4GLoadBalance		 OBJECT-TYPE
		SYNTAX					 Counter32
		MAX-ACCESS			 read-only
		STATUS					 current
		DESCRIPTION			 " -- "
		::=  { rrcConnEstabProcEntry  34 }


	rrcConnReleaseRedirectionTo3GLoadBalance		 OBJECT-TYPE
		SYNTAX					 Counter32
		MAX-ACCESS			 read-only
		STATUS					 current
		DESCRIPTION			 " -- "
		::=  { rrcConnEstabProcEntry  35 }


	rrcConnReleaseRedirectionTo2GLoadBalance		 OBJECT-TYPE
		SYNTAX					 Counter32
		MAX-ACCESS			 read-only
		STATUS					 current
		DESCRIPTION			 " -- "
		::=  { rrcConnEstabProcEntry  36 }


	rrcConnReleaseRedirectionTo2GRemoteRip		 OBJECT-TYPE
		SYNTAX					 Counter32
		MAX-ACCESS			 read-only
		STATUS					 current
		DESCRIPTION			 " -- "
		::=  { rrcConnEstabProcEntry  37 }


	rrcConnReleaseCsfb3G		 OBJECT-TYPE
		SYNTAX					 Counter32
		MAX-ACCESS			 read-only
		STATUS					 current
		DESCRIPTION			 " -- "
		::=  { rrcConnEstabProcEntry  38 }


	rrcConnReleasePdcpNotRcvSn		 OBJECT-TYPE
		SYNTAX					 Counter32
		MAX-ACCESS			 read-only
		STATUS					 current
		DESCRIPTION			 " -- "
		::=  { rrcConnEstabProcEntry  39 }


	rrcAttConnEstabMoVolte		 OBJECT-TYPE
		SYNTAX					 Counter32
		MAX-ACCESS			 read-only
		STATUS					 current
		DESCRIPTION			 " -- "
		::=  { rrcConnEstabProcEntry  40 }


	rrcSuccConnEstabMoVolte		 OBJECT-TYPE
		SYNTAX					 Counter32
		MAX-ACCESS			 read-only
		STATUS					 current
		DESCRIPTION			 " -- "
		::=  { rrcConnEstabProcEntry  41 }


	rrcConnEstabTimeTable		 OBJECT-TYPE
		SYNTAX					 SEQUENCE  OF	 RrcConnEstabTimeEntry
		MAX-ACCESS			 not-accessible
		STATUS					 current
		DESCRIPTION			 " -- "
		::=  { rrcrelatedOriginCounter  2 }


	rrcConnEstabTimeEntry		 OBJECT-TYPE
		SYNTAX					 RrcConnEstabTimeEntry
		MAX-ACCESS			 not-accessible
		STATUS					 current
		DESCRIPTION			 " -- "
		INDEX						{ rrcConnEstabTimeLcId }
		::=  { rrcConnEstabTimeTable  1 }


	RrcConnEstabTimeEntry		 ::=  SEQUENCE {
		rrcConnEstabTimeLcId					Integer32,
		rrcConnEstabTimeRowStatus					RowStatus,
		rrcConnEstabTimeMeanEmergency					Counter32,
		rrcConnEstabTimeMaxEmergency					Counter32,
		rrcConnEstabTimeMeanHighPriorityAccess					Counter32,
		rrcConnEstabTimeMaxHighPriorityAccess					Counter32,
		rrcConnEstabTimeMeanMtAccess					Counter32,
		rrcConnEstabTimeMaxMtAccess					Counter32,
		rrcConnEstabTimeMeanMoSignalling					Counter32,
		rrcConnEstabTimeMaxMoSignalling					Counter32,
		rrcConnEstabTimeMeanMoData					Counter32,
		rrcConnEstabTimeMaxMoData					Counter32,
		rrcConnEstabTimeMax					Counter32,
		rrcConnEstabTimeMean					Counter32
		}


	rrcConnEstabTimeLcId		 OBJECT-TYPE
		SYNTAX					 Integer32( 0 .. 23 )
		MAX-ACCESS			 not-accessible
		STATUS					 current
		DESCRIPTION			 " -- "
		::=  { rrcConnEstabTimeEntry  1 }


	rrcConnEstabTimeRowStatus		 OBJECT-TYPE
		SYNTAX					 RowStatus
		MAX-ACCESS			 read-only
		STATUS					 current
		DESCRIPTION			 " -- "
		::=  { rrcConnEstabTimeEntry  2 }


	rrcConnEstabTimeMeanEmergency		 OBJECT-TYPE
		SYNTAX					 Counter32
		MAX-ACCESS			 read-only
		STATUS					 current
		DESCRIPTION			 " -- "
		::=  { rrcConnEstabTimeEntry  3 }


	rrcConnEstabTimeMaxEmergency		 OBJECT-TYPE
		SYNTAX					 Counter32
		MAX-ACCESS			 read-only
		STATUS					 current
		DESCRIPTION			 " -- "
		::=  { rrcConnEstabTimeEntry  4 }


	rrcConnEstabTimeMeanHighPriorityAccess		 OBJECT-TYPE
		SYNTAX					 Counter32
		MAX-ACCESS			 read-only
		STATUS					 current
		DESCRIPTION			 " -- "
		::=  { rrcConnEstabTimeEntry  5 }


	rrcConnEstabTimeMaxHighPriorityAccess		 OBJECT-TYPE
		SYNTAX					 Counter32
		MAX-ACCESS			 read-only
		STATUS					 current
		DESCRIPTION			 " -- "
		::=  { rrcConnEstabTimeEntry  6 }


	rrcConnEstabTimeMeanMtAccess		 OBJECT-TYPE
		SYNTAX					 Counter32
		MAX-ACCESS			 read-only
		STATUS					 current
		DESCRIPTION			 " -- "
		::=  { rrcConnEstabTimeEntry  7 }


	rrcConnEstabTimeMaxMtAccess		 OBJECT-TYPE
		SYNTAX					 Counter32
		MAX-ACCESS			 read-only
		STATUS					 current
		DESCRIPTION			 " -- "
		::=  { rrcConnEstabTimeEntry  8 }


	rrcConnEstabTimeMeanMoSignalling		 OBJECT-TYPE
		SYNTAX					 Counter32
		MAX-ACCESS			 read-only
		STATUS					 current
		DESCRIPTION			 " -- "
		::=  { rrcConnEstabTimeEntry  9 }


	rrcConnEstabTimeMaxMoSignalling		 OBJECT-TYPE
		SYNTAX					 Counter32
		MAX-ACCESS			 read-only
		STATUS					 current
		DESCRIPTION			 " -- "
		::=  { rrcConnEstabTimeEntry  10 }


	rrcConnEstabTimeMeanMoData		 OBJECT-TYPE
		SYNTAX					 Counter32
		MAX-ACCESS			 read-only
		STATUS					 current
		DESCRIPTION			 " -- "
		::=  { rrcConnEstabTimeEntry  11 }


	rrcConnEstabTimeMaxMoData		 OBJECT-TYPE
		SYNTAX					 Counter32
		MAX-ACCESS			 read-only
		STATUS					 current
		DESCRIPTION			 " -- "
		::=  { rrcConnEstabTimeEntry  12 }


	rrcConnEstabTimeMax		 OBJECT-TYPE
		SYNTAX					 Counter32
		MAX-ACCESS			 read-only
		STATUS					 current
		DESCRIPTION			 " -- "
		::=  { rrcConnEstabTimeEntry  13 }


	rrcConnEstabTimeMean		 OBJECT-TYPE
		SYNTAX					 Counter32
		MAX-ACCESS			 read-only
		STATUS					 current
		DESCRIPTION			 " -- "
		::=  { rrcConnEstabTimeEntry  14 }


	rrcConnReEstabProcTable		 OBJECT-TYPE
		SYNTAX					 SEQUENCE  OF	 RrcConnReEstabProcEntry
		MAX-ACCESS			 not-accessible
		STATUS					 current
		DESCRIPTION			 " -- "
		::=  { rrcrelatedOriginCounter  3 }


	rrcConnReEstabProcEntry		 OBJECT-TYPE
		SYNTAX					 RrcConnReEstabProcEntry
		MAX-ACCESS			 not-accessible
		STATUS					 current
		DESCRIPTION			 " -- "
		INDEX						{ rrcConnReEstabProcLcId }
		::=  { rrcConnReEstabProcTable  1 }


	RrcConnReEstabProcEntry		 ::=  SEQUENCE {
		rrcConnReEstabProcLcId					Integer32,
		rrcConnReEstabProcRowStatus					RowStatus,
		rrcConnReEstabAttRlFail					Counter32,
		rrcConnReEstabSuccRlFail					Counter32,
		rrcConnReEstabAttHandOverFail					Counter32,
		rrcConnReEstabSuccHandOverFail					Counter32,
		rrcConnReEstabAttReConfigFail					Counter32,
		rrcConnReEstabSuccReConfigFail					Counter32,
		rrcConnReEstabFailMaxUeNum					Counter32,
		rrcConnReEstabFailCellOverLoad					Counter32,
		rrcConnReEstabFailPucchAllocFail					Counter32,
		rrcConnReEstabFailSrsAllocFail					Counter32,
		rrcConnReEstabFailTpcAllocFail					Counter32,
		rrcConnReEstabFailTerminalNoRsp					Counter32,
		rrcConnReEstabFailPerEncodeFail					Counter32,
		rrcConnReEstabFailParameterError					Counter32,
		rrcConnReEstabInterEnbAccessJudgeFail					Counter32,
		rrcConnReEstabFailDrbIdAllocFail					Counter32,
		rrcConnReEstabFailSpsFail					Counter32,
		rrcConnReEstabFailInstAllocFail					Counter32,
		rrcConnReEstabFailOthers					Counter32,
		rrcConnReEstabSuccNonSrccell					Counter32,
		rrcConnReEstabInterEnbNoContext					Counter32,
		rrcConnReEstabInterEnbUEContextAtt					Counter32,
		rrcConnReEstabInterEnbUEContextSucc					Counter32,
		rrcConnReEstabInterEnbSucc					Counter32,
		rrcConnReEstabInterEnbFailTerminalNoRsp					Counter32,
		rrcConnReEstabInterEnbScSentRp					Counter32,
		rrcConnReEstabInterEnbScfailMrReCfg					Counter32,
		rrcConnReEstabInterEnbScfailDrbCfg					Counter32,
		rrcConnReEstabInterEnbScfailOther					Counter32
		}


	rrcConnReEstabProcLcId		 OBJECT-TYPE
		SYNTAX					 Integer32( 0 .. 23 )
		MAX-ACCESS			 not-accessible
		STATUS					 current
		DESCRIPTION			 " -- "
		::=  { rrcConnReEstabProcEntry  1 }


	rrcConnReEstabProcRowStatus		 OBJECT-TYPE
		SYNTAX					 RowStatus
		MAX-ACCESS			 read-only
		STATUS					 current
		DESCRIPTION			 " -- "
		::=  { rrcConnReEstabProcEntry  2 }


	rrcConnReEstabAttRlFail		 OBJECT-TYPE
		SYNTAX					 Counter32
		MAX-ACCESS			 read-only
		STATUS					 current
		DESCRIPTION			 " -- "
		::=  { rrcConnReEstabProcEntry  3 }


	rrcConnReEstabSuccRlFail		 OBJECT-TYPE
		SYNTAX					 Counter32
		MAX-ACCESS			 read-only
		STATUS					 current
		DESCRIPTION			 " -- "
		::=  { rrcConnReEstabProcEntry  4 }


	rrcConnReEstabAttHandOverFail		 OBJECT-TYPE
		SYNTAX					 Counter32
		MAX-ACCESS			 read-only
		STATUS					 current
		DESCRIPTION			 " -- "
		::=  { rrcConnReEstabProcEntry  5 }


	rrcConnReEstabSuccHandOverFail		 OBJECT-TYPE
		SYNTAX					 Counter32
		MAX-ACCESS			 read-only
		STATUS					 current
		DESCRIPTION			 " -- "
		::=  { rrcConnReEstabProcEntry  6 }


	rrcConnReEstabAttReConfigFail		 OBJECT-TYPE
		SYNTAX					 Counter32
		MAX-ACCESS			 read-only
		STATUS					 current
		DESCRIPTION			 " -- "
		::=  { rrcConnReEstabProcEntry  7 }


	rrcConnReEstabSuccReConfigFail		 OBJECT-TYPE
		SYNTAX					 Counter32
		MAX-ACCESS			 read-only
		STATUS					 current
		DESCRIPTION			 " -- "
		::=  { rrcConnReEstabProcEntry  8 }


	rrcConnReEstabFailMaxUeNum		 OBJECT-TYPE
		SYNTAX					 Counter32
		MAX-ACCESS			 read-only
		STATUS					 current
		DESCRIPTION			 " -- "
		::=  { rrcConnReEstabProcEntry  9 }


	rrcConnReEstabFailCellOverLoad		 OBJECT-TYPE
		SYNTAX					 Counter32
		MAX-ACCESS			 read-only
		STATUS					 current
		DESCRIPTION			 " -- "
		::=  { rrcConnReEstabProcEntry  10 }


	rrcConnReEstabFailPucchAllocFail		 OBJECT-TYPE
		SYNTAX					 Counter32
		MAX-ACCESS			 read-only
		STATUS					 current
		DESCRIPTION			 " -- "
		::=  { rrcConnReEstabProcEntry  11 }


	rrcConnReEstabFailSrsAllocFail		 OBJECT-TYPE
		SYNTAX					 Counter32
		MAX-ACCESS			 read-only
		STATUS					 current
		DESCRIPTION			 " -- "
		::=  { rrcConnReEstabProcEntry  12 }


	rrcConnReEstabFailTpcAllocFail		 OBJECT-TYPE
		SYNTAX					 Counter32
		MAX-ACCESS			 read-only
		STATUS					 current
		DESCRIPTION			 " -- "
		::=  { rrcConnReEstabProcEntry  13 }


	rrcConnReEstabFailTerminalNoRsp		 OBJECT-TYPE
		SYNTAX					 Counter32
		MAX-ACCESS			 read-only
		STATUS					 current
		DESCRIPTION			 " -- "
		::=  { rrcConnReEstabProcEntry  14 }


	rrcConnReEstabFailPerEncodeFail		 OBJECT-TYPE
		SYNTAX					 Counter32
		MAX-ACCESS			 read-only
		STATUS					 current
		DESCRIPTION			 " -- "
		::=  { rrcConnReEstabProcEntry  15 }


	rrcConnReEstabFailParameterError		 OBJECT-TYPE
		SYNTAX					 Counter32
		MAX-ACCESS			 read-only
		STATUS					 current
		DESCRIPTION			 " -- "
		::=  { rrcConnReEstabProcEntry  16 }


	rrcConnReEstabInterEnbAccessJudgeFail		 OBJECT-TYPE
		SYNTAX					 Counter32
		MAX-ACCESS			 read-only
		STATUS					 current
		DESCRIPTION			 " -- "
		::=  { rrcConnReEstabProcEntry  17 }


	rrcConnReEstabFailDrbIdAllocFail		 OBJECT-TYPE
		SYNTAX					 Counter32
		MAX-ACCESS			 read-only
		STATUS					 current
		DESCRIPTION			 " -- "
		::=  { rrcConnReEstabProcEntry  18 }


	rrcConnReEstabFailSpsFail		 OBJECT-TYPE
		SYNTAX					 Counter32
		MAX-ACCESS			 read-only
		STATUS					 current
		DESCRIPTION			 " -- "
		::=  { rrcConnReEstabProcEntry  19 }


	rrcConnReEstabFailInstAllocFail		 OBJECT-TYPE
		SYNTAX					 Counter32
		MAX-ACCESS			 read-only
		STATUS					 current
		DESCRIPTION			 " -- "
		::=  { rrcConnReEstabProcEntry  20 }


	rrcConnReEstabFailOthers		 OBJECT-TYPE
		SYNTAX					 Counter32
		MAX-ACCESS			 read-only
		STATUS					 current
		DESCRIPTION			 " -- "
		::=  { rrcConnReEstabProcEntry  21 }


	rrcConnReEstabSuccNonSrccell		 OBJECT-TYPE
		SYNTAX					 Counter32
		MAX-ACCESS			 read-only
		STATUS					 current
		DESCRIPTION			 " -- "
		::=  { rrcConnReEstabProcEntry  22 }


	rrcConnReEstabInterEnbNoContext		 OBJECT-TYPE
		SYNTAX					 Counter32
		MAX-ACCESS			 read-only
		STATUS					 current
		DESCRIPTION			 " -- "
		::=  { rrcConnReEstabProcEntry  23 }


	rrcConnReEstabInterEnbUEContextAtt		 OBJECT-TYPE
		SYNTAX					 Counter32
		MAX-ACCESS			 read-only
		STATUS					 current
		DESCRIPTION			 " -- "
		::=  { rrcConnReEstabProcEntry  24 }


	rrcConnReEstabInterEnbUEContextSucc		 OBJECT-TYPE
		SYNTAX					 Counter32
		MAX-ACCESS			 read-only
		STATUS					 current
		DESCRIPTION			 " -- "
		::=  { rrcConnReEstabProcEntry  25 }


	rrcConnReEstabInterEnbSucc		 OBJECT-TYPE
		SYNTAX					 Counter32
		MAX-ACCESS			 read-only
		STATUS					 current
		DESCRIPTION			 " -- "
		::=  { rrcConnReEstabProcEntry  26 }


	rrcConnReEstabInterEnbFailTerminalNoRsp		 OBJECT-TYPE
		SYNTAX					 Counter32
		MAX-ACCESS			 read-only
		STATUS					 current
		DESCRIPTION			 " -- "
		::=  { rrcConnReEstabProcEntry  27 }


	rrcConnReEstabInterEnbScSentRp		 OBJECT-TYPE
		SYNTAX					 Counter32
		MAX-ACCESS			 read-only
		STATUS					 current
		DESCRIPTION			 " -- "
		::=  { rrcConnReEstabProcEntry  28 }


	rrcConnReEstabInterEnbScfailMrReCfg		 OBJECT-TYPE
		SYNTAX					 Counter32
		MAX-ACCESS			 read-only
		STATUS					 current
		DESCRIPTION			 " -- "
		::=  { rrcConnReEstabProcEntry  29 }


	rrcConnReEstabInterEnbScfailDrbCfg		 OBJECT-TYPE
		SYNTAX					 Counter32
		MAX-ACCESS			 read-only
		STATUS					 current
		DESCRIPTION			 " -- "
		::=  { rrcConnReEstabProcEntry  30 }


	rrcConnReEstabInterEnbScfailOther		 OBJECT-TYPE
		SYNTAX					 Counter32
		MAX-ACCESS			 read-only
		STATUS					 current
		DESCRIPTION			 " -- "
		::=  { rrcConnReEstabProcEntry  31 }


	rrcConnNumberTable		 OBJECT-TYPE
		SYNTAX					 SEQUENCE  OF	 RrcConnNumberEntry
		MAX-ACCESS			 not-accessible
		STATUS					 current
		DESCRIPTION			 " -- "
		::=  { rrcrelatedOriginCounter  4 }


	rrcConnNumberEntry		 OBJECT-TYPE
		SYNTAX					 RrcConnNumberEntry
		MAX-ACCESS			 not-accessible
		STATUS					 current
		DESCRIPTION			 " -- "
		INDEX						{ rrcConnNumberLcId }
		::=  { rrcConnNumberTable  1 }


	RrcConnNumberEntry		 ::=  SEQUENCE {
		rrcConnNumberLcId					Integer32,
		rrcConnNumberRowStatus					RowStatus,
		rrcConnMean					Counter32,
		rrcConnMax					Counter32
		}


	rrcConnNumberLcId		 OBJECT-TYPE
		SYNTAX					 Integer32( 0 .. 23 )
		MAX-ACCESS			 not-accessible
		STATUS					 current
		DESCRIPTION			 " -- "
		::=  { rrcConnNumberEntry  1 }


	rrcConnNumberRowStatus		 OBJECT-TYPE
		SYNTAX					 RowStatus
		MAX-ACCESS			 read-only
		STATUS					 current
		DESCRIPTION			 " -- "
		::=  { rrcConnNumberEntry  2 }


	rrcConnMean		 OBJECT-TYPE
		SYNTAX					 Counter32
		MAX-ACCESS			 read-only
		STATUS					 current
		DESCRIPTION			 " -- "
		::=  { rrcConnNumberEntry  3 }


	rrcConnMax		 OBJECT-TYPE
		SYNTAX					 Counter32
		MAX-ACCESS			 read-only
		STATUS					 current
		DESCRIPTION			 " -- "
		::=  { rrcConnNumberEntry  4 }


	rrcConnReconfigProcTable		 OBJECT-TYPE
		SYNTAX					 SEQUENCE  OF	 RrcConnReconfigProcEntry
		MAX-ACCESS			 not-accessible
		STATUS					 current
		DESCRIPTION			 " -- "
		::=  { rrcrelatedOriginCounter  5 }


	rrcConnReconfigProcEntry		 OBJECT-TYPE
		SYNTAX					 RrcConnReconfigProcEntry
		MAX-ACCESS			 not-accessible
		STATUS					 current
		DESCRIPTION			 " -- "
		INDEX						{ rrcConnReconfigProcLcId }
		::=  { rrcConnReconfigProcTable  1 }


	RrcConnReconfigProcEntry		 ::=  SEQUENCE {
		rrcConnReconfigProcLcId					Integer32,
		rrcConnReconfigProcRowStatus					RowStatus,
		rrcAttConnReconfigRabSetup					Counter32,
		rrcSuccConnReconfigRabSetup					Counter32,
		rrcAttConnReconfigRabModify					Counter32,
		rrcSuccConnReconfigRabModify					Counter32,
		rrcAttConnReconfigRabDelete					Counter32,
		rrcSuccConnReconfigRabDelete					Counter32,
		rrcAttConnReconfigMeasCfg					Counter32,
		rrcSuccConnReconfigMeasCfg					Counter32,
		rrcAttConnReconfigHandOverIntraCell					Counter32,
		rrcSuccConnReconfigHandOverIntraCell					Counter32,
		rrcAttConnReconfigSrsCfg					Counter32,
		rrcSuccConnReconfigSrsCfg					Counter32,
		rrcAttConnReconfigTmChange					Counter32,
		rrcSuccConnReconfigTmChange					Counter32,
		rrcAttConnReconfigResReclaim					Counter32,
		rrcSuccConnReconfigResReclaim					Counter32,
		rrcAttConnReconfigRrcReestablish					Counter32,
		rrcSuccConnReconfigRrcReestablish					Counter32,
		rrcFailConnReconfigAmbr					Counter32,
		rrcFailConnReconfigPrb					Counter32,
		rrcFailConnReconfigCellBlock					Counter32,
		rrcFailConnReconfigTpc					Counter32,
		rrcFailConnReconfigDrbID					Counter32,
		rrcFailConnReconfigSPS					Counter32,
		rrcFailConnReconfigLoChID					Counter32,
		rrcFailConnReconfigPucch					Counter32,
		rrcFailConnReconfigSrs					Counter32,
		rrcFailConnReconfigTerminalNoRsp					Counter32,
		rrcFailConnReconfigPerEncodeFail					Counter32,
		rrcFailConnReconfigParameterError					Counter32,
		rrcFailConnReconfigStateError					Counter32,
		rrcFailConnReconfigRlFailure					Counter32,
		rrcFailConnReconfigRrcReestablish					Counter32,
		rrcFailConnReconfigSecurityFailure					Counter32,
		rrcFailConnReconfigAccessJudgeFailure					Counter32,
		rrcFailConnReconfigMobilityFailure					Counter32,
		rrcFailConnReconfigInstAllocFail					Counter32,
		rrcFailConnReconfigOthers					Counter32
		}


	rrcConnReconfigProcLcId		 OBJECT-TYPE
		SYNTAX					 Integer32( 0 .. 23 )
		MAX-ACCESS			 not-accessible
		STATUS					 current
		DESCRIPTION			 " -- "
		::=  { rrcConnReconfigProcEntry  1 }


	rrcConnReconfigProcRowStatus		 OBJECT-TYPE
		SYNTAX					 RowStatus
		MAX-ACCESS			 read-only
		STATUS					 current
		DESCRIPTION			 " -- "
		::=  { rrcConnReconfigProcEntry  2 }


	rrcAttConnReconfigRabSetup		 OBJECT-TYPE
		SYNTAX					 Counter32
		MAX-ACCESS			 read-only
		STATUS					 current
		DESCRIPTION			 " -- "
		::=  { rrcConnReconfigProcEntry  3 }


	rrcSuccConnReconfigRabSetup		 OBJECT-TYPE
		SYNTAX					 Counter32
		MAX-ACCESS			 read-only
		STATUS					 current
		DESCRIPTION			 " -- "
		::=  { rrcConnReconfigProcEntry  4 }


	rrcAttConnReconfigRabModify		 OBJECT-TYPE
		SYNTAX					 Counter32
		MAX-ACCESS			 read-only
		STATUS					 current
		DESCRIPTION			 " -- "
		::=  { rrcConnReconfigProcEntry  5 }


	rrcSuccConnReconfigRabModify		 OBJECT-TYPE
		SYNTAX					 Counter32
		MAX-ACCESS			 read-only
		STATUS					 current
		DESCRIPTION			 " -- "
		::=  { rrcConnReconfigProcEntry  6 }


	rrcAttConnReconfigRabDelete		 OBJECT-TYPE
		SYNTAX					 Counter32
		MAX-ACCESS			 read-only
		STATUS					 current
		DESCRIPTION			 " -- "
		::=  { rrcConnReconfigProcEntry  7 }


	rrcSuccConnReconfigRabDelete		 OBJECT-TYPE
		SYNTAX					 Counter32
		MAX-ACCESS			 read-only
		STATUS					 current
		DESCRIPTION			 " -- "
		::=  { rrcConnReconfigProcEntry  8 }


	rrcAttConnReconfigMeasCfg		 OBJECT-TYPE
		SYNTAX					 Counter32
		MAX-ACCESS			 read-only
		STATUS					 current
		DESCRIPTION			 " -- "
		::=  { rrcConnReconfigProcEntry  9 }


	rrcSuccConnReconfigMeasCfg		 OBJECT-TYPE
		SYNTAX					 Counter32
		MAX-ACCESS			 read-only
		STATUS					 current
		DESCRIPTION			 " -- "
		::=  { rrcConnReconfigProcEntry  10 }


	rrcAttConnReconfigHandOverIntraCell		 OBJECT-TYPE
		SYNTAX					 Counter32
		MAX-ACCESS			 read-only
		STATUS					 current
		DESCRIPTION			 " -- "
		::=  { rrcConnReconfigProcEntry  11 }


	rrcSuccConnReconfigHandOverIntraCell		 OBJECT-TYPE
		SYNTAX					 Counter32
		MAX-ACCESS			 read-only
		STATUS					 current
		DESCRIPTION			 " -- "
		::=  { rrcConnReconfigProcEntry  12 }


	rrcAttConnReconfigSrsCfg		 OBJECT-TYPE
		SYNTAX					 Counter32
		MAX-ACCESS			 read-only
		STATUS					 current
		DESCRIPTION			 " -- "
		::=  { rrcConnReconfigProcEntry  13 }


	rrcSuccConnReconfigSrsCfg		 OBJECT-TYPE
		SYNTAX					 Counter32
		MAX-ACCESS			 read-only
		STATUS					 current
		DESCRIPTION			 " -- "
		::=  { rrcConnReconfigProcEntry  14 }


	rrcAttConnReconfigTmChange		 OBJECT-TYPE
		SYNTAX					 Counter32
		MAX-ACCESS			 read-only
		STATUS					 current
		DESCRIPTION			 " -- "
		::=  { rrcConnReconfigProcEntry  15 }


	rrcSuccConnReconfigTmChange		 OBJECT-TYPE
		SYNTAX					 Counter32
		MAX-ACCESS			 read-only
		STATUS					 current
		DESCRIPTION			 " -- "
		::=  { rrcConnReconfigProcEntry  16 }


	rrcAttConnReconfigResReclaim		 OBJECT-TYPE
		SYNTAX					 Counter32
		MAX-ACCESS			 read-only
		STATUS					 current
		DESCRIPTION			 " -- "
		::=  { rrcConnReconfigProcEntry  17 }


	rrcSuccConnReconfigResReclaim		 OBJECT-TYPE
		SYNTAX					 Counter32
		MAX-ACCESS			 read-only
		STATUS					 current
		DESCRIPTION			 " -- "
		::=  { rrcConnReconfigProcEntry  18 }


	rrcAttConnReconfigRrcReestablish		 OBJECT-TYPE
		SYNTAX					 Counter32
		MAX-ACCESS			 read-only
		STATUS					 current
		DESCRIPTION			 " -- "
		::=  { rrcConnReconfigProcEntry  19 }


	rrcSuccConnReconfigRrcReestablish		 OBJECT-TYPE
		SYNTAX					 Counter32
		MAX-ACCESS			 read-only
		STATUS					 current
		DESCRIPTION			 " -- "
		::=  { rrcConnReconfigProcEntry  20 }


	rrcFailConnReconfigAmbr		 OBJECT-TYPE
		SYNTAX					 Counter32
		MAX-ACCESS			 read-only
		STATUS					 current
		DESCRIPTION			 " -- "
		::=  { rrcConnReconfigProcEntry  21 }


	rrcFailConnReconfigPrb		 OBJECT-TYPE
		SYNTAX					 Counter32
		MAX-ACCESS			 read-only
		STATUS					 current
		DESCRIPTION			 " -- "
		::=  { rrcConnReconfigProcEntry  22 }


	rrcFailConnReconfigCellBlock		 OBJECT-TYPE
		SYNTAX					 Counter32
		MAX-ACCESS			 read-only
		STATUS					 current
		DESCRIPTION			 " -- "
		::=  { rrcConnReconfigProcEntry  23 }


	rrcFailConnReconfigTpc		 OBJECT-TYPE
		SYNTAX					 Counter32
		MAX-ACCESS			 read-only
		STATUS					 current
		DESCRIPTION			 " -- "
		::=  { rrcConnReconfigProcEntry  24 }


	rrcFailConnReconfigDrbID		 OBJECT-TYPE
		SYNTAX					 Counter32
		MAX-ACCESS			 read-only
		STATUS					 current
		DESCRIPTION			 " -- "
		::=  { rrcConnReconfigProcEntry  25 }


	rrcFailConnReconfigSPS		 OBJECT-TYPE
		SYNTAX					 Counter32
		MAX-ACCESS			 read-only
		STATUS					 current
		DESCRIPTION			 " -- "
		::=  { rrcConnReconfigProcEntry  26 }


	rrcFailConnReconfigLoChID		 OBJECT-TYPE
		SYNTAX					 Counter32
		MAX-ACCESS			 read-only
		STATUS					 current
		DESCRIPTION			 " -- "
		::=  { rrcConnReconfigProcEntry  27 }


	rrcFailConnReconfigPucch		 OBJECT-TYPE
		SYNTAX					 Counter32
		MAX-ACCESS			 read-only
		STATUS					 current
		DESCRIPTION			 " -- "
		::=  { rrcConnReconfigProcEntry  28 }


	rrcFailConnReconfigSrs		 OBJECT-TYPE
		SYNTAX					 Counter32
		MAX-ACCESS			 read-only
		STATUS					 current
		DESCRIPTION			 " -- "
		::=  { rrcConnReconfigProcEntry  29 }


	rrcFailConnReconfigTerminalNoRsp		 OBJECT-TYPE
		SYNTAX					 Counter32
		MAX-ACCESS			 read-only
		STATUS					 current
		DESCRIPTION			 " -- "
		::=  { rrcConnReconfigProcEntry  30 }


	rrcFailConnReconfigPerEncodeFail		 OBJECT-TYPE
		SYNTAX					 Counter32
		MAX-ACCESS			 read-only
		STATUS					 current
		DESCRIPTION			 " -- "
		::=  { rrcConnReconfigProcEntry  31 }


	rrcFailConnReconfigParameterError		 OBJECT-TYPE
		SYNTAX					 Counter32
		MAX-ACCESS			 read-only
		STATUS					 current
		DESCRIPTION			 " -- "
		::=  { rrcConnReconfigProcEntry  32 }


	rrcFailConnReconfigStateError		 OBJECT-TYPE
		SYNTAX					 Counter32
		MAX-ACCESS			 read-only
		STATUS					 current
		DESCRIPTION			 " -- "
		::=  { rrcConnReconfigProcEntry  33 }


	rrcFailConnReconfigRlFailure		 OBJECT-TYPE
		SYNTAX					 Counter32
		MAX-ACCESS			 read-only
		STATUS					 current
		DESCRIPTION			 " -- "
		::=  { rrcConnReconfigProcEntry  34 }


	rrcFailConnReconfigRrcReestablish		 OBJECT-TYPE
		SYNTAX					 Counter32
		MAX-ACCESS			 read-only
		STATUS					 current
		DESCRIPTION			 " -- "
		::=  { rrcConnReconfigProcEntry  35 }


	rrcFailConnReconfigSecurityFailure		 OBJECT-TYPE
		SYNTAX					 Counter32
		MAX-ACCESS			 read-only
		STATUS					 current
		DESCRIPTION			 " -- "
		::=  { rrcConnReconfigProcEntry  36 }


	rrcFailConnReconfigAccessJudgeFailure		 OBJECT-TYPE
		SYNTAX					 Counter32
		MAX-ACCESS			 read-only
		STATUS					 current
		DESCRIPTION			 " -- "
		::=  { rrcConnReconfigProcEntry  37 }


	rrcFailConnReconfigMobilityFailure		 OBJECT-TYPE
		SYNTAX					 Counter32
		MAX-ACCESS			 read-only
		STATUS					 current
		DESCRIPTION			 " -- "
		::=  { rrcConnReconfigProcEntry  38 }


	rrcFailConnReconfigInstAllocFail		 OBJECT-TYPE
		SYNTAX					 Counter32
		MAX-ACCESS			 read-only
		STATUS					 current
		DESCRIPTION			 " -- "
		::=  { rrcConnReconfigProcEntry  39 }


	rrcFailConnReconfigOthers		 OBJECT-TYPE
		SYNTAX					 Counter32
		MAX-ACCESS			 read-only
		STATUS					 current
		DESCRIPTION			 " -- "
		::=  { rrcConnReconfigProcEntry  40 }


	rbEstabProcTable		 OBJECT-TYPE
		SYNTAX					 SEQUENCE  OF	 RbEstabProcEntry
		MAX-ACCESS			 not-accessible
		STATUS					 current
		DESCRIPTION			 " -- "
		::=  { rrcrelatedOriginCounter  6 }


	rbEstabProcEntry		 OBJECT-TYPE
		SYNTAX					 RbEstabProcEntry
		MAX-ACCESS			 not-accessible
		STATUS					 current
		DESCRIPTION			 " -- "
		INDEX						{ rbEstabProcLcId }
		::=  { rbEstabProcTable  1 }


	RbEstabProcEntry		 ::=  SEQUENCE {
		rbEstabProcLcId					Integer32,
		rbEstabProcRowStatus					RowStatus,
		rbFailEstabRej					Counter32,
		rbFailEstabReEstab					Counter32,
		rbFailEstabNoReply					Counter32,
		rbFailEstabIntraEnbError					Counter32,
		rbAttEstabQci1					Counter32,
		rbSuccEstabQci1					Counter32,
		rbAttEstabQci2					Counter32,
		rbSuccEstabQci2					Counter32,
		rbAttEstabQci3					Counter32,
		rbSuccEstabQci3					Counter32,
		rbAttEstabQci4					Counter32,
		rbSuccEstabQci4					Counter32,
		rbAttEstabQci5					Counter32,
		rbSuccEstabQci5					Counter32,
		rbAttEstabQci6					Counter32,
		rbSuccEstabQci6					Counter32,
		rbAttEstabQci7					Counter32,
		rbSuccEstabQci7					Counter32,
		rbAttEstabQci8					Counter32,
		rbSuccEstabQci8					Counter32,
		rbAttEstabQci9					Counter32,
		rbSuccEstabQci9					Counter32
		}


	rbEstabProcLcId		 OBJECT-TYPE
		SYNTAX					 Integer32( 0 .. 23 )
		MAX-ACCESS			 not-accessible
		STATUS					 current
		DESCRIPTION			 " -- "
		::=  { rbEstabProcEntry  1 }


	rbEstabProcRowStatus		 OBJECT-TYPE
		SYNTAX					 RowStatus
		MAX-ACCESS			 read-only
		STATUS					 current
		DESCRIPTION			 " -- "
		::=  { rbEstabProcEntry  2 }


	rbFailEstabRej		 OBJECT-TYPE
		SYNTAX					 Counter32
		MAX-ACCESS			 read-only
		STATUS					 current
		DESCRIPTION			 " -- "
		::=  { rbEstabProcEntry  3 }


	rbFailEstabReEstab		 OBJECT-TYPE
		SYNTAX					 Counter32
		MAX-ACCESS			 read-only
		STATUS					 current
		DESCRIPTION			 " -- "
		::=  { rbEstabProcEntry  4 }


	rbFailEstabNoReply		 OBJECT-TYPE
		SYNTAX					 Counter32
		MAX-ACCESS			 read-only
		STATUS					 current
		DESCRIPTION			 " -- "
		::=  { rbEstabProcEntry  5 }


	rbFailEstabIntraEnbError		 OBJECT-TYPE
		SYNTAX					 Counter32
		MAX-ACCESS			 read-only
		STATUS					 current
		DESCRIPTION			 " -- "
		::=  { rbEstabProcEntry  6 }


	rbAttEstabQci1		 OBJECT-TYPE
		SYNTAX					 Counter32
		MAX-ACCESS			 read-only
		STATUS					 current
		DESCRIPTION			 " -- "
		::=  { rbEstabProcEntry  7 }


	rbSuccEstabQci1		 OBJECT-TYPE
		SYNTAX					 Counter32
		MAX-ACCESS			 read-only
		STATUS					 current
		DESCRIPTION			 " -- "
		::=  { rbEstabProcEntry  8 }


	rbAttEstabQci2		 OBJECT-TYPE
		SYNTAX					 Counter32
		MAX-ACCESS			 read-only
		STATUS					 current
		DESCRIPTION			 " -- "
		::=  { rbEstabProcEntry  9 }


	rbSuccEstabQci2		 OBJECT-TYPE
		SYNTAX					 Counter32
		MAX-ACCESS			 read-only
		STATUS					 current
		DESCRIPTION			 " -- "
		::=  { rbEstabProcEntry  10 }


	rbAttEstabQci3		 OBJECT-TYPE
		SYNTAX					 Counter32
		MAX-ACCESS			 read-only
		STATUS					 current
		DESCRIPTION			 " -- "
		::=  { rbEstabProcEntry  11 }


	rbSuccEstabQci3		 OBJECT-TYPE
		SYNTAX					 Counter32
		MAX-ACCESS			 read-only
		STATUS					 current
		DESCRIPTION			 " -- "
		::=  { rbEstabProcEntry  12 }


	rbAttEstabQci4		 OBJECT-TYPE
		SYNTAX					 Counter32
		MAX-ACCESS			 read-only
		STATUS					 current
		DESCRIPTION			 " -- "
		::=  { rbEstabProcEntry  13 }


	rbSuccEstabQci4		 OBJECT-TYPE
		SYNTAX					 Counter32
		MAX-ACCESS			 read-only
		STATUS					 current
		DESCRIPTION			 " -- "
		::=  { rbEstabProcEntry  14 }


	rbAttEstabQci5		 OBJECT-TYPE
		SYNTAX					 Counter32
		MAX-ACCESS			 read-only
		STATUS					 current
		DESCRIPTION			 " -- "
		::=  { rbEstabProcEntry  15 }


	rbSuccEstabQci5		 OBJECT-TYPE
		SYNTAX					 Counter32
		MAX-ACCESS			 read-only
		STATUS					 current
		DESCRIPTION			 " -- "
		::=  { rbEstabProcEntry  16 }


	rbAttEstabQci6		 OBJECT-TYPE
		SYNTAX					 Counter32
		MAX-ACCESS			 read-only
		STATUS					 current
		DESCRIPTION			 " -- "
		::=  { rbEstabProcEntry  17 }


	rbSuccEstabQci6		 OBJECT-TYPE
		SYNTAX					 Counter32
		MAX-ACCESS			 read-only
		STATUS					 current
		DESCRIPTION			 " -- "
		::=  { rbEstabProcEntry  18 }


	rbAttEstabQci7		 OBJECT-TYPE
		SYNTAX					 Counter32
		MAX-ACCESS			 read-only
		STATUS					 current
		DESCRIPTION			 " -- "
		::=  { rbEstabProcEntry  19 }


	rbSuccEstabQci7		 OBJECT-TYPE
		SYNTAX					 Counter32
		MAX-ACCESS			 read-only
		STATUS					 current
		DESCRIPTION			 " -- "
		::=  { rbEstabProcEntry  20 }


	rbAttEstabQci8		 OBJECT-TYPE
		SYNTAX					 Counter32
		MAX-ACCESS			 read-only
		STATUS					 current
		DESCRIPTION			 " -- "
		::=  { rbEstabProcEntry  21 }


	rbSuccEstabQci8		 OBJECT-TYPE
		SYNTAX					 Counter32
		MAX-ACCESS			 read-only
		STATUS					 current
		DESCRIPTION			 " -- "
		::=  { rbEstabProcEntry  22 }


	rbAttEstabQci9		 OBJECT-TYPE
		SYNTAX					 Counter32
		MAX-ACCESS			 read-only
		STATUS					 current
		DESCRIPTION			 " -- "
		::=  { rbEstabProcEntry  23 }


	rbSuccEstabQci9		 OBJECT-TYPE
		SYNTAX					 Counter32
		MAX-ACCESS			 read-only
		STATUS					 current
		DESCRIPTION			 " -- "
		::=  { rbEstabProcEntry  24 }


	s1HandOverProcInterEnbTable		 OBJECT-TYPE
		SYNTAX					 SEQUENCE  OF	 S1HandOverProcInterEnbEntry
		MAX-ACCESS			 not-accessible
		STATUS					 current
		DESCRIPTION			 " -- "
		::=  { rrcrelatedOriginCounter  7 }


	s1HandOverProcInterEnbEntry		 OBJECT-TYPE
		SYNTAX					 S1HandOverProcInterEnbEntry
		MAX-ACCESS			 not-accessible
		STATUS					 current
		DESCRIPTION			 " -- "
		INDEX						{ s1HandOverProcInterEnbLcId }
		::=  { s1HandOverProcInterEnbTable  1 }


	S1HandOverProcInterEnbEntry		 ::=  SEQUENCE {
		s1HandOverProcInterEnbLcId					Integer32,
		s1HandOverProcInterEnbRowStatus					RowStatus,
		hoAttOutIntraFreqS1					Counter32,
		hoSuccPrepOutIntraFreqS1					Counter32,
		hoSuccOutIntraFreqS1					Counter32,
		hoAttOutInterFreqS1					Counter32,
		hoSuccPrepOutInterFreqS1					Counter32,
		hoSuccOutInterFreqS1					Counter32,
		hoFailPrepOutIntraFreqS1Fail					Counter32,
		hoFailPrepOutIntraFreqS1NoRsp					Counter32,
		hoFailPrepOutInterFreqS1Fail					Counter32,
		hoFailPrepOutInterFreqS1NoRsp					Counter32,
		hoSuccPrepOutIntraFreqS1PartialHandover					Counter32,
		hoSuccPrepOutInterFreqS1PartialHandover					Counter32,
		hoFailOutIntraFreqS1NoRsp					Counter32,
		hoFailOutInterFreqS1NoRsp					Counter32,
		hoAttIncIntraFreqS1					Counter32,
		hoSuccPrepIncIntraFreqS1					Counter32,
		hoSuccIncIntraFreqS1					Counter32,
		hoAttIncInterFreqS1					Counter32,
		hoSuccPrepIncInterFreqS1					Counter32,
		hoSuccIncInterFreqS1					Counter32,
		hoFailPrepIncIntraFreqS1MaxUeNum					Counter32,
		hoFailPrepIncIntraFreqS1CellOverLoad					Counter32,
		hoFailPrepIncIntraFreqS1Prb					Counter32,
		hoFailPrepIncIntraFreqS1HandoverRestrictList					Counter32,
		hoFailPrepIncIntraFreqS1CellBlock					Counter32,
		hoFailPrepIncIntraFreqS1Tpc					Counter32,
		hoFailPrepIncIntraFreqS1DrbID					Counter32,
		hoFailPrepIncIntraFreqS1SPS					Counter32,
		hoFailPrepIncIntraFreqS1LoChID					Counter32,
		hoFailPrepIncIntraFreqS1Pucch					Counter32,
		hoFailPrepIncIntraFreqS1Srs					Counter32,
		hoFailPrepIncIntraFreqS1PerEncodeFail					Counter32,
		hoFailPrepIncIntraFreqS1PerDecodeFail					Counter32,
		hoFailPrepIncIntraFreqS1SecurityFailure					Counter32,
		hoFailPrepIncIntraFreqS1ParameterError					Counter32,
		hoFailPrepIncIntraFreqS1Others					Counter32,
		hoFailPrepIncInterFreqS1MaxUeNum					Counter32,
		hoFailPrepIncInterFreqS1CellOverLoad					Counter32,
		hoFailPrepIncInterFreqS1Prb					Counter32,
		hoFailPrepIncInterFreqS1HandoverRestrictList					Counter32,
		hoFailPrepIncInterFreqS1CellBlock					Counter32,
		hoFailPrepIncInterFreqS1Tpc					Counter32,
		hoFailPrepIncInterFreqS1DrbID					Counter32,
		hoFailPrepIncInterFreqS1SPS					Counter32,
		hoFailPrepIncInterFreqS1LoChID					Counter32,
		hoFailPrepIncInterFreqS1Pucch					Counter32,
		hoFailPrepIncInterFreqS1Srs					Counter32,
		hoFailPrepIncInterFreqS1PerEncodeFail					Counter32,
		hoFailPrepIncInterFreqS1PerDecodeFail					Counter32,
		hoFailPrepIncInterFreqS1SecurityFailure					Counter32,
		hoFailPrepIncInterFreqS1ParameterError					Counter32,
		hoFailPrepIncInterFreqS1Others					Counter32,
		hoSucOutIntraFreqS1					Counter32,
		hoSucOutInterFreqS1					Counter32,
		hoAttOutExecIntraFreqS1					Counter32,
		hoAttOutExecInterFreqS1					Counter32,
		hoAttOutPrepIntraFreqS1					Counter32,
		hoAttOutPrepInterFreqS1					Counter32,
		hoFailPrepOutIntraFreqS1SourceFail					Counter32,
		hoFailPrepOutInterFreqS1SourceFail					Counter32
		}


	s1HandOverProcInterEnbLcId		 OBJECT-TYPE
		SYNTAX					 Integer32( 0 .. 23 )
		MAX-ACCESS			 not-accessible
		STATUS					 current
		DESCRIPTION			 " -- "
		::=  { s1HandOverProcInterEnbEntry  1 }


	s1HandOverProcInterEnbRowStatus		 OBJECT-TYPE
		SYNTAX					 RowStatus
		MAX-ACCESS			 read-only
		STATUS					 current
		DESCRIPTION			 " -- "
		::=  { s1HandOverProcInterEnbEntry  2 }


	hoAttOutIntraFreqS1		 OBJECT-TYPE
		SYNTAX					 Counter32
		MAX-ACCESS			 read-only
		STATUS					 current
		DESCRIPTION			 " -- "
		::=  { s1HandOverProcInterEnbEntry  3 }


	hoSuccPrepOutIntraFreqS1		 OBJECT-TYPE
		SYNTAX					 Counter32
		MAX-ACCESS			 read-only
		STATUS					 current
		DESCRIPTION			 " -- "
		::=  { s1HandOverProcInterEnbEntry  4 }


	hoSuccOutIntraFreqS1		 OBJECT-TYPE
		SYNTAX					 Counter32
		MAX-ACCESS			 read-only
		STATUS					 current
		DESCRIPTION			 " -- "
		::=  { s1HandOverProcInterEnbEntry  5 }


	hoAttOutInterFreqS1		 OBJECT-TYPE
		SYNTAX					 Counter32
		MAX-ACCESS			 read-only
		STATUS					 current
		DESCRIPTION			 " -- "
		::=  { s1HandOverProcInterEnbEntry  6 }


	hoSuccPrepOutInterFreqS1		 OBJECT-TYPE
		SYNTAX					 Counter32
		MAX-ACCESS			 read-only
		STATUS					 current
		DESCRIPTION			 " -- "
		::=  { s1HandOverProcInterEnbEntry  7 }


	hoSuccOutInterFreqS1		 OBJECT-TYPE
		SYNTAX					 Counter32
		MAX-ACCESS			 read-only
		STATUS					 current
		DESCRIPTION			 " -- "
		::=  { s1HandOverProcInterEnbEntry  8 }


	hoFailPrepOutIntraFreqS1Fail		 OBJECT-TYPE
		SYNTAX					 Counter32
		MAX-ACCESS			 read-only
		STATUS					 current
		DESCRIPTION			 " -- "
		::=  { s1HandOverProcInterEnbEntry  9 }


	hoFailPrepOutIntraFreqS1NoRsp		 OBJECT-TYPE
		SYNTAX					 Counter32
		MAX-ACCESS			 read-only
		STATUS					 current
		DESCRIPTION			 " -- "
		::=  { s1HandOverProcInterEnbEntry  10 }


	hoFailPrepOutInterFreqS1Fail		 OBJECT-TYPE
		SYNTAX					 Counter32
		MAX-ACCESS			 read-only
		STATUS					 current
		DESCRIPTION			 " -- "
		::=  { s1HandOverProcInterEnbEntry  11 }


	hoFailPrepOutInterFreqS1NoRsp		 OBJECT-TYPE
		SYNTAX					 Counter32
		MAX-ACCESS			 read-only
		STATUS					 current
		DESCRIPTION			 " -- "
		::=  { s1HandOverProcInterEnbEntry  12 }


	hoSuccPrepOutIntraFreqS1PartialHandover		 OBJECT-TYPE
		SYNTAX					 Counter32
		MAX-ACCESS			 read-only
		STATUS					 current
		DESCRIPTION			 " -- "
		::=  { s1HandOverProcInterEnbEntry  13 }


	hoSuccPrepOutInterFreqS1PartialHandover		 OBJECT-TYPE
		SYNTAX					 Counter32
		MAX-ACCESS			 read-only
		STATUS					 current
		DESCRIPTION			 " -- "
		::=  { s1HandOverProcInterEnbEntry  14 }


	hoFailOutIntraFreqS1NoRsp		 OBJECT-TYPE
		SYNTAX					 Counter32
		MAX-ACCESS			 read-only
		STATUS					 current
		DESCRIPTION			 " -- "
		::=  { s1HandOverProcInterEnbEntry  15 }


	hoFailOutInterFreqS1NoRsp		 OBJECT-TYPE
		SYNTAX					 Counter32
		MAX-ACCESS			 read-only
		STATUS					 current
		DESCRIPTION			 " -- "
		::=  { s1HandOverProcInterEnbEntry  16 }


	hoAttIncIntraFreqS1		 OBJECT-TYPE
		SYNTAX					 Counter32
		MAX-ACCESS			 read-only
		STATUS					 current
		DESCRIPTION			 " -- "
		::=  { s1HandOverProcInterEnbEntry  17 }


	hoSuccPrepIncIntraFreqS1		 OBJECT-TYPE
		SYNTAX					 Counter32
		MAX-ACCESS			 read-only
		STATUS					 current
		DESCRIPTION			 " -- "
		::=  { s1HandOverProcInterEnbEntry  18 }


	hoSuccIncIntraFreqS1		 OBJECT-TYPE
		SYNTAX					 Counter32
		MAX-ACCESS			 read-only
		STATUS					 current
		DESCRIPTION			 " -- "
		::=  { s1HandOverProcInterEnbEntry  19 }


	hoAttIncInterFreqS1		 OBJECT-TYPE
		SYNTAX					 Counter32
		MAX-ACCESS			 read-only
		STATUS					 current
		DESCRIPTION			 " -- "
		::=  { s1HandOverProcInterEnbEntry  20 }


	hoSuccPrepIncInterFreqS1		 OBJECT-TYPE
		SYNTAX					 Counter32
		MAX-ACCESS			 read-only
		STATUS					 current
		DESCRIPTION			 " -- "
		::=  { s1HandOverProcInterEnbEntry  21 }


	hoSuccIncInterFreqS1		 OBJECT-TYPE
		SYNTAX					 Counter32
		MAX-ACCESS			 read-only
		STATUS					 current
		DESCRIPTION			 " -- "
		::=  { s1HandOverProcInterEnbEntry  22 }


	hoFailPrepIncIntraFreqS1MaxUeNum		 OBJECT-TYPE
		SYNTAX					 Counter32
		MAX-ACCESS			 read-only
		STATUS					 current
		DESCRIPTION			 " -- "
		::=  { s1HandOverProcInterEnbEntry  23 }


	hoFailPrepIncIntraFreqS1CellOverLoad		 OBJECT-TYPE
		SYNTAX					 Counter32
		MAX-ACCESS			 read-only
		STATUS					 current
		DESCRIPTION			 " -- "
		::=  { s1HandOverProcInterEnbEntry  24 }


	hoFailPrepIncIntraFreqS1Prb		 OBJECT-TYPE
		SYNTAX					 Counter32
		MAX-ACCESS			 read-only
		STATUS					 current
		DESCRIPTION			 " -- "
		::=  { s1HandOverProcInterEnbEntry  25 }


	hoFailPrepIncIntraFreqS1HandoverRestrictList		 OBJECT-TYPE
		SYNTAX					 Counter32
		MAX-ACCESS			 read-only
		STATUS					 current
		DESCRIPTION			 " -- "
		::=  { s1HandOverProcInterEnbEntry  26 }


	hoFailPrepIncIntraFreqS1CellBlock		 OBJECT-TYPE
		SYNTAX					 Counter32
		MAX-ACCESS			 read-only
		STATUS					 current
		DESCRIPTION			 " -- "
		::=  { s1HandOverProcInterEnbEntry  27 }


	hoFailPrepIncIntraFreqS1Tpc		 OBJECT-TYPE
		SYNTAX					 Counter32
		MAX-ACCESS			 read-only
		STATUS					 current
		DESCRIPTION			 " -- "
		::=  { s1HandOverProcInterEnbEntry  28 }


	hoFailPrepIncIntraFreqS1DrbID		 OBJECT-TYPE
		SYNTAX					 Counter32
		MAX-ACCESS			 read-only
		STATUS					 current
		DESCRIPTION			 " -- "
		::=  { s1HandOverProcInterEnbEntry  29 }


	hoFailPrepIncIntraFreqS1SPS		 OBJECT-TYPE
		SYNTAX					 Counter32
		MAX-ACCESS			 read-only
		STATUS					 current
		DESCRIPTION			 " -- "
		::=  { s1HandOverProcInterEnbEntry  30 }


	hoFailPrepIncIntraFreqS1LoChID		 OBJECT-TYPE
		SYNTAX					 Counter32
		MAX-ACCESS			 read-only
		STATUS					 current
		DESCRIPTION			 " -- "
		::=  { s1HandOverProcInterEnbEntry  31 }


	hoFailPrepIncIntraFreqS1Pucch		 OBJECT-TYPE
		SYNTAX					 Counter32
		MAX-ACCESS			 read-only
		STATUS					 current
		DESCRIPTION			 " -- "
		::=  { s1HandOverProcInterEnbEntry  32 }


	hoFailPrepIncIntraFreqS1Srs		 OBJECT-TYPE
		SYNTAX					 Counter32
		MAX-ACCESS			 read-only
		STATUS					 current
		DESCRIPTION			 " -- "
		::=  { s1HandOverProcInterEnbEntry  33 }


	hoFailPrepIncIntraFreqS1PerEncodeFail		 OBJECT-TYPE
		SYNTAX					 Counter32
		MAX-ACCESS			 read-only
		STATUS					 current
		DESCRIPTION			 " -- "
		::=  { s1HandOverProcInterEnbEntry  34 }


	hoFailPrepIncIntraFreqS1PerDecodeFail		 OBJECT-TYPE
		SYNTAX					 Counter32
		MAX-ACCESS			 read-only
		STATUS					 current
		DESCRIPTION			 " -- "
		::=  { s1HandOverProcInterEnbEntry  35 }


	hoFailPrepIncIntraFreqS1SecurityFailure		 OBJECT-TYPE
		SYNTAX					 Counter32
		MAX-ACCESS			 read-only
		STATUS					 current
		DESCRIPTION			 " -- "
		::=  { s1HandOverProcInterEnbEntry  36 }


	hoFailPrepIncIntraFreqS1ParameterError		 OBJECT-TYPE
		SYNTAX					 Counter32
		MAX-ACCESS			 read-only
		STATUS					 current
		DESCRIPTION			 " -- "
		::=  { s1HandOverProcInterEnbEntry  37 }


	hoFailPrepIncIntraFreqS1Others		 OBJECT-TYPE
		SYNTAX					 Counter32
		MAX-ACCESS			 read-only
		STATUS					 current
		DESCRIPTION			 " -- "
		::=  { s1HandOverProcInterEnbEntry  38 }


	hoFailPrepIncInterFreqS1MaxUeNum		 OBJECT-TYPE
		SYNTAX					 Counter32
		MAX-ACCESS			 read-only
		STATUS					 current
		DESCRIPTION			 " -- "
		::=  { s1HandOverProcInterEnbEntry  39 }


	hoFailPrepIncInterFreqS1CellOverLoad		 OBJECT-TYPE
		SYNTAX					 Counter32
		MAX-ACCESS			 read-only
		STATUS					 current
		DESCRIPTION			 " -- "
		::=  { s1HandOverProcInterEnbEntry  40 }


	hoFailPrepIncInterFreqS1Prb		 OBJECT-TYPE
		SYNTAX					 Counter32
		MAX-ACCESS			 read-only
		STATUS					 current
		DESCRIPTION			 " -- "
		::=  { s1HandOverProcInterEnbEntry  41 }


	hoFailPrepIncInterFreqS1HandoverRestrictList		 OBJECT-TYPE
		SYNTAX					 Counter32
		MAX-ACCESS			 read-only
		STATUS					 current
		DESCRIPTION			 " -- "
		::=  { s1HandOverProcInterEnbEntry  42 }


	hoFailPrepIncInterFreqS1CellBlock		 OBJECT-TYPE
		SYNTAX					 Counter32
		MAX-ACCESS			 read-only
		STATUS					 current
		DESCRIPTION			 " -- "
		::=  { s1HandOverProcInterEnbEntry  43 }


	hoFailPrepIncInterFreqS1Tpc		 OBJECT-TYPE
		SYNTAX					 Counter32
		MAX-ACCESS			 read-only
		STATUS					 current
		DESCRIPTION			 " -- "
		::=  { s1HandOverProcInterEnbEntry  44 }


	hoFailPrepIncInterFreqS1DrbID		 OBJECT-TYPE
		SYNTAX					 Counter32
		MAX-ACCESS			 read-only
		STATUS					 current
		DESCRIPTION			 " -- "
		::=  { s1HandOverProcInterEnbEntry  45 }


	hoFailPrepIncInterFreqS1SPS		 OBJECT-TYPE
		SYNTAX					 Counter32
		MAX-ACCESS			 read-only
		STATUS					 current
		DESCRIPTION			 " -- "
		::=  { s1HandOverProcInterEnbEntry  46 }


	hoFailPrepIncInterFreqS1LoChID		 OBJECT-TYPE
		SYNTAX					 Counter32
		MAX-ACCESS			 read-only
		STATUS					 current
		DESCRIPTION			 " -- "
		::=  { s1HandOverProcInterEnbEntry  47 }


	hoFailPrepIncInterFreqS1Pucch		 OBJECT-TYPE
		SYNTAX					 Counter32
		MAX-ACCESS			 read-only
		STATUS					 current
		DESCRIPTION			 " -- "
		::=  { s1HandOverProcInterEnbEntry  48 }


	hoFailPrepIncInterFreqS1Srs		 OBJECT-TYPE
		SYNTAX					 Counter32
		MAX-ACCESS			 read-only
		STATUS					 current
		DESCRIPTION			 " -- "
		::=  { s1HandOverProcInterEnbEntry  49 }


	hoFailPrepIncInterFreqS1PerEncodeFail		 OBJECT-TYPE
		SYNTAX					 Counter32
		MAX-ACCESS			 read-only
		STATUS					 current
		DESCRIPTION			 " -- "
		::=  { s1HandOverProcInterEnbEntry  50 }


	hoFailPrepIncInterFreqS1PerDecodeFail		 OBJECT-TYPE
		SYNTAX					 Counter32
		MAX-ACCESS			 read-only
		STATUS					 current
		DESCRIPTION			 " -- "
		::=  { s1HandOverProcInterEnbEntry  51 }


	hoFailPrepIncInterFreqS1SecurityFailure		 OBJECT-TYPE
		SYNTAX					 Counter32
		MAX-ACCESS			 read-only
		STATUS					 current
		DESCRIPTION			 " -- "
		::=  { s1HandOverProcInterEnbEntry  52 }


	hoFailPrepIncInterFreqS1ParameterError		 OBJECT-TYPE
		SYNTAX					 Counter32
		MAX-ACCESS			 read-only
		STATUS					 current
		DESCRIPTION			 " -- "
		::=  { s1HandOverProcInterEnbEntry  53 }


	hoFailPrepIncInterFreqS1Others		 OBJECT-TYPE
		SYNTAX					 Counter32
		MAX-ACCESS			 read-only
		STATUS					 current
		DESCRIPTION			 " -- "
		::=  { s1HandOverProcInterEnbEntry  54 }


	hoSucOutIntraFreqS1		 OBJECT-TYPE
		SYNTAX					 Counter32
		MAX-ACCESS			 read-only
		STATUS					 current
		DESCRIPTION			 " -- "
		::=  { s1HandOverProcInterEnbEntry  55 }


	hoSucOutInterFreqS1		 OBJECT-TYPE
		SYNTAX					 Counter32
		MAX-ACCESS			 read-only
		STATUS					 current
		DESCRIPTION			 " -- "
		::=  { s1HandOverProcInterEnbEntry  56 }


	hoAttOutExecIntraFreqS1		 OBJECT-TYPE
		SYNTAX					 Counter32
		MAX-ACCESS			 read-only
		STATUS					 current
		DESCRIPTION			 " -- "
		::=  { s1HandOverProcInterEnbEntry  57 }


	hoAttOutExecInterFreqS1		 OBJECT-TYPE
		SYNTAX					 Counter32
		MAX-ACCESS			 read-only
		STATUS					 current
		DESCRIPTION			 " -- "
		::=  { s1HandOverProcInterEnbEntry  58 }


	hoAttOutPrepIntraFreqS1		 OBJECT-TYPE
		SYNTAX					 Counter32
		MAX-ACCESS			 read-only
		STATUS					 current
		DESCRIPTION			 " -- "
		::=  { s1HandOverProcInterEnbEntry  59 }


	hoAttOutPrepInterFreqS1		 OBJECT-TYPE
		SYNTAX					 Counter32
		MAX-ACCESS			 read-only
		STATUS					 current
		DESCRIPTION			 " -- "
		::=  { s1HandOverProcInterEnbEntry  60 }


	hoFailPrepOutIntraFreqS1SourceFail		 OBJECT-TYPE
		SYNTAX					 Counter32
		MAX-ACCESS			 read-only
		STATUS					 current
		DESCRIPTION			 " -- "
		::=  { s1HandOverProcInterEnbEntry  61 }


	hoFailPrepOutInterFreqS1SourceFail		 OBJECT-TYPE
		SYNTAX					 Counter32
		MAX-ACCESS			 read-only
		STATUS					 current
		DESCRIPTION			 " -- "
		::=  { s1HandOverProcInterEnbEntry  62 }


	x2HandOverProcInterEnbTable		 OBJECT-TYPE
		SYNTAX					 SEQUENCE  OF	 X2HandOverProcInterEnbEntry
		MAX-ACCESS			 not-accessible
		STATUS					 current
		DESCRIPTION			 " -- "
		::=  { rrcrelatedOriginCounter  8 }


	x2HandOverProcInterEnbEntry		 OBJECT-TYPE
		SYNTAX					 X2HandOverProcInterEnbEntry
		MAX-ACCESS			 not-accessible
		STATUS					 current
		DESCRIPTION			 " -- "
		INDEX						{ x2HandOverProcInterEnbLcId }
		::=  { x2HandOverProcInterEnbTable  1 }


	X2HandOverProcInterEnbEntry		 ::=  SEQUENCE {
		x2HandOverProcInterEnbLcId					Integer32,
		x2HandOverProcInterEnbRowStatus					RowStatus,
		hoAttOutIntraFreqX2					Counter32,
		hoSuccPrepOutIntraFreqX2					Counter32,
		hoSuccOutIntraFreqX2					Counter32,
		hoAttOutInterFreqX2					Counter32,
		hoSuccPrepOutInterFreqX2					Counter32,
		hoSuccOutInterFreqX2					Counter32,
		hoFailPrepOutIntraFreqX2Fail					Counter32,
		hoFailPrepOutIntraFreqX2NoRsp					Counter32,
		hoFailPrepOutInterFreqX2Fail					Counter32,
		hoFailPrepOutInterFreqX2NoRsp					Counter32,
		hoSuccPrepOutIntraFreqX2PartialHandover					Counter32,
		hoSuccPrepOutInterFreqX2PartialHandover					Counter32,
		hoFailOutIntraFreqX2TarExecuteNoRsp					Counter32,
		hoFailOutInterFreqX2TarExecuteNoRsp					Counter32,
		hoAttIncIntraFreqX2					Counter32,
		hoSuccPrepIncIntraFreqX2					Counter32,
		hoSuccIncIntraFreqX2					Counter32,
		hoAttIncInterFreqX2					Counter32,
		hoSuccPrepIncInterFreqX2					Counter32,
		hoSuccIncInterFreqX2					Counter32,
		hoFailPrepIncIntraFreqX2MaxUeNum					Counter32,
		hoFailPrepIncIntraFreqX2CellOverLoad					Counter32,
		hoFailPrepIncIntraFreqX2Prb					Counter32,
		hoFailPrepIncIntraFreqX2HandoverRestrictList					Counter32,
		hoFailPrepIncIntraFreqX2CellBlock					Counter32,
		hoFailPrepIncIntraFreqX2Tpc					Counter32,
		hoFailPrepIncIntraFreqX2DrbID					Counter32,
		hoFailPrepIncIntraFreqX2SPS					Counter32,
		hoFailPrepIncIntraFreqX2LoChID					Counter32,
		hoFailPrepIncIntraFreqX2Pucch					Counter32,
		hoFailPrepIncIntraFreqX2Srs					Counter32,
		hoFailPrepIncIntraFreqX2PerEncodeFail					Counter32,
		hoFailPrepIncIntraFreqX2PerDecodeFail					Counter32,
		hoFailPrepIncIntraFreqX2SecurityFailure					Counter32,
		hoFailPrepIncIntraFreqX2ParameterError					Counter32,
		hoFailPrepIncIntraFreqX2Others					Counter32,
		hoFailPrepIncInterFreqX2MaxUeNum					Counter32,
		hoFailPrepIncInterFreqX2CellOverLoad					Counter32,
		hoFailPrepIncInterFreqX2Prb					Counter32,
		hoFailPrepIncInterFreqX2HandoverRestrictList					Counter32,
		hoFailPrepIncInterFreqX2CellBlock					Counter32,
		hoFailPrepIncInterFreqX2Tpc					Counter32,
		hoFailPrepIncInterFreqX2DrbID					Counter32,
		hoFailPrepIncInterFreqX2SPS					Counter32,
		hoFailPrepIncInterFreqX2LoChID					Counter32,
		hoFailPrepIncInterFreqX2Pucch					Counter32,
		hoFailPrepIncInterFreqX2Srs					Counter32,
		hoFailPrepIncInterFreqX2PerEncodeFail					Counter32,
		hoFailPrepIncInterFreqX2PerDecodeFail					Counter32,
		hoFailPrepIncInterFreqX2SecurityFailure					Counter32,
		hoFailPrepIncInterFreqX2ParameterError					Counter32,
		hoFailPrepIncInterFreqX2Others					Counter32,
		hoFailOutIntraFreqX2SourceFail					Counter32,
		hoFailOutInterFreqX2SourceFail					Counter32,
		hoAttOutExecIntraFreqX2					Counter32,
		hoAttOutExecInterFreqX2					Counter32,
		hoAttOutPrepIntraFreqX2					Counter32,
		hoAttOutPrepInterFreqX2					Counter32,
		hoFailPrepOutIntraFreqX2SourceFail					Counter32,
		hoFailPrepOutInterFreqX2SourceFail					Counter32
		}


	x2HandOverProcInterEnbLcId		 OBJECT-TYPE
		SYNTAX					 Integer32( 0 .. 23 )
		MAX-ACCESS			 not-accessible
		STATUS					 current
		DESCRIPTION			 " -- "
		::=  { x2HandOverProcInterEnbEntry  1 }


	x2HandOverProcInterEnbRowStatus		 OBJECT-TYPE
		SYNTAX					 RowStatus
		MAX-ACCESS			 read-only
		STATUS					 current
		DESCRIPTION			 " -- "
		::=  { x2HandOverProcInterEnbEntry  2 }


	hoAttOutIntraFreqX2		 OBJECT-TYPE
		SYNTAX					 Counter32
		MAX-ACCESS			 read-only
		STATUS					 current
		DESCRIPTION			 " -- "
		::=  { x2HandOverProcInterEnbEntry  3 }


	hoSuccPrepOutIntraFreqX2		 OBJECT-TYPE
		SYNTAX					 Counter32
		MAX-ACCESS			 read-only
		STATUS					 current
		DESCRIPTION			 " -- "
		::=  { x2HandOverProcInterEnbEntry  4 }


	hoSuccOutIntraFreqX2		 OBJECT-TYPE
		SYNTAX					 Counter32
		MAX-ACCESS			 read-only
		STATUS					 current
		DESCRIPTION			 " -- "
		::=  { x2HandOverProcInterEnbEntry  5 }


	hoAttOutInterFreqX2		 OBJECT-TYPE
		SYNTAX					 Counter32
		MAX-ACCESS			 read-only
		STATUS					 current
		DESCRIPTION			 " -- "
		::=  { x2HandOverProcInterEnbEntry  6 }


	hoSuccPrepOutInterFreqX2		 OBJECT-TYPE
		SYNTAX					 Counter32
		MAX-ACCESS			 read-only
		STATUS					 current
		DESCRIPTION			 " -- "
		::=  { x2HandOverProcInterEnbEntry  7 }


	hoSuccOutInterFreqX2		 OBJECT-TYPE
		SYNTAX					 Counter32
		MAX-ACCESS			 read-only
		STATUS					 current
		DESCRIPTION			 " -- "
		::=  { x2HandOverProcInterEnbEntry  8 }


	hoFailPrepOutIntraFreqX2Fail		 OBJECT-TYPE
		SYNTAX					 Counter32
		MAX-ACCESS			 read-only
		STATUS					 current
		DESCRIPTION			 " -- "
		::=  { x2HandOverProcInterEnbEntry  9 }


	hoFailPrepOutIntraFreqX2NoRsp		 OBJECT-TYPE
		SYNTAX					 Counter32
		MAX-ACCESS			 read-only
		STATUS					 current
		DESCRIPTION			 " -- "
		::=  { x2HandOverProcInterEnbEntry  10 }


	hoFailPrepOutInterFreqX2Fail		 OBJECT-TYPE
		SYNTAX					 Counter32
		MAX-ACCESS			 read-only
		STATUS					 current
		DESCRIPTION			 " -- "
		::=  { x2HandOverProcInterEnbEntry  11 }


	hoFailPrepOutInterFreqX2NoRsp		 OBJECT-TYPE
		SYNTAX					 Counter32
		MAX-ACCESS			 read-only
		STATUS					 current
		DESCRIPTION			 " -- "
		::=  { x2HandOverProcInterEnbEntry  12 }


	hoSuccPrepOutIntraFreqX2PartialHandover		 OBJECT-TYPE
		SYNTAX					 Counter32
		MAX-ACCESS			 read-only
		STATUS					 current
		DESCRIPTION			 " -- "
		::=  { x2HandOverProcInterEnbEntry  13 }


	hoSuccPrepOutInterFreqX2PartialHandover		 OBJECT-TYPE
		SYNTAX					 Counter32
		MAX-ACCESS			 read-only
		STATUS					 current
		DESCRIPTION			 " -- "
		::=  { x2HandOverProcInterEnbEntry  14 }


	hoFailOutIntraFreqX2TarExecuteNoRsp		 OBJECT-TYPE
		SYNTAX					 Counter32
		MAX-ACCESS			 read-only
		STATUS					 current
		DESCRIPTION			 " -- "
		::=  { x2HandOverProcInterEnbEntry  15 }


	hoFailOutInterFreqX2TarExecuteNoRsp		 OBJECT-TYPE
		SYNTAX					 Counter32
		MAX-ACCESS			 read-only
		STATUS					 current
		DESCRIPTION			 " -- "
		::=  { x2HandOverProcInterEnbEntry  16 }


	hoAttIncIntraFreqX2		 OBJECT-TYPE
		SYNTAX					 Counter32
		MAX-ACCESS			 read-only
		STATUS					 current
		DESCRIPTION			 " -- "
		::=  { x2HandOverProcInterEnbEntry  17 }


	hoSuccPrepIncIntraFreqX2		 OBJECT-TYPE
		SYNTAX					 Counter32
		MAX-ACCESS			 read-only
		STATUS					 current
		DESCRIPTION			 " -- "
		::=  { x2HandOverProcInterEnbEntry  18 }


	hoSuccIncIntraFreqX2		 OBJECT-TYPE
		SYNTAX					 Counter32
		MAX-ACCESS			 read-only
		STATUS					 current
		DESCRIPTION			 " -- "
		::=  { x2HandOverProcInterEnbEntry  19 }


	hoAttIncInterFreqX2		 OBJECT-TYPE
		SYNTAX					 Counter32
		MAX-ACCESS			 read-only
		STATUS					 current
		DESCRIPTION			 " -- "
		::=  { x2HandOverProcInterEnbEntry  20 }


	hoSuccPrepIncInterFreqX2		 OBJECT-TYPE
		SYNTAX					 Counter32
		MAX-ACCESS			 read-only
		STATUS					 current
		DESCRIPTION			 " -- "
		::=  { x2HandOverProcInterEnbEntry  21 }


	hoSuccIncInterFreqX2		 OBJECT-TYPE
		SYNTAX					 Counter32
		MAX-ACCESS			 read-only
		STATUS					 current
		DESCRIPTION			 " -- "
		::=  { x2HandOverProcInterEnbEntry  22 }


	hoFailPrepIncIntraFreqX2MaxUeNum		 OBJECT-TYPE
		SYNTAX					 Counter32
		MAX-ACCESS			 read-only
		STATUS					 current
		DESCRIPTION			 " -- "
		::=  { x2HandOverProcInterEnbEntry  23 }


	hoFailPrepIncIntraFreqX2CellOverLoad		 OBJECT-TYPE
		SYNTAX					 Counter32
		MAX-ACCESS			 read-only
		STATUS					 current
		DESCRIPTION			 " -- "
		::=  { x2HandOverProcInterEnbEntry  24 }


	hoFailPrepIncIntraFreqX2Prb		 OBJECT-TYPE
		SYNTAX					 Counter32
		MAX-ACCESS			 read-only
		STATUS					 current
		DESCRIPTION			 " -- "
		::=  { x2HandOverProcInterEnbEntry  25 }


	hoFailPrepIncIntraFreqX2HandoverRestrictList		 OBJECT-TYPE
		SYNTAX					 Counter32
		MAX-ACCESS			 read-only
		STATUS					 current
		DESCRIPTION			 " -- "
		::=  { x2HandOverProcInterEnbEntry  26 }


	hoFailPrepIncIntraFreqX2CellBlock		 OBJECT-TYPE
		SYNTAX					 Counter32
		MAX-ACCESS			 read-only
		STATUS					 current
		DESCRIPTION			 " -- "
		::=  { x2HandOverProcInterEnbEntry  27 }


	hoFailPrepIncIntraFreqX2Tpc		 OBJECT-TYPE
		SYNTAX					 Counter32
		MAX-ACCESS			 read-only
		STATUS					 current
		DESCRIPTION			 " -- "
		::=  { x2HandOverProcInterEnbEntry  28 }


	hoFailPrepIncIntraFreqX2DrbID		 OBJECT-TYPE
		SYNTAX					 Counter32
		MAX-ACCESS			 read-only
		STATUS					 current
		DESCRIPTION			 " -- "
		::=  { x2HandOverProcInterEnbEntry  29 }


	hoFailPrepIncIntraFreqX2SPS		 OBJECT-TYPE
		SYNTAX					 Counter32
		MAX-ACCESS			 read-only
		STATUS					 current
		DESCRIPTION			 " -- "
		::=  { x2HandOverProcInterEnbEntry  30 }


	hoFailPrepIncIntraFreqX2LoChID		 OBJECT-TYPE
		SYNTAX					 Counter32
		MAX-ACCESS			 read-only
		STATUS					 current
		DESCRIPTION			 " -- "
		::=  { x2HandOverProcInterEnbEntry  31 }


	hoFailPrepIncIntraFreqX2Pucch		 OBJECT-TYPE
		SYNTAX					 Counter32
		MAX-ACCESS			 read-only
		STATUS					 current
		DESCRIPTION			 " -- "
		::=  { x2HandOverProcInterEnbEntry  32 }


	hoFailPrepIncIntraFreqX2Srs		 OBJECT-TYPE
		SYNTAX					 Counter32
		MAX-ACCESS			 read-only
		STATUS					 current
		DESCRIPTION			 " -- "
		::=  { x2HandOverProcInterEnbEntry  33 }


	hoFailPrepIncIntraFreqX2PerEncodeFail		 OBJECT-TYPE
		SYNTAX					 Counter32
		MAX-ACCESS			 read-only
		STATUS					 current
		DESCRIPTION			 " -- "
		::=  { x2HandOverProcInterEnbEntry  34 }


	hoFailPrepIncIntraFreqX2PerDecodeFail		 OBJECT-TYPE
		SYNTAX					 Counter32
		MAX-ACCESS			 read-only
		STATUS					 current
		DESCRIPTION			 " -- "
		::=  { x2HandOverProcInterEnbEntry  35 }


	hoFailPrepIncIntraFreqX2SecurityFailure		 OBJECT-TYPE
		SYNTAX					 Counter32
		MAX-ACCESS			 read-only
		STATUS					 current
		DESCRIPTION			 " -- "
		::=  { x2HandOverProcInterEnbEntry  36 }


	hoFailPrepIncIntraFreqX2ParameterError		 OBJECT-TYPE
		SYNTAX					 Counter32
		MAX-ACCESS			 read-only
		STATUS					 current
		DESCRIPTION			 " -- "
		::=  { x2HandOverProcInterEnbEntry  37 }


	hoFailPrepIncIntraFreqX2Others		 OBJECT-TYPE
		SYNTAX					 Counter32
		MAX-ACCESS			 read-only
		STATUS					 current
		DESCRIPTION			 " -- "
		::=  { x2HandOverProcInterEnbEntry  38 }


	hoFailPrepIncInterFreqX2MaxUeNum		 OBJECT-TYPE
		SYNTAX					 Counter32
		MAX-ACCESS			 read-only
		STATUS					 current
		DESCRIPTION			 " -- "
		::=  { x2HandOverProcInterEnbEntry  39 }


	hoFailPrepIncInterFreqX2CellOverLoad		 OBJECT-TYPE
		SYNTAX					 Counter32
		MAX-ACCESS			 read-only
		STATUS					 current
		DESCRIPTION			 " -- "
		::=  { x2HandOverProcInterEnbEntry  40 }


	hoFailPrepIncInterFreqX2Prb		 OBJECT-TYPE
		SYNTAX					 Counter32
		MAX-ACCESS			 read-only
		STATUS					 current
		DESCRIPTION			 " -- "
		::=  { x2HandOverProcInterEnbEntry  41 }


	hoFailPrepIncInterFreqX2HandoverRestrictList		 OBJECT-TYPE
		SYNTAX					 Counter32
		MAX-ACCESS			 read-only
		STATUS					 current
		DESCRIPTION			 " -- "
		::=  { x2HandOverProcInterEnbEntry  42 }


	hoFailPrepIncInterFreqX2CellBlock		 OBJECT-TYPE
		SYNTAX					 Counter32
		MAX-ACCESS			 read-only
		STATUS					 current
		DESCRIPTION			 " -- "
		::=  { x2HandOverProcInterEnbEntry  43 }


	hoFailPrepIncInterFreqX2Tpc		 OBJECT-TYPE
		SYNTAX					 Counter32
		MAX-ACCESS			 read-only
		STATUS					 current
		DESCRIPTION			 " -- "
		::=  { x2HandOverProcInterEnbEntry  44 }


	hoFailPrepIncInterFreqX2DrbID		 OBJECT-TYPE
		SYNTAX					 Counter32
		MAX-ACCESS			 read-only
		STATUS					 current
		DESCRIPTION			 " -- "
		::=  { x2HandOverProcInterEnbEntry  45 }


	hoFailPrepIncInterFreqX2SPS		 OBJECT-TYPE
		SYNTAX					 Counter32
		MAX-ACCESS			 read-only
		STATUS					 current
		DESCRIPTION			 " -- "
		::=  { x2HandOverProcInterEnbEntry  46 }


	hoFailPrepIncInterFreqX2LoChID		 OBJECT-TYPE
		SYNTAX					 Counter32
		MAX-ACCESS			 read-only
		STATUS					 current
		DESCRIPTION			 " -- "
		::=  { x2HandOverProcInterEnbEntry  47 }


	hoFailPrepIncInterFreqX2Pucch		 OBJECT-TYPE
		SYNTAX					 Counter32
		MAX-ACCESS			 read-only
		STATUS					 current
		DESCRIPTION			 " -- "
		::=  { x2HandOverProcInterEnbEntry  48 }


	hoFailPrepIncInterFreqX2Srs		 OBJECT-TYPE
		SYNTAX					 Counter32
		MAX-ACCESS			 read-only
		STATUS					 current
		DESCRIPTION			 " -- "
		::=  { x2HandOverProcInterEnbEntry  49 }


	hoFailPrepIncInterFreqX2PerEncodeFail		 OBJECT-TYPE
		SYNTAX					 Counter32
		MAX-ACCESS			 read-only
		STATUS					 current
		DESCRIPTION			 " -- "
		::=  { x2HandOverProcInterEnbEntry  50 }


	hoFailPrepIncInterFreqX2PerDecodeFail		 OBJECT-TYPE
		SYNTAX					 Counter32
		MAX-ACCESS			 read-only
		STATUS					 current
		DESCRIPTION			 " -- "
		::=  { x2HandOverProcInterEnbEntry  51 }


	hoFailPrepIncInterFreqX2SecurityFailure		 OBJECT-TYPE
		SYNTAX					 Counter32
		MAX-ACCESS			 read-only
		STATUS					 current
		DESCRIPTION			 " -- "
		::=  { x2HandOverProcInterEnbEntry  52 }


	hoFailPrepIncInterFreqX2ParameterError		 OBJECT-TYPE
		SYNTAX					 Counter32
		MAX-ACCESS			 read-only
		STATUS					 current
		DESCRIPTION			 " -- "
		::=  { x2HandOverProcInterEnbEntry  53 }


	hoFailPrepIncInterFreqX2Others		 OBJECT-TYPE
		SYNTAX					 Counter32
		MAX-ACCESS			 read-only
		STATUS					 current
		DESCRIPTION			 " -- "
		::=  { x2HandOverProcInterEnbEntry  54 }


	hoFailOutIntraFreqX2SourceFail		 OBJECT-TYPE
		SYNTAX					 Counter32
		MAX-ACCESS			 read-only
		STATUS					 current
		DESCRIPTION			 " -- "
		::=  { x2HandOverProcInterEnbEntry  55 }


	hoFailOutInterFreqX2SourceFail		 OBJECT-TYPE
		SYNTAX					 Counter32
		MAX-ACCESS			 read-only
		STATUS					 current
		DESCRIPTION			 " -- "
		::=  { x2HandOverProcInterEnbEntry  56 }


	hoAttOutExecIntraFreqX2		 OBJECT-TYPE
		SYNTAX					 Counter32
		MAX-ACCESS			 read-only
		STATUS					 current
		DESCRIPTION			 " -- "
		::=  { x2HandOverProcInterEnbEntry  57 }


	hoAttOutExecInterFreqX2		 OBJECT-TYPE
		SYNTAX					 Counter32
		MAX-ACCESS			 read-only
		STATUS					 current
		DESCRIPTION			 " -- "
		::=  { x2HandOverProcInterEnbEntry  58 }


	hoAttOutPrepIntraFreqX2		 OBJECT-TYPE
		SYNTAX					 Counter32
		MAX-ACCESS			 read-only
		STATUS					 current
		DESCRIPTION			 " -- "
		::=  { x2HandOverProcInterEnbEntry  59 }


	hoAttOutPrepInterFreqX2		 OBJECT-TYPE
		SYNTAX					 Counter32
		MAX-ACCESS			 read-only
		STATUS					 current
		DESCRIPTION			 " -- "
		::=  { x2HandOverProcInterEnbEntry  60 }


	hoFailPrepOutIntraFreqX2SourceFail		 OBJECT-TYPE
		SYNTAX					 Counter32
		MAX-ACCESS			 read-only
		STATUS					 current
		DESCRIPTION			 " -- "
		::=  { x2HandOverProcInterEnbEntry  61 }


	hoFailPrepOutInterFreqX2SourceFail		 OBJECT-TYPE
		SYNTAX					 Counter32
		MAX-ACCESS			 read-only
		STATUS					 current
		DESCRIPTION			 " -- "
		::=  { x2HandOverProcInterEnbEntry  62 }


	handOverProcIntraEnbTable		 OBJECT-TYPE
		SYNTAX					 SEQUENCE  OF	 HandOverProcIntraEnbEntry
		MAX-ACCESS			 not-accessible
		STATUS					 current
		DESCRIPTION			 " -- "
		::=  { rrcrelatedOriginCounter  9 }


	handOverProcIntraEnbEntry		 OBJECT-TYPE
		SYNTAX					 HandOverProcIntraEnbEntry
		MAX-ACCESS			 not-accessible
		STATUS					 current
		DESCRIPTION			 " -- "
		INDEX						{ handOverProcIntraEnbLcId }
		::=  { handOverProcIntraEnbTable  1 }


	HandOverProcIntraEnbEntry		 ::=  SEQUENCE {
		handOverProcIntraEnbLcId					Integer32,
		handOverProcIntraEnbRowStatus					RowStatus,
		hoAttIncIntraFreqInterCellIntraEnb					Counter32,
		hoSuccIncIntraFreqInterCellIntraEnb					Counter32,
		hoAttIncInterFreqInterCellIntraEnb					Counter32,
		hoSuccIncInterFreqInterCellIntraEnb					Counter32,
		hoAttOutIntraFreqInterCellIntraEnb					Counter32,
		hoSuccOutIntraFreqInterCellIntraEnb					Counter32,
		hoAttOutInterFreqInterCellIntraEnb					Counter32,
		hoSuccOutInterFreqInterCellIntraEnb					Counter32,
		hoFailIncIntraFreqInterCellIntraEnbMaxUeNum					Counter32,
		hoFailIncIntraFreqInterCellIntraEnbOL					Counter32,
		hoFailIncIntraFreqInterCellIntraEnbPrb					Counter32,
		hoFailIncIntraFreqInterCellIntraEnbCellBlock					Counter32,
		hoFailIncIntraFreqInterCellIntraEnbTpc					Counter32,
		hoFailIncIntraFreqInterCellIntraEnbDrbID					Counter32,
		hoFailIncIntraFreqInterCellIntraEnbSPS					Counter32,
		hoFailIncIntraFreqInterCellIntraEnbLoChID					Counter32,
		hoFailIncIntraFreqInterCellIntraEnbPucch					Counter32,
		hoFailIncIntraFreqInterCellIntraEnbSrs					Counter32,
		hoFailIncIntraFreqInterCellIntraEnbSrcNoRsp					Counter32,
		hoFailIncIntraFreqInterCellIntraEnbSecFail					Counter32,
		hoFailIncIntraFreqInterCellIntraEnbOthers					Counter32,
		hoFailIncInterFreqInterCellIntraEnbMaxUeNum					Counter32,
		hoFailIncInterFreqInterCellIntraEnbOL					Counter32,
		hoFailIncInterFreqInterCellIntraEnbPrb					Counter32,
		hoFailIncInterFreqInterCellIntraEnbCellBlock					Counter32,
		hoFailIncInterFreqInterCellIntraEnbTpc					Counter32,
		hoFailIncInterFreqInterCellIntraEnbDrbID					Counter32,
		hoFailIncInterFreqInterCellIntraEnbSPS					Counter32,
		hoFailIncInterFreqInterCellIntraEnbLoChID					Counter32,
		hoFailIncInterFreqInterCellIntraEnbPucch					Counter32,
		hoFailIncInterFreqInterCellIntraEnbSrs					Counter32,
		hoFailIncInterFreqInterCellIntraEnbSrcNoRsp					Counter32,
		hoFailIncInterFreqInterCellIntraEnbSecFail					Counter32,
		hoFailIncInterFreqInterCellIntraEnbOthers					Counter32,
		hoFailOutIntraFreqInterCellIntraEnbTarExcNoRsp					Counter32,
		hoFailOutIntraFreqInterCellIntraEnbPerEncFail					Counter32,
		hoFailOutInterFreqInterCellIntraEnbTarExcNoRsp					Counter32,
		hoFailOutInterFreqInterCellIntraEnbPerEncFail					Counter32,
		hoAttOutIntraFreqIntraEnb					Counter32,
		hoAttOutInterFreqIntraEnb					Counter32,
		hoSuccPrepOutIntraFreqIntraEnb					Counter32,
		hoSuccPrepOutInterFreqIntraEnb					Counter32,
		hoAttIncIntraFreqIntraEnb					Counter32,
		hoAttIncInterFreqIntraEnb					Counter32,
		hoSuccPrepIncIntraFreqIntraEnb					Counter32,
		hoSuccPrepIncInterFreqIntraEnb					Counter32,
		hoFailPrepIncIntraFreqIntraEnbMaxUeNum					Counter32,
		hoFailPrepIncIntraFreqIntraEnbCellOverLoad					Counter32,
		hoFailPrepIncIntraFreqIntraEnbPrb					Counter32,
		hoFailPrepIncIntraFreqIntraEnbHORestrictList					Counter32,
		hoFailPrepIncIntraFreqIntraEnbCellBlock					Counter32,
		hoFailPrepIncIntraFreqIntraEnbTpc					Counter32,
		hoFailPrepIncIntraFreqIntraEnbDrbID					Counter32,
		hoFailPrepIncIntraFreqIntraEnbSPS					Counter32,
		hoFailPrepIncIntraFreqIntraEnbLoChID					Counter32,
		hoFailPrepIncIntraFreqIntraEnbPucch					Counter32,
		hoFailPrepIncIntraFreqIntraEnbSrs					Counter32,
		hoFailPrepIncIntraFreqIntraEnbParameterError					Counter32,
		hoFailPrepIncIntraFreqIntraEnbOthers					Counter32,
		hoFailPrepIncInterFreqIntraEnbMaxUeNum					Counter32,
		hoFailPrepIncInterFreqIntraEnbCellOverLoad					Counter32,
		hoFailPrepIncInterFreqIntraEnbPrb					Counter32,
		hoFailPrepIncInterFreqIntraEnbHORestrictList					Counter32,
		hoFailPrepIncInterFreqIntraEnbCellBlock					Counter32,
		hoFailPrepIncInterFreqIntraEnbTpc					Counter32,
		hoFailPrepIncInterFreqIntraEnbDrbID					Counter32,
		hoFailPrepIncInterFreqIntraEnbSPS					Counter32,
		hoFailPrepIncInterFreqIntraEnbLoChID					Counter32,
		hoFailPrepIncInterFreqIntraEnbPucch					Counter32,
		hoFailPrepIncInterFreqIntraEnbSrs					Counter32,
		hoFailPrepIncInterFreqIntraEnbParameterError					Counter32,
		hoFailPrepIncInterFreqIntraEnbOthers					Counter32
		}


	handOverProcIntraEnbLcId		 OBJECT-TYPE
		SYNTAX					 Integer32( 0 .. 23 )
		MAX-ACCESS			 not-accessible
		STATUS					 current
		DESCRIPTION			 " -- "
		::=  { handOverProcIntraEnbEntry  1 }


	handOverProcIntraEnbRowStatus		 OBJECT-TYPE
		SYNTAX					 RowStatus
		MAX-ACCESS			 read-only
		STATUS					 current
		DESCRIPTION			 " -- "
		::=  { handOverProcIntraEnbEntry  2 }


	hoAttIncIntraFreqInterCellIntraEnb		 OBJECT-TYPE
		SYNTAX					 Counter32
		MAX-ACCESS			 read-only
		STATUS					 current
		DESCRIPTION			 " -- "
		::=  { handOverProcIntraEnbEntry  3 }


	hoSuccIncIntraFreqInterCellIntraEnb		 OBJECT-TYPE
		SYNTAX					 Counter32
		MAX-ACCESS			 read-only
		STATUS					 current
		DESCRIPTION			 " -- "
		::=  { handOverProcIntraEnbEntry  4 }


	hoAttIncInterFreqInterCellIntraEnb		 OBJECT-TYPE
		SYNTAX					 Counter32
		MAX-ACCESS			 read-only
		STATUS					 current
		DESCRIPTION			 " -- "
		::=  { handOverProcIntraEnbEntry  5 }


	hoSuccIncInterFreqInterCellIntraEnb		 OBJECT-TYPE
		SYNTAX					 Counter32
		MAX-ACCESS			 read-only
		STATUS					 current
		DESCRIPTION			 " -- "
		::=  { handOverProcIntraEnbEntry  6 }


	hoAttOutIntraFreqInterCellIntraEnb		 OBJECT-TYPE
		SYNTAX					 Counter32
		MAX-ACCESS			 read-only
		STATUS					 current
		DESCRIPTION			 " -- "
		::=  { handOverProcIntraEnbEntry  7 }


	hoSuccOutIntraFreqInterCellIntraEnb		 OBJECT-TYPE
		SYNTAX					 Counter32
		MAX-ACCESS			 read-only
		STATUS					 current
		DESCRIPTION			 " -- "
		::=  { handOverProcIntraEnbEntry  8 }


	hoAttOutInterFreqInterCellIntraEnb		 OBJECT-TYPE
		SYNTAX					 Counter32
		MAX-ACCESS			 read-only
		STATUS					 current
		DESCRIPTION			 " -- "
		::=  { handOverProcIntraEnbEntry  9 }


	hoSuccOutInterFreqInterCellIntraEnb		 OBJECT-TYPE
		SYNTAX					 Counter32
		MAX-ACCESS			 read-only
		STATUS					 current
		DESCRIPTION			 " -- "
		::=  { handOverProcIntraEnbEntry  10 }


	hoFailIncIntraFreqInterCellIntraEnbMaxUeNum		 OBJECT-TYPE
		SYNTAX					 Counter32
		MAX-ACCESS			 read-only
		STATUS					 current
		DESCRIPTION			 " -- "
		::=  { handOverProcIntraEnbEntry  11 }


	hoFailIncIntraFreqInterCellIntraEnbOL		 OBJECT-TYPE
		SYNTAX					 Counter32
		MAX-ACCESS			 read-only
		STATUS					 current
		DESCRIPTION			 " -- "
		::=  { handOverProcIntraEnbEntry  12 }


	hoFailIncIntraFreqInterCellIntraEnbPrb		 OBJECT-TYPE
		SYNTAX					 Counter32
		MAX-ACCESS			 read-only
		STATUS					 current
		DESCRIPTION			 " -- "
		::=  { handOverProcIntraEnbEntry  13 }


	hoFailIncIntraFreqInterCellIntraEnbCellBlock		 OBJECT-TYPE
		SYNTAX					 Counter32
		MAX-ACCESS			 read-only
		STATUS					 current
		DESCRIPTION			 " -- "
		::=  { handOverProcIntraEnbEntry  14 }


	hoFailIncIntraFreqInterCellIntraEnbTpc		 OBJECT-TYPE
		SYNTAX					 Counter32
		MAX-ACCESS			 read-only
		STATUS					 current
		DESCRIPTION			 " -- "
		::=  { handOverProcIntraEnbEntry  15 }


	hoFailIncIntraFreqInterCellIntraEnbDrbID		 OBJECT-TYPE
		SYNTAX					 Counter32
		MAX-ACCESS			 read-only
		STATUS					 current
		DESCRIPTION			 " -- "
		::=  { handOverProcIntraEnbEntry  16 }


	hoFailIncIntraFreqInterCellIntraEnbSPS		 OBJECT-TYPE
		SYNTAX					 Counter32
		MAX-ACCESS			 read-only
		STATUS					 current
		DESCRIPTION			 " -- "
		::=  { handOverProcIntraEnbEntry  17 }


	hoFailIncIntraFreqInterCellIntraEnbLoChID		 OBJECT-TYPE
		SYNTAX					 Counter32
		MAX-ACCESS			 read-only
		STATUS					 current
		DESCRIPTION			 " -- "
		::=  { handOverProcIntraEnbEntry  18 }


	hoFailIncIntraFreqInterCellIntraEnbPucch		 OBJECT-TYPE
		SYNTAX					 Counter32
		MAX-ACCESS			 read-only
		STATUS					 current
		DESCRIPTION			 " -- "
		::=  { handOverProcIntraEnbEntry  19 }


	hoFailIncIntraFreqInterCellIntraEnbSrs		 OBJECT-TYPE
		SYNTAX					 Counter32
		MAX-ACCESS			 read-only
		STATUS					 current
		DESCRIPTION			 " -- "
		::=  { handOverProcIntraEnbEntry  20 }


	hoFailIncIntraFreqInterCellIntraEnbSrcNoRsp		 OBJECT-TYPE
		SYNTAX					 Counter32
		MAX-ACCESS			 read-only
		STATUS					 current
		DESCRIPTION			 " -- "
		::=  { handOverProcIntraEnbEntry  21 }


	hoFailIncIntraFreqInterCellIntraEnbSecFail		 OBJECT-TYPE
		SYNTAX					 Counter32
		MAX-ACCESS			 read-only
		STATUS					 current
		DESCRIPTION			 " -- "
		::=  { handOverProcIntraEnbEntry  22 }


	hoFailIncIntraFreqInterCellIntraEnbOthers		 OBJECT-TYPE
		SYNTAX					 Counter32
		MAX-ACCESS			 read-only
		STATUS					 current
		DESCRIPTION			 " -- "
		::=  { handOverProcIntraEnbEntry  23 }


	hoFailIncInterFreqInterCellIntraEnbMaxUeNum		 OBJECT-TYPE
		SYNTAX					 Counter32
		MAX-ACCESS			 read-only
		STATUS					 current
		DESCRIPTION			 " -- "
		::=  { handOverProcIntraEnbEntry  24 }


	hoFailIncInterFreqInterCellIntraEnbOL		 OBJECT-TYPE
		SYNTAX					 Counter32
		MAX-ACCESS			 read-only
		STATUS					 current
		DESCRIPTION			 " -- "
		::=  { handOverProcIntraEnbEntry  25 }


	hoFailIncInterFreqInterCellIntraEnbPrb		 OBJECT-TYPE
		SYNTAX					 Counter32
		MAX-ACCESS			 read-only
		STATUS					 current
		DESCRIPTION			 " -- "
		::=  { handOverProcIntraEnbEntry  26 }


	hoFailIncInterFreqInterCellIntraEnbCellBlock		 OBJECT-TYPE
		SYNTAX					 Counter32
		MAX-ACCESS			 read-only
		STATUS					 current
		DESCRIPTION			 " -- "
		::=  { handOverProcIntraEnbEntry  27 }


	hoFailIncInterFreqInterCellIntraEnbTpc		 OBJECT-TYPE
		SYNTAX					 Counter32
		MAX-ACCESS			 read-only
		STATUS					 current
		DESCRIPTION			 " -- "
		::=  { handOverProcIntraEnbEntry  28 }


	hoFailIncInterFreqInterCellIntraEnbDrbID		 OBJECT-TYPE
		SYNTAX					 Counter32
		MAX-ACCESS			 read-only
		STATUS					 current
		DESCRIPTION			 " -- "
		::=  { handOverProcIntraEnbEntry  29 }


	hoFailIncInterFreqInterCellIntraEnbSPS		 OBJECT-TYPE
		SYNTAX					 Counter32
		MAX-ACCESS			 read-only
		STATUS					 current
		DESCRIPTION			 " -- "
		::=  { handOverProcIntraEnbEntry  30 }


	hoFailIncInterFreqInterCellIntraEnbLoChID		 OBJECT-TYPE
		SYNTAX					 Counter32
		MAX-ACCESS			 read-only
		STATUS					 current
		DESCRIPTION			 " -- "
		::=  { handOverProcIntraEnbEntry  31 }


	hoFailIncInterFreqInterCellIntraEnbPucch		 OBJECT-TYPE
		SYNTAX					 Counter32
		MAX-ACCESS			 read-only
		STATUS					 current
		DESCRIPTION			 " -- "
		::=  { handOverProcIntraEnbEntry  32 }


	hoFailIncInterFreqInterCellIntraEnbSrs		 OBJECT-TYPE
		SYNTAX					 Counter32
		MAX-ACCESS			 read-only
		STATUS					 current
		DESCRIPTION			 " -- "
		::=  { handOverProcIntraEnbEntry  33 }


	hoFailIncInterFreqInterCellIntraEnbSrcNoRsp		 OBJECT-TYPE
		SYNTAX					 Counter32
		MAX-ACCESS			 read-only
		STATUS					 current
		DESCRIPTION			 " -- "
		::=  { handOverProcIntraEnbEntry  34 }


	hoFailIncInterFreqInterCellIntraEnbSecFail		 OBJECT-TYPE
		SYNTAX					 Counter32
		MAX-ACCESS			 read-only
		STATUS					 current
		DESCRIPTION			 " -- "
		::=  { handOverProcIntraEnbEntry  35 }


	hoFailIncInterFreqInterCellIntraEnbOthers		 OBJECT-TYPE
		SYNTAX					 Counter32
		MAX-ACCESS			 read-only
		STATUS					 current
		DESCRIPTION			 " -- "
		::=  { handOverProcIntraEnbEntry  36 }


	hoFailOutIntraFreqInterCellIntraEnbTarExcNoRsp		 OBJECT-TYPE
		SYNTAX					 Counter32
		MAX-ACCESS			 read-only
		STATUS					 current
		DESCRIPTION			 " -- "
		::=  { handOverProcIntraEnbEntry  37 }


	hoFailOutIntraFreqInterCellIntraEnbPerEncFail		 OBJECT-TYPE
		SYNTAX					 Counter32
		MAX-ACCESS			 read-only
		STATUS					 current
		DESCRIPTION			 " -- "
		::=  { handOverProcIntraEnbEntry  38 }


	hoFailOutInterFreqInterCellIntraEnbTarExcNoRsp		 OBJECT-TYPE
		SYNTAX					 Counter32
		MAX-ACCESS			 read-only
		STATUS					 current
		DESCRIPTION			 " -- "
		::=  { handOverProcIntraEnbEntry  39 }


	hoFailOutInterFreqInterCellIntraEnbPerEncFail		 OBJECT-TYPE
		SYNTAX					 Counter32
		MAX-ACCESS			 read-only
		STATUS					 current
		DESCRIPTION			 " -- "
		::=  { handOverProcIntraEnbEntry  40 }


	hoAttOutIntraFreqIntraEnb		 OBJECT-TYPE
		SYNTAX					 Counter32
		MAX-ACCESS			 read-only
		STATUS					 current
		DESCRIPTION			 " -- "
		::=  { handOverProcIntraEnbEntry  41 }


	hoAttOutInterFreqIntraEnb		 OBJECT-TYPE
		SYNTAX					 Counter32
		MAX-ACCESS			 read-only
		STATUS					 current
		DESCRIPTION			 " -- "
		::=  { handOverProcIntraEnbEntry  42 }


	hoSuccPrepOutIntraFreqIntraEnb		 OBJECT-TYPE
		SYNTAX					 Counter32
		MAX-ACCESS			 read-only
		STATUS					 current
		DESCRIPTION			 " -- "
		::=  { handOverProcIntraEnbEntry  43 }


	hoSuccPrepOutInterFreqIntraEnb		 OBJECT-TYPE
		SYNTAX					 Counter32
		MAX-ACCESS			 read-only
		STATUS					 current
		DESCRIPTION			 " -- "
		::=  { handOverProcIntraEnbEntry  44 }


	hoAttIncIntraFreqIntraEnb		 OBJECT-TYPE
		SYNTAX					 Counter32
		MAX-ACCESS			 read-only
		STATUS					 current
		DESCRIPTION			 " -- "
		::=  { handOverProcIntraEnbEntry  45 }


	hoAttIncInterFreqIntraEnb		 OBJECT-TYPE
		SYNTAX					 Counter32
		MAX-ACCESS			 read-only
		STATUS					 current
		DESCRIPTION			 " -- "
		::=  { handOverProcIntraEnbEntry  46 }


	hoSuccPrepIncIntraFreqIntraEnb		 OBJECT-TYPE
		SYNTAX					 Counter32
		MAX-ACCESS			 read-only
		STATUS					 current
		DESCRIPTION			 " -- "
		::=  { handOverProcIntraEnbEntry  47 }


	hoSuccPrepIncInterFreqIntraEnb		 OBJECT-TYPE
		SYNTAX					 Counter32
		MAX-ACCESS			 read-only
		STATUS					 current
		DESCRIPTION			 " -- "
		::=  { handOverProcIntraEnbEntry  48 }


	hoFailPrepIncIntraFreqIntraEnbMaxUeNum		 OBJECT-TYPE
		SYNTAX					 Counter32
		MAX-ACCESS			 read-only
		STATUS					 current
		DESCRIPTION			 " -- "
		::=  { handOverProcIntraEnbEntry  49 }


	hoFailPrepIncIntraFreqIntraEnbCellOverLoad		 OBJECT-TYPE
		SYNTAX					 Counter32
		MAX-ACCESS			 read-only
		STATUS					 current
		DESCRIPTION			 " -- "
		::=  { handOverProcIntraEnbEntry  50 }


	hoFailPrepIncIntraFreqIntraEnbPrb		 OBJECT-TYPE
		SYNTAX					 Counter32
		MAX-ACCESS			 read-only
		STATUS					 current
		DESCRIPTION			 " -- "
		::=  { handOverProcIntraEnbEntry  51 }


	hoFailPrepIncIntraFreqIntraEnbHORestrictList		 OBJECT-TYPE
		SYNTAX					 Counter32
		MAX-ACCESS			 read-only
		STATUS					 current
		DESCRIPTION			 " -- "
		::=  { handOverProcIntraEnbEntry  52 }


	hoFailPrepIncIntraFreqIntraEnbCellBlock		 OBJECT-TYPE
		SYNTAX					 Counter32
		MAX-ACCESS			 read-only
		STATUS					 current
		DESCRIPTION			 " -- "
		::=  { handOverProcIntraEnbEntry  53 }


	hoFailPrepIncIntraFreqIntraEnbTpc		 OBJECT-TYPE
		SYNTAX					 Counter32
		MAX-ACCESS			 read-only
		STATUS					 current
		DESCRIPTION			 " -- "
		::=  { handOverProcIntraEnbEntry  54 }


	hoFailPrepIncIntraFreqIntraEnbDrbID		 OBJECT-TYPE
		SYNTAX					 Counter32
		MAX-ACCESS			 read-only
		STATUS					 current
		DESCRIPTION			 " -- "
		::=  { handOverProcIntraEnbEntry  55 }


	hoFailPrepIncIntraFreqIntraEnbSPS		 OBJECT-TYPE
		SYNTAX					 Counter32
		MAX-ACCESS			 read-only
		STATUS					 current
		DESCRIPTION			 " -- "
		::=  { handOverProcIntraEnbEntry  56 }


	hoFailPrepIncIntraFreqIntraEnbLoChID		 OBJECT-TYPE
		SYNTAX					 Counter32
		MAX-ACCESS			 read-only
		STATUS					 current
		DESCRIPTION			 " -- "
		::=  { handOverProcIntraEnbEntry  57 }


	hoFailPrepIncIntraFreqIntraEnbPucch		 OBJECT-TYPE
		SYNTAX					 Counter32
		MAX-ACCESS			 read-only
		STATUS					 current
		DESCRIPTION			 " -- "
		::=  { handOverProcIntraEnbEntry  58 }


	hoFailPrepIncIntraFreqIntraEnbSrs		 OBJECT-TYPE
		SYNTAX					 Counter32
		MAX-ACCESS			 read-only
		STATUS					 current
		DESCRIPTION			 " -- "
		::=  { handOverProcIntraEnbEntry  59 }


	hoFailPrepIncIntraFreqIntraEnbParameterError		 OBJECT-TYPE
		SYNTAX					 Counter32
		MAX-ACCESS			 read-only
		STATUS					 current
		DESCRIPTION			 " -- "
		::=  { handOverProcIntraEnbEntry  60 }


	hoFailPrepIncIntraFreqIntraEnbOthers		 OBJECT-TYPE
		SYNTAX					 Counter32
		MAX-ACCESS			 read-only
		STATUS					 current
		DESCRIPTION			 " -- "
		::=  { handOverProcIntraEnbEntry  61 }


	hoFailPrepIncInterFreqIntraEnbMaxUeNum		 OBJECT-TYPE
		SYNTAX					 Counter32
		MAX-ACCESS			 read-only
		STATUS					 current
		DESCRIPTION			 " -- "
		::=  { handOverProcIntraEnbEntry  62 }


	hoFailPrepIncInterFreqIntraEnbCellOverLoad		 OBJECT-TYPE
		SYNTAX					 Counter32
		MAX-ACCESS			 read-only
		STATUS					 current
		DESCRIPTION			 " -- "
		::=  { handOverProcIntraEnbEntry  63 }


	hoFailPrepIncInterFreqIntraEnbPrb		 OBJECT-TYPE
		SYNTAX					 Counter32
		MAX-ACCESS			 read-only
		STATUS					 current
		DESCRIPTION			 " -- "
		::=  { handOverProcIntraEnbEntry  64 }


	hoFailPrepIncInterFreqIntraEnbHORestrictList		 OBJECT-TYPE
		SYNTAX					 Counter32
		MAX-ACCESS			 read-only
		STATUS					 current
		DESCRIPTION			 " -- "
		::=  { handOverProcIntraEnbEntry  65 }


	hoFailPrepIncInterFreqIntraEnbCellBlock		 OBJECT-TYPE
		SYNTAX					 Counter32
		MAX-ACCESS			 read-only
		STATUS					 current
		DESCRIPTION			 " -- "
		::=  { handOverProcIntraEnbEntry  66 }


	hoFailPrepIncInterFreqIntraEnbTpc		 OBJECT-TYPE
		SYNTAX					 Counter32
		MAX-ACCESS			 read-only
		STATUS					 current
		DESCRIPTION			 " -- "
		::=  { handOverProcIntraEnbEntry  67 }


	hoFailPrepIncInterFreqIntraEnbDrbID		 OBJECT-TYPE
		SYNTAX					 Counter32
		MAX-ACCESS			 read-only
		STATUS					 current
		DESCRIPTION			 " -- "
		::=  { handOverProcIntraEnbEntry  68 }


	hoFailPrepIncInterFreqIntraEnbSPS		 OBJECT-TYPE
		SYNTAX					 Counter32
		MAX-ACCESS			 read-only
		STATUS					 current
		DESCRIPTION			 " -- "
		::=  { handOverProcIntraEnbEntry  69 }


	hoFailPrepIncInterFreqIntraEnbLoChID		 OBJECT-TYPE
		SYNTAX					 Counter32
		MAX-ACCESS			 read-only
		STATUS					 current
		DESCRIPTION			 " -- "
		::=  { handOverProcIntraEnbEntry  70 }


	hoFailPrepIncInterFreqIntraEnbPucch		 OBJECT-TYPE
		SYNTAX					 Counter32
		MAX-ACCESS			 read-only
		STATUS					 current
		DESCRIPTION			 " -- "
		::=  { handOverProcIntraEnbEntry  71 }


	hoFailPrepIncInterFreqIntraEnbSrs		 OBJECT-TYPE
		SYNTAX					 Counter32
		MAX-ACCESS			 read-only
		STATUS					 current
		DESCRIPTION			 " -- "
		::=  { handOverProcIntraEnbEntry  72 }


	hoFailPrepIncInterFreqIntraEnbParameterError		 OBJECT-TYPE
		SYNTAX					 Counter32
		MAX-ACCESS			 read-only
		STATUS					 current
		DESCRIPTION			 " -- "
		::=  { handOverProcIntraEnbEntry  73 }


	hoFailPrepIncInterFreqIntraEnbOthers		 OBJECT-TYPE
		SYNTAX					 Counter32
		MAX-ACCESS			 read-only
		STATUS					 current
		DESCRIPTION			 " -- "
		::=  { handOverProcIntraEnbEntry  74 }


	ueAccNumTable		 OBJECT-TYPE
		SYNTAX					 SEQUENCE  OF	 UeAccNumEntry
		MAX-ACCESS			 not-accessible
		STATUS					 current
		DESCRIPTION			 " -- "
		::=  { rrcrelatedOriginCounter  10 }


	ueAccNumEntry		 OBJECT-TYPE
		SYNTAX					 UeAccNumEntry
		MAX-ACCESS			 not-accessible
		STATUS					 current
		DESCRIPTION			 " -- "
		INDEX						{ ueAccNumLcId }
		::=  { ueAccNumTable  1 }


	UeAccNumEntry		 ::=  SEQUENCE {
		ueAccNumLcId					Integer32,
		ueAccNumRowStatus					RowStatus,
		ueaccPreambleSendNum					Counter32,
		ueaccPreambleContentNum					Counter32,
		ueaccPreambleSuccNum					Counter32
		}


	ueAccNumLcId		 OBJECT-TYPE
		SYNTAX					 Integer32( 0 .. 23 )
		MAX-ACCESS			 not-accessible
		STATUS					 current
		DESCRIPTION			 " -- "
		::=  { ueAccNumEntry  1 }


	ueAccNumRowStatus		 OBJECT-TYPE
		SYNTAX					 RowStatus
		MAX-ACCESS			 read-only
		STATUS					 current
		DESCRIPTION			 " -- "
		::=  { ueAccNumEntry  2 }


	ueaccPreambleSendNum		 OBJECT-TYPE
		SYNTAX					 Counter32
		MAX-ACCESS			 read-only
		STATUS					 current
		DESCRIPTION			 " -- "
		::=  { ueAccNumEntry  3 }


	ueaccPreambleContentNum		 OBJECT-TYPE
		SYNTAX					 Counter32
		MAX-ACCESS			 read-only
		STATUS					 current
		DESCRIPTION			 " -- "
		::=  { ueAccNumEntry  4 }


	ueaccPreambleSuccNum		 OBJECT-TYPE
		SYNTAX					 Counter32
		MAX-ACCESS			 read-only
		STATUS					 current
		DESCRIPTION			 " -- "
		::=  { ueAccNumEntry  5 }


	intraRATInterCellHOTable		 OBJECT-TYPE
		SYNTAX					 SEQUENCE  OF	 IntraRATInterCellHOEntry
		MAX-ACCESS			 not-accessible
		STATUS					 current
		DESCRIPTION			 " -- "
		::=  { rrcrelatedOriginCounter  11 }


	intraRATInterCellHOEntry		 OBJECT-TYPE
		SYNTAX					 IntraRATInterCellHOEntry
		MAX-ACCESS			 not-accessible
		STATUS					 current
		DESCRIPTION			 " -- "
		INDEX						{ intraRATInterCellHOLcId }
		::=  { intraRATInterCellHOTable  1 }


	IntraRATInterCellHOEntry		 ::=  SEQUENCE {
		intraRATInterCellHOLcId					Integer32,
		intraRATInterCellHORowStatus					RowStatus,
		hoOutAttIntraFreqRadio					Counter32,
		hoSuccOutIntraFreqRadio					Counter32,
		hoOutAttInterFreqRadio					Counter32,
		hoSuccOutInterFreqRadio					Counter32,
		hoOutAttIntraFreqLoadBalance					Counter32,
		hoSuccOutIntraFreqLoadBalance					Counter32,
		hoOutAttInterFreqLoadBalance					Counter32,
		hoSuccOutInterFreqLoadBalance					Counter32,
		hoOutAttIntraFreqOMC					Counter32,
		hoSuccOutIntraFreqOMC					Counter32,
		hoOutAttInterFreqOMC					Counter32,
		hoSuccOutInterFreqOMC					Counter32,
		hoAttOutIntraFreq					Counter32,
		hoAttOutInterFreq					Counter32,
		hoAttOutInterEnb					Counter32,
		hoFailOutS1Prep					Counter32,
		hoFailOutX2Prep					Counter32,
		hoFailOutIntraEnbPrep					Counter32,
		hoFailOutRRCReConn					Counter32,
		hoFailOutHoExeTimeOut					Counter32,
		hoFailOutOther					Counter32,
		hoCoverHoleSum					Counter32,
		hoOutAttIntraFreqService					Counter32,
		hoSuccOutIntraFreqService					Counter32,
		hoOutAttInterFreqService					Counter32,
		hoSuccOutInterFreqService					Counter32,
		hoHoPreAttRadio					Counter32,
		hoHoPreSuccRadio					Counter32,
		hoHoPreAttLB					Counter32,
		hoHoPreSuccLB					Counter32,
		hoHoPreAttSV					Counter32,
		hoHoPreSuccSV					Counter32,
		hoHoPreAttOMC					Counter32,
		hoHoPreSuccOMC					Counter32,
		hoFailOutHoPrepTimeOut					Counter32
		}


	intraRATInterCellHOLcId		 OBJECT-TYPE
		SYNTAX					 Integer32( 0 .. 23 )
		MAX-ACCESS			 not-accessible
		STATUS					 current
		DESCRIPTION			 " -- "
		::=  { intraRATInterCellHOEntry  1 }


	intraRATInterCellHORowStatus		 OBJECT-TYPE
		SYNTAX					 RowStatus
		MAX-ACCESS			 read-only
		STATUS					 current
		DESCRIPTION			 " -- "
		::=  { intraRATInterCellHOEntry  2 }


	hoOutAttIntraFreqRadio		 OBJECT-TYPE
		SYNTAX					 Counter32
		MAX-ACCESS			 read-only
		STATUS					 current
		DESCRIPTION			 " -- "
		::=  { intraRATInterCellHOEntry  3 }


	hoSuccOutIntraFreqRadio		 OBJECT-TYPE
		SYNTAX					 Counter32
		MAX-ACCESS			 read-only
		STATUS					 current
		DESCRIPTION			 " -- "
		::=  { intraRATInterCellHOEntry  4 }


	hoOutAttInterFreqRadio		 OBJECT-TYPE
		SYNTAX					 Counter32
		MAX-ACCESS			 read-only
		STATUS					 current
		DESCRIPTION			 " -- "
		::=  { intraRATInterCellHOEntry  5 }


	hoSuccOutInterFreqRadio		 OBJECT-TYPE
		SYNTAX					 Counter32
		MAX-ACCESS			 read-only
		STATUS					 current
		DESCRIPTION			 " -- "
		::=  { intraRATInterCellHOEntry  6 }


	hoOutAttIntraFreqLoadBalance		 OBJECT-TYPE
		SYNTAX					 Counter32
		MAX-ACCESS			 read-only
		STATUS					 current
		DESCRIPTION			 " -- "
		::=  { intraRATInterCellHOEntry  7 }


	hoSuccOutIntraFreqLoadBalance		 OBJECT-TYPE
		SYNTAX					 Counter32
		MAX-ACCESS			 read-only
		STATUS					 current
		DESCRIPTION			 " -- "
		::=  { intraRATInterCellHOEntry  8 }


	hoOutAttInterFreqLoadBalance		 OBJECT-TYPE
		SYNTAX					 Counter32
		MAX-ACCESS			 read-only
		STATUS					 current
		DESCRIPTION			 " -- "
		::=  { intraRATInterCellHOEntry  9 }


	hoSuccOutInterFreqLoadBalance		 OBJECT-TYPE
		SYNTAX					 Counter32
		MAX-ACCESS			 read-only
		STATUS					 current
		DESCRIPTION			 " -- "
		::=  { intraRATInterCellHOEntry  10 }


	hoOutAttIntraFreqOMC		 OBJECT-TYPE
		SYNTAX					 Counter32
		MAX-ACCESS			 read-only
		STATUS					 current
		DESCRIPTION			 " -- "
		::=  { intraRATInterCellHOEntry  11 }


	hoSuccOutIntraFreqOMC		 OBJECT-TYPE
		SYNTAX					 Counter32
		MAX-ACCESS			 read-only
		STATUS					 current
		DESCRIPTION			 " -- "
		::=  { intraRATInterCellHOEntry  12 }


	hoOutAttInterFreqOMC		 OBJECT-TYPE
		SYNTAX					 Counter32
		MAX-ACCESS			 read-only
		STATUS					 current
		DESCRIPTION			 " -- "
		::=  { intraRATInterCellHOEntry  13 }


	hoSuccOutInterFreqOMC		 OBJECT-TYPE
		SYNTAX					 Counter32
		MAX-ACCESS			 read-only
		STATUS					 current
		DESCRIPTION			 " -- "
		::=  { intraRATInterCellHOEntry  14 }


	hoAttOutIntraFreq		 OBJECT-TYPE
		SYNTAX					 Counter32
		MAX-ACCESS			 read-only
		STATUS					 current
		DESCRIPTION			 " -- "
		::=  { intraRATInterCellHOEntry  15 }


	hoAttOutInterFreq		 OBJECT-TYPE
		SYNTAX					 Counter32
		MAX-ACCESS			 read-only
		STATUS					 current
		DESCRIPTION			 " -- "
		::=  { intraRATInterCellHOEntry  16 }


	hoAttOutInterEnb		 OBJECT-TYPE
		SYNTAX					 Counter32
		MAX-ACCESS			 read-only
		STATUS					 current
		DESCRIPTION			 " -- "
		::=  { intraRATInterCellHOEntry  17 }


	hoFailOutS1Prep		 OBJECT-TYPE
		SYNTAX					 Counter32
		MAX-ACCESS			 read-only
		STATUS					 current
		DESCRIPTION			 " -- "
		::=  { intraRATInterCellHOEntry  18 }


	hoFailOutX2Prep		 OBJECT-TYPE
		SYNTAX					 Counter32
		MAX-ACCESS			 read-only
		STATUS					 current
		DESCRIPTION			 " -- "
		::=  { intraRATInterCellHOEntry  19 }


	hoFailOutIntraEnbPrep		 OBJECT-TYPE
		SYNTAX					 Counter32
		MAX-ACCESS			 read-only
		STATUS					 current
		DESCRIPTION			 " -- "
		::=  { intraRATInterCellHOEntry  20 }


	hoFailOutRRCReConn		 OBJECT-TYPE
		SYNTAX					 Counter32
		MAX-ACCESS			 read-only
		STATUS					 current
		DESCRIPTION			 " -- "
		::=  { intraRATInterCellHOEntry  21 }


	hoFailOutHoExeTimeOut		 OBJECT-TYPE
		SYNTAX					 Counter32
		MAX-ACCESS			 read-only
		STATUS					 current
		DESCRIPTION			 " -- "
		::=  { intraRATInterCellHOEntry  22 }


	hoFailOutOther		 OBJECT-TYPE
		SYNTAX					 Counter32
		MAX-ACCESS			 read-only
		STATUS					 current
		DESCRIPTION			 " -- "
		::=  { intraRATInterCellHOEntry  23 }


	hoCoverHoleSum		 OBJECT-TYPE
		SYNTAX					 Counter32
		MAX-ACCESS			 read-only
		STATUS					 current
		DESCRIPTION			 " -- "
		::=  { intraRATInterCellHOEntry  24 }


	hoOutAttIntraFreqService		 OBJECT-TYPE
		SYNTAX					 Counter32
		MAX-ACCESS			 read-only
		STATUS					 current
		DESCRIPTION			 " -- "
		::=  { intraRATInterCellHOEntry  25 }


	hoSuccOutIntraFreqService		 OBJECT-TYPE
		SYNTAX					 Counter32
		MAX-ACCESS			 read-only
		STATUS					 current
		DESCRIPTION			 " -- "
		::=  { intraRATInterCellHOEntry  26 }


	hoOutAttInterFreqService		 OBJECT-TYPE
		SYNTAX					 Counter32
		MAX-ACCESS			 read-only
		STATUS					 current
		DESCRIPTION			 " -- "
		::=  { intraRATInterCellHOEntry  27 }


	hoSuccOutInterFreqService		 OBJECT-TYPE
		SYNTAX					 Counter32
		MAX-ACCESS			 read-only
		STATUS					 current
		DESCRIPTION			 " -- "
		::=  { intraRATInterCellHOEntry  28 }


	hoHoPreAttRadio		 OBJECT-TYPE
		SYNTAX					 Counter32
		MAX-ACCESS			 read-only
		STATUS					 current
		DESCRIPTION			 " -- "
		::=  { intraRATInterCellHOEntry  29 }


	hoHoPreSuccRadio		 OBJECT-TYPE
		SYNTAX					 Counter32
		MAX-ACCESS			 read-only
		STATUS					 current
		DESCRIPTION			 " -- "
		::=  { intraRATInterCellHOEntry  30 }


	hoHoPreAttLB		 OBJECT-TYPE
		SYNTAX					 Counter32
		MAX-ACCESS			 read-only
		STATUS					 current
		DESCRIPTION			 " -- "
		::=  { intraRATInterCellHOEntry  31 }


	hoHoPreSuccLB		 OBJECT-TYPE
		SYNTAX					 Counter32
		MAX-ACCESS			 read-only
		STATUS					 current
		DESCRIPTION			 " -- "
		::=  { intraRATInterCellHOEntry  32 }


	hoHoPreAttSV		 OBJECT-TYPE
		SYNTAX					 Counter32
		MAX-ACCESS			 read-only
		STATUS					 current
		DESCRIPTION			 " -- "
		::=  { intraRATInterCellHOEntry  33 }


	hoHoPreSuccSV		 OBJECT-TYPE
		SYNTAX					 Counter32
		MAX-ACCESS			 read-only
		STATUS					 current
		DESCRIPTION			 " -- "
		::=  { intraRATInterCellHOEntry  34 }


	hoHoPreAttOMC		 OBJECT-TYPE
		SYNTAX					 Counter32
		MAX-ACCESS			 read-only
		STATUS					 current
		DESCRIPTION			 " -- "
		::=  { intraRATInterCellHOEntry  35 }


	hoHoPreSuccOMC		 OBJECT-TYPE
		SYNTAX					 Counter32
		MAX-ACCESS			 read-only
		STATUS					 current
		DESCRIPTION			 " -- "
		::=  { intraRATInterCellHOEntry  36 }


	hoFailOutHoPrepTimeOut		 OBJECT-TYPE
		SYNTAX					 Counter32
		MAX-ACCESS			 read-only
		STATUS					 current
		DESCRIPTION			 " -- "
		::=  { intraRATInterCellHOEntry  37 }


	s1hoCancelProcInterEnbTable		 OBJECT-TYPE
		SYNTAX					 SEQUENCE  OF	 S1hoCancelProcInterEnbEntry
		MAX-ACCESS			 not-accessible
		STATUS					 current
		DESCRIPTION			 " -- "
		::=  { rrcrelatedOriginCounter  12 }


	s1hoCancelProcInterEnbEntry		 OBJECT-TYPE
		SYNTAX					 S1hoCancelProcInterEnbEntry
		MAX-ACCESS			 not-accessible
		STATUS					 current
		DESCRIPTION			 " -- "
		INDEX						{ s1hoCancelProcInterEnbLcId }
		::=  { s1hoCancelProcInterEnbTable  1 }


	S1hoCancelProcInterEnbEntry		 ::=  SEQUENCE {
		s1hoCancelProcInterEnbLcId					Integer32,
		s1hoCancelProcInterEnbRowStatus					RowStatus,
		hoCancelIntraFreqIntraEnbS1HandOverSucc					Counter32,
		hoCancelIntraFreqInterEnbS1HandOverFail					Counter32,
		hoCancelAckIntraFreqInterEnbS1					Counter32,
		hoCancelInterFreqInterEnbS1HandOverSucc					Counter32,
		hoCancelInterFreqInterEnbS1HandOverFail					Counter32,
		hoCancelAckInterFreqInterEnbS1					Counter32
		}


	s1hoCancelProcInterEnbLcId		 OBJECT-TYPE
		SYNTAX					 Integer32( 0 .. 23 )
		MAX-ACCESS			 not-accessible
		STATUS					 current
		DESCRIPTION			 " -- "
		::=  { s1hoCancelProcInterEnbEntry  1 }


	s1hoCancelProcInterEnbRowStatus		 OBJECT-TYPE
		SYNTAX					 RowStatus
		MAX-ACCESS			 read-only
		STATUS					 current
		DESCRIPTION			 " -- "
		::=  { s1hoCancelProcInterEnbEntry  2 }


	hoCancelIntraFreqIntraEnbS1HandOverSucc		 OBJECT-TYPE
		SYNTAX					 Counter32
		MAX-ACCESS			 read-only
		STATUS					 current
		DESCRIPTION			 " -- "
		::=  { s1hoCancelProcInterEnbEntry  3 }


	hoCancelIntraFreqInterEnbS1HandOverFail		 OBJECT-TYPE
		SYNTAX					 Counter32
		MAX-ACCESS			 read-only
		STATUS					 current
		DESCRIPTION			 " -- "
		::=  { s1hoCancelProcInterEnbEntry  4 }


	hoCancelAckIntraFreqInterEnbS1		 OBJECT-TYPE
		SYNTAX					 Counter32
		MAX-ACCESS			 read-only
		STATUS					 current
		DESCRIPTION			 " -- "
		::=  { s1hoCancelProcInterEnbEntry  5 }


	hoCancelInterFreqInterEnbS1HandOverSucc		 OBJECT-TYPE
		SYNTAX					 Counter32
		MAX-ACCESS			 read-only
		STATUS					 current
		DESCRIPTION			 " -- "
		::=  { s1hoCancelProcInterEnbEntry  6 }


	hoCancelInterFreqInterEnbS1HandOverFail		 OBJECT-TYPE
		SYNTAX					 Counter32
		MAX-ACCESS			 read-only
		STATUS					 current
		DESCRIPTION			 " -- "
		::=  { s1hoCancelProcInterEnbEntry  7 }


	hoCancelAckInterFreqInterEnbS1		 OBJECT-TYPE
		SYNTAX					 Counter32
		MAX-ACCESS			 read-only
		STATUS					 current
		DESCRIPTION			 " -- "
		::=  { s1hoCancelProcInterEnbEntry  8 }


	x2hoCancelProcInterEnbTable		 OBJECT-TYPE
		SYNTAX					 SEQUENCE  OF	 X2hoCancelProcInterEnbEntry
		MAX-ACCESS			 not-accessible
		STATUS					 current
		DESCRIPTION			 " -- "
		::=  { rrcrelatedOriginCounter  13 }


	x2hoCancelProcInterEnbEntry		 OBJECT-TYPE
		SYNTAX					 X2hoCancelProcInterEnbEntry
		MAX-ACCESS			 not-accessible
		STATUS					 current
		DESCRIPTION			 " -- "
		INDEX						{ x2hoCancelProcInterEnbLcId }
		::=  { x2hoCancelProcInterEnbTable  1 }


	X2hoCancelProcInterEnbEntry		 ::=  SEQUENCE {
		x2hoCancelProcInterEnbLcId					Integer32,
		x2hoCancelProcInterEnbRowStatus					RowStatus,
		hoCancelIntraFreqIntraEnbX2HandOverSucc					Counter32,
		hoCancelIntraFreqIntraEnbX2HandOverFail					Counter32,
		hoCancelInterFreqInterEnbX2HandOverSucc					Counter32,
		hoCancelInterFreqInterEnbX2HandOverFail					Counter32
		}


	x2hoCancelProcInterEnbLcId		 OBJECT-TYPE
		SYNTAX					 Integer32( 0 .. 23 )
		MAX-ACCESS			 not-accessible
		STATUS					 current
		DESCRIPTION			 " -- "
		::=  { x2hoCancelProcInterEnbEntry  1 }


	x2hoCancelProcInterEnbRowStatus		 OBJECT-TYPE
		SYNTAX					 RowStatus
		MAX-ACCESS			 read-only
		STATUS					 current
		DESCRIPTION			 " -- "
		::=  { x2hoCancelProcInterEnbEntry  2 }


	hoCancelIntraFreqIntraEnbX2HandOverSucc		 OBJECT-TYPE
		SYNTAX					 Counter32
		MAX-ACCESS			 read-only
		STATUS					 current
		DESCRIPTION			 " -- "
		::=  { x2hoCancelProcInterEnbEntry  3 }


	hoCancelIntraFreqIntraEnbX2HandOverFail		 OBJECT-TYPE
		SYNTAX					 Counter32
		MAX-ACCESS			 read-only
		STATUS					 current
		DESCRIPTION			 " -- "
		::=  { x2hoCancelProcInterEnbEntry  4 }


	hoCancelInterFreqInterEnbX2HandOverSucc		 OBJECT-TYPE
		SYNTAX					 Counter32
		MAX-ACCESS			 read-only
		STATUS					 current
		DESCRIPTION			 " -- "
		::=  { x2hoCancelProcInterEnbEntry  5 }


	hoCancelInterFreqInterEnbX2HandOverFail		 OBJECT-TYPE
		SYNTAX					 Counter32
		MAX-ACCESS			 read-only
		STATUS					 current
		DESCRIPTION			 " -- "
		::=  { x2hoCancelProcInterEnbEntry  6 }


	handOverInterRATTable		 OBJECT-TYPE
		SYNTAX					 SEQUENCE  OF	 HandOverInterRATEntry
		MAX-ACCESS			 not-accessible
		STATUS					 current
		DESCRIPTION			 " -- "
		::=  { rrcrelatedOriginCounter  14 }


	handOverInterRATEntry		 OBJECT-TYPE
		SYNTAX					 HandOverInterRATEntry
		MAX-ACCESS			 not-accessible
		STATUS					 current
		DESCRIPTION			 " -- "
		INDEX						{ handOverInterRATLcId }
		::=  { handOverInterRATTable  1 }


	HandOverInterRATEntry		 ::=  SEQUENCE {
		handOverInterRATLcId					Integer32,
		handOverInterRATRowStatus					RowStatus,
		irathoAttOutGprs					Counter32,
		irathoSuccOutGprs					Counter32,
		irathoFailOutGprs					Counter32,
		irathoAttOutTdscdma					Counter32,
		irathoSuccOutUtran					Counter32,
		irathoFailOutTdscdma					Counter32,
		irathoAttOutCdma2000					Counter32,
		irathoAttIncGprs					Counter32,
		irathoSuccIncGprs					Counter32,
		irathoAttIncTdscdma					Counter32,
		irathoSuccIncTdscdma					Counter32,
		irathoAttPrepOutGprs					Counter32,
		irathoSuccPrepOutGprs					Counter32,
		irathoFailPrepOutGprsOverTime					Counter32,
		irathoFailPrepOutGprsSyntaxError					Counter32,
		irathoFailPrepOutGprsTgtEpcEnbSystemFailure					Counter32,
		irathoFailPrepOutGprsOtherFailure					Counter32,
		irathoAttPrepOutUtran					Counter32,
		irathoSuccPrepOutUtran					Counter32,
		irathoFailPrepOutUtranOverTime					Counter32,
		irathoFailPrepOutUtranSyntaxError					Counter32,
		irathoFailPrepOutUtranTgtEpcEnbSystemFailure					Counter32,
		irathoFailPrepOutUtranOtherFailure					Counter32,
		irathoAttPrepIncGprs					Counter32,
		irathoSuccPrepIncGprs					Counter32,
		irathoFailPrepIncGprsResourceAllocFailure					Counter32,
		irathoFailPrepIncGprsCacFailure					Counter32,
		irathoFailPrepIncGprsInstFailure					Counter32,
		irathoFailPrepIncGprsPerFailure					Counter32,
		irathoFailPrepIncGprsOthers					Counter32,
		irathoAttPrepIncUtran					Counter32,
		irathoSuccPrepIncUtran					Counter32,
		irathoFailPrepIncUtranResourceAllocFailure					Counter32,
		irathoFailPrepIncUtranCacFailure					Counter32,
		irathoFailPrepIncUtranInstFailure					Counter32,
		irathoFailPrepIncUtranPerFailure					Counter32,
		irathoFailPrepIncUtranOthers					Counter32
		}


	handOverInterRATLcId		 OBJECT-TYPE
		SYNTAX					 Integer32( 0 .. 23 )
		MAX-ACCESS			 not-accessible
		STATUS					 current
		DESCRIPTION			 " -- "
		::=  { handOverInterRATEntry  1 }


	handOverInterRATRowStatus		 OBJECT-TYPE
		SYNTAX					 RowStatus
		MAX-ACCESS			 read-only
		STATUS					 current
		DESCRIPTION			 " -- "
		::=  { handOverInterRATEntry  2 }


	irathoAttOutGprs		 OBJECT-TYPE
		SYNTAX					 Counter32
		MAX-ACCESS			 read-only
		STATUS					 current
		DESCRIPTION			 " -- "
		::=  { handOverInterRATEntry  3 }


	irathoSuccOutGprs		 OBJECT-TYPE
		SYNTAX					 Counter32
		MAX-ACCESS			 read-only
		STATUS					 current
		DESCRIPTION			 " -- "
		::=  { handOverInterRATEntry  4 }


	irathoFailOutGprs		 OBJECT-TYPE
		SYNTAX					 Counter32
		MAX-ACCESS			 read-only
		STATUS					 current
		DESCRIPTION			 " -- "
		::=  { handOverInterRATEntry  5 }


	irathoAttOutTdscdma		 OBJECT-TYPE
		SYNTAX					 Counter32
		MAX-ACCESS			 read-only
		STATUS					 current
		DESCRIPTION			 " -- "
		::=  { handOverInterRATEntry  6 }


	irathoSuccOutUtran		 OBJECT-TYPE
		SYNTAX					 Counter32
		MAX-ACCESS			 read-only
		STATUS					 current
		DESCRIPTION			 " -- "
		::=  { handOverInterRATEntry  7 }


	irathoFailOutTdscdma		 OBJECT-TYPE
		SYNTAX					 Counter32
		MAX-ACCESS			 read-only
		STATUS					 current
		DESCRIPTION			 " -- "
		::=  { handOverInterRATEntry  8 }


	irathoAttOutCdma2000		 OBJECT-TYPE
		SYNTAX					 Counter32
		MAX-ACCESS			 read-only
		STATUS					 current
		DESCRIPTION			 " -- "
		::=  { handOverInterRATEntry  9 }


	irathoAttIncGprs		 OBJECT-TYPE
		SYNTAX					 Counter32
		MAX-ACCESS			 read-only
		STATUS					 current
		DESCRIPTION			 " -- "
		::=  { handOverInterRATEntry  10 }


	irathoSuccIncGprs		 OBJECT-TYPE
		SYNTAX					 Counter32
		MAX-ACCESS			 read-only
		STATUS					 current
		DESCRIPTION			 " -- "
		::=  { handOverInterRATEntry  11 }


	irathoAttIncTdscdma		 OBJECT-TYPE
		SYNTAX					 Counter32
		MAX-ACCESS			 read-only
		STATUS					 current
		DESCRIPTION			 " -- "
		::=  { handOverInterRATEntry  12 }


	irathoSuccIncTdscdma		 OBJECT-TYPE
		SYNTAX					 Counter32
		MAX-ACCESS			 read-only
		STATUS					 current
		DESCRIPTION			 " -- "
		::=  { handOverInterRATEntry  13 }


	irathoAttPrepOutGprs		 OBJECT-TYPE
		SYNTAX					 Counter32
		MAX-ACCESS			 read-only
		STATUS					 current
		DESCRIPTION			 " -- "
		::=  { handOverInterRATEntry  14 }


	irathoSuccPrepOutGprs		 OBJECT-TYPE
		SYNTAX					 Counter32
		MAX-ACCESS			 read-only
		STATUS					 current
		DESCRIPTION			 " -- "
		::=  { handOverInterRATEntry  15 }


	irathoFailPrepOutGprsOverTime		 OBJECT-TYPE
		SYNTAX					 Counter32
		MAX-ACCESS			 read-only
		STATUS					 current
		DESCRIPTION			 " -- "
		::=  { handOverInterRATEntry  16 }


	irathoFailPrepOutGprsSyntaxError		 OBJECT-TYPE
		SYNTAX					 Counter32
		MAX-ACCESS			 read-only
		STATUS					 current
		DESCRIPTION			 " -- "
		::=  { handOverInterRATEntry  17 }


	irathoFailPrepOutGprsTgtEpcEnbSystemFailure		 OBJECT-TYPE
		SYNTAX					 Counter32
		MAX-ACCESS			 read-only
		STATUS					 current
		DESCRIPTION			 " -- "
		::=  { handOverInterRATEntry  18 }


	irathoFailPrepOutGprsOtherFailure		 OBJECT-TYPE
		SYNTAX					 Counter32
		MAX-ACCESS			 read-only
		STATUS					 current
		DESCRIPTION			 " -- "
		::=  { handOverInterRATEntry  19 }


	irathoAttPrepOutUtran		 OBJECT-TYPE
		SYNTAX					 Counter32
		MAX-ACCESS			 read-only
		STATUS					 current
		DESCRIPTION			 " -- "
		::=  { handOverInterRATEntry  20 }


	irathoSuccPrepOutUtran		 OBJECT-TYPE
		SYNTAX					 Counter32
		MAX-ACCESS			 read-only
		STATUS					 current
		DESCRIPTION			 " -- "
		::=  { handOverInterRATEntry  21 }


	irathoFailPrepOutUtranOverTime		 OBJECT-TYPE
		SYNTAX					 Counter32
		MAX-ACCESS			 read-only
		STATUS					 current
		DESCRIPTION			 " -- "
		::=  { handOverInterRATEntry  22 }


	irathoFailPrepOutUtranSyntaxError		 OBJECT-TYPE
		SYNTAX					 Counter32
		MAX-ACCESS			 read-only
		STATUS					 current
		DESCRIPTION			 " -- "
		::=  { handOverInterRATEntry  23 }


	irathoFailPrepOutUtranTgtEpcEnbSystemFailure		 OBJECT-TYPE
		SYNTAX					 Counter32
		MAX-ACCESS			 read-only
		STATUS					 current
		DESCRIPTION			 " -- "
		::=  { handOverInterRATEntry  24 }


	irathoFailPrepOutUtranOtherFailure		 OBJECT-TYPE
		SYNTAX					 Counter32
		MAX-ACCESS			 read-only
		STATUS					 current
		DESCRIPTION			 " -- "
		::=  { handOverInterRATEntry  25 }


	irathoAttPrepIncGprs		 OBJECT-TYPE
		SYNTAX					 Counter32
		MAX-ACCESS			 read-only
		STATUS					 current
		DESCRIPTION			 " -- "
		::=  { handOverInterRATEntry  26 }


	irathoSuccPrepIncGprs		 OBJECT-TYPE
		SYNTAX					 Counter32
		MAX-ACCESS			 read-only
		STATUS					 current
		DESCRIPTION			 " -- "
		::=  { handOverInterRATEntry  27 }


	irathoFailPrepIncGprsResourceAllocFailure		 OBJECT-TYPE
		SYNTAX					 Counter32
		MAX-ACCESS			 read-only
		STATUS					 current
		DESCRIPTION			 " -- "
		::=  { handOverInterRATEntry  28 }


	irathoFailPrepIncGprsCacFailure		 OBJECT-TYPE
		SYNTAX					 Counter32
		MAX-ACCESS			 read-only
		STATUS					 current
		DESCRIPTION			 " -- "
		::=  { handOverInterRATEntry  29 }


	irathoFailPrepIncGprsInstFailure		 OBJECT-TYPE
		SYNTAX					 Counter32
		MAX-ACCESS			 read-only
		STATUS					 current
		DESCRIPTION			 " -- "
		::=  { handOverInterRATEntry  30 }


	irathoFailPrepIncGprsPerFailure		 OBJECT-TYPE
		SYNTAX					 Counter32
		MAX-ACCESS			 read-only
		STATUS					 current
		DESCRIPTION			 " -- "
		::=  { handOverInterRATEntry  31 }


	irathoFailPrepIncGprsOthers		 OBJECT-TYPE
		SYNTAX					 Counter32
		MAX-ACCESS			 read-only
		STATUS					 current
		DESCRIPTION			 " -- "
		::=  { handOverInterRATEntry  32 }


	irathoAttPrepIncUtran		 OBJECT-TYPE
		SYNTAX					 Counter32
		MAX-ACCESS			 read-only
		STATUS					 current
		DESCRIPTION			 " -- "
		::=  { handOverInterRATEntry  33 }


	irathoSuccPrepIncUtran		 OBJECT-TYPE
		SYNTAX					 Counter32
		MAX-ACCESS			 read-only
		STATUS					 current
		DESCRIPTION			 " -- "
		::=  { handOverInterRATEntry  34 }


	irathoFailPrepIncUtranResourceAllocFailure		 OBJECT-TYPE
		SYNTAX					 Counter32
		MAX-ACCESS			 read-only
		STATUS					 current
		DESCRIPTION			 " -- "
		::=  { handOverInterRATEntry  35 }


	irathoFailPrepIncUtranCacFailure		 OBJECT-TYPE
		SYNTAX					 Counter32
		MAX-ACCESS			 read-only
		STATUS					 current
		DESCRIPTION			 " -- "
		::=  { handOverInterRATEntry  36 }


	irathoFailPrepIncUtranInstFailure		 OBJECT-TYPE
		SYNTAX					 Counter32
		MAX-ACCESS			 read-only
		STATUS					 current
		DESCRIPTION			 " -- "
		::=  { handOverInterRATEntry  37 }


	irathoFailPrepIncUtranPerFailure		 OBJECT-TYPE
		SYNTAX					 Counter32
		MAX-ACCESS			 read-only
		STATUS					 current
		DESCRIPTION			 " -- "
		::=  { handOverInterRATEntry  38 }


	irathoFailPrepIncUtranOthers		 OBJECT-TYPE
		SYNTAX					 Counter32
		MAX-ACCESS			 read-only
		STATUS					 current
		DESCRIPTION			 " -- "
		::=  { handOverInterRATEntry  39 }


	douAdjcHandOverProcedureTable		 OBJECT-TYPE
		SYNTAX					 SEQUENCE  OF	 DouAdjcHandOverProcedureEntry
		MAX-ACCESS			 not-accessible
		STATUS					 current
		DESCRIPTION			 " -- "
		::=  { rrcrelatedOriginCounter  15 }


	douAdjcHandOverProcedureEntry		 OBJECT-TYPE
		SYNTAX					 DouAdjcHandOverProcedureEntry
		MAX-ACCESS			 not-accessible
		STATUS					 current
		DESCRIPTION			 " -- "
		INDEX						{ douAdjcHandOverProcedureCellAdjCellLcId,douAdjcHandOverProcedureCellAdjCellIndex }
		::=  { douAdjcHandOverProcedureTable  1 }


	DouAdjcHandOverProcedureEntry		 ::=  SEQUENCE {
		douAdjcHandOverProcedureCellAdjCellLcId					Integer32,
		douAdjcHandOverProcedureCellAdjCellIndex					Integer32,
		douAdjcHandOverProcedureRowStatus					RowStatus,
		hoOutAttMeasure					Counter32,
		hoOutSuccMeasure					Counter32,
		hoOutAttLoadBalance					Counter32,
		hoOutSuccLoadBalance					Counter32,
		hoOutFailTooEarly					Counter32,
		hoOutFailTooLate					Counter32,
		hoOutFailToWrongCell					Counter32,
		hoOutSuccMro					Counter32,
		hoOutFailPingpong					Counter32,
		hoHoPreAttTarget					Counter32,
		hoHoPreSuccTarget					Counter32,
		hoOutPrepFailCauseTCellNoResponse					Counter32,
		hoOutPrepFailCauseHOPrepFailureMsg					Counter32,
		hoOutFailTooEarlyType1					Counter32,
		hoOutFailTooEarlyType2					Counter32,
		hoOutFailTooLateType1					Counter32,
		hoOutFailTooLateType2					Counter32,
		hoOutFailToWrongCellType1					Counter32,
		hoOutFailToWrongCellType2					Counter32,
		hoAdjCellDiscvNum					Counter32,
		hoOutAttMLBMeasure					Counter32,
		hoOutSuccMLBMro					Counter32,
		hoOutFailMLBPingpong					Counter32,
		hoOutFailMLBTooEarlyType1					Counter32,
		hoOutFailMLBTooEarlyType2					Counter32,
		hoOutFailMLBTooLateType1					Counter32,
		hoOutFailMLBTooLateType2					Counter32,
		hoOutFailMLBToWrongCellType1					Counter32,
		hoOutFailMLBToWrongCellType2					Counter32,
		hoHoPreAttQci1					Counter32,
		hoHoPreSuccQci1					Counter32,
		hoOutAttQci1					Counter32,
		hoOutSuccQci1					Counter32,
		hoNcHoPreAttM					Counter32,
		hoNcHoPreSuccM					Counter32,
		hoNcHoPreAttLB					Counter32,
		hoNcHoPreSuccLB					Counter32,
		hoNcHoPreAttS					Counter32,
		hoNcHoPreSuccS					Counter32,
		hoOutAttS					Counter32,
		hoOutSuccS					Counter32
		}


	douAdjcHandOverProcedureCellAdjCellLcId		 OBJECT-TYPE
		SYNTAX					 Integer32( 0 .. 23 )
		MAX-ACCESS			 not-accessible
		STATUS					 current
		DESCRIPTION			 " -- "
		::=  { douAdjcHandOverProcedureEntry  1 }


	douAdjcHandOverProcedureCellAdjCellIndex		 OBJECT-TYPE
		SYNTAX					 Integer32( 1 .. 256 )
		MAX-ACCESS			 not-accessible
		STATUS					 current
		DESCRIPTION			 " -- "
		::=  { douAdjcHandOverProcedureEntry  2 }


	douAdjcHandOverProcedureRowStatus		 OBJECT-TYPE
		SYNTAX					 RowStatus
		MAX-ACCESS			 read-only
		STATUS					 current
		DESCRIPTION			 " -- "
		::=  { douAdjcHandOverProcedureEntry  3 }


	hoOutAttMeasure		 OBJECT-TYPE
		SYNTAX					 Counter32
		MAX-ACCESS			 read-only
		STATUS					 current
		DESCRIPTION			 " -- "
		::=  { douAdjcHandOverProcedureEntry  4 }


	hoOutSuccMeasure		 OBJECT-TYPE
		SYNTAX					 Counter32
		MAX-ACCESS			 read-only
		STATUS					 current
		DESCRIPTION			 " -- "
		::=  { douAdjcHandOverProcedureEntry  5 }


	hoOutAttLoadBalance		 OBJECT-TYPE
		SYNTAX					 Counter32
		MAX-ACCESS			 read-only
		STATUS					 current
		DESCRIPTION			 " -- "
		::=  { douAdjcHandOverProcedureEntry  6 }


	hoOutSuccLoadBalance		 OBJECT-TYPE
		SYNTAX					 Counter32
		MAX-ACCESS			 read-only
		STATUS					 current
		DESCRIPTION			 " -- "
		::=  { douAdjcHandOverProcedureEntry  7 }


	hoOutFailTooEarly		 OBJECT-TYPE
		SYNTAX					 Counter32
		MAX-ACCESS			 read-only
		STATUS					 current
		DESCRIPTION			 " -- "
		::=  { douAdjcHandOverProcedureEntry  8 }


	hoOutFailTooLate		 OBJECT-TYPE
		SYNTAX					 Counter32
		MAX-ACCESS			 read-only
		STATUS					 current
		DESCRIPTION			 " -- "
		::=  { douAdjcHandOverProcedureEntry  9 }


	hoOutFailToWrongCell		 OBJECT-TYPE
		SYNTAX					 Counter32
		MAX-ACCESS			 read-only
		STATUS					 current
		DESCRIPTION			 " -- "
		::=  { douAdjcHandOverProcedureEntry  10 }


	hoOutSuccMro		 OBJECT-TYPE
		SYNTAX					 Counter32
		MAX-ACCESS			 read-only
		STATUS					 current
		DESCRIPTION			 " -- "
		::=  { douAdjcHandOverProcedureEntry  11 }


	hoOutFailPingpong		 OBJECT-TYPE
		SYNTAX					 Counter32
		MAX-ACCESS			 read-only
		STATUS					 current
		DESCRIPTION			 " -- "
		::=  { douAdjcHandOverProcedureEntry  12 }


	hoHoPreAttTarget		 OBJECT-TYPE
		SYNTAX					 Counter32
		MAX-ACCESS			 read-only
		STATUS					 current
		DESCRIPTION			 " -- "
		::=  { douAdjcHandOverProcedureEntry  13 }


	hoHoPreSuccTarget		 OBJECT-TYPE
		SYNTAX					 Counter32
		MAX-ACCESS			 read-only
		STATUS					 current
		DESCRIPTION			 " -- "
		::=  { douAdjcHandOverProcedureEntry  14 }


	hoOutPrepFailCauseTCellNoResponse		 OBJECT-TYPE
		SYNTAX					 Counter32
		MAX-ACCESS			 read-only
		STATUS					 current
		DESCRIPTION			 " -- "
		::=  { douAdjcHandOverProcedureEntry  15 }


	hoOutPrepFailCauseHOPrepFailureMsg		 OBJECT-TYPE
		SYNTAX					 Counter32
		MAX-ACCESS			 read-only
		STATUS					 current
		DESCRIPTION			 " -- "
		::=  { douAdjcHandOverProcedureEntry  16 }


	hoOutFailTooEarlyType1		 OBJECT-TYPE
		SYNTAX					 Counter32
		MAX-ACCESS			 read-only
		STATUS					 current
		DESCRIPTION			 " -- "
		::=  { douAdjcHandOverProcedureEntry  17 }


	hoOutFailTooEarlyType2		 OBJECT-TYPE
		SYNTAX					 Counter32
		MAX-ACCESS			 read-only
		STATUS					 current
		DESCRIPTION			 " -- "
		::=  { douAdjcHandOverProcedureEntry  18 }


	hoOutFailTooLateType1		 OBJECT-TYPE
		SYNTAX					 Counter32
		MAX-ACCESS			 read-only
		STATUS					 current
		DESCRIPTION			 " -- "
		::=  { douAdjcHandOverProcedureEntry  19 }


	hoOutFailTooLateType2		 OBJECT-TYPE
		SYNTAX					 Counter32
		MAX-ACCESS			 read-only
		STATUS					 current
		DESCRIPTION			 " -- "
		::=  { douAdjcHandOverProcedureEntry  20 }


	hoOutFailToWrongCellType1		 OBJECT-TYPE
		SYNTAX					 Counter32
		MAX-ACCESS			 read-only
		STATUS					 current
		DESCRIPTION			 " -- "
		::=  { douAdjcHandOverProcedureEntry  21 }


	hoOutFailToWrongCellType2		 OBJECT-TYPE
		SYNTAX					 Counter32
		MAX-ACCESS			 read-only
		STATUS					 current
		DESCRIPTION			 " -- "
		::=  { douAdjcHandOverProcedureEntry  22 }


	hoAdjCellDiscvNum		 OBJECT-TYPE
		SYNTAX					 Counter32
		MAX-ACCESS			 read-only
		STATUS					 current
		DESCRIPTION			 " -- "
		::=  { douAdjcHandOverProcedureEntry  23 }


	hoOutAttMLBMeasure		 OBJECT-TYPE
		SYNTAX					 Counter32
		MAX-ACCESS			 read-only
		STATUS					 current
		DESCRIPTION			 " -- "
		::=  { douAdjcHandOverProcedureEntry  24 }


	hoOutSuccMLBMro		 OBJECT-TYPE
		SYNTAX					 Counter32
		MAX-ACCESS			 read-only
		STATUS					 current
		DESCRIPTION			 " -- "
		::=  { douAdjcHandOverProcedureEntry  25 }


	hoOutFailMLBPingpong		 OBJECT-TYPE
		SYNTAX					 Counter32
		MAX-ACCESS			 read-only
		STATUS					 current
		DESCRIPTION			 " -- "
		::=  { douAdjcHandOverProcedureEntry  26 }


	hoOutFailMLBTooEarlyType1		 OBJECT-TYPE
		SYNTAX					 Counter32
		MAX-ACCESS			 read-only
		STATUS					 current
		DESCRIPTION			 " -- "
		::=  { douAdjcHandOverProcedureEntry  27 }


	hoOutFailMLBTooEarlyType2		 OBJECT-TYPE
		SYNTAX					 Counter32
		MAX-ACCESS			 read-only
		STATUS					 current
		DESCRIPTION			 " -- "
		::=  { douAdjcHandOverProcedureEntry  28 }


	hoOutFailMLBTooLateType1		 OBJECT-TYPE
		SYNTAX					 Counter32
		MAX-ACCESS			 read-only
		STATUS					 current
		DESCRIPTION			 " -- "
		::=  { douAdjcHandOverProcedureEntry  29 }


	hoOutFailMLBTooLateType2		 OBJECT-TYPE
		SYNTAX					 Counter32
		MAX-ACCESS			 read-only
		STATUS					 current
		DESCRIPTION			 " -- "
		::=  { douAdjcHandOverProcedureEntry  30 }


	hoOutFailMLBToWrongCellType1		 OBJECT-TYPE
		SYNTAX					 Counter32
		MAX-ACCESS			 read-only
		STATUS					 current
		DESCRIPTION			 " -- "
		::=  { douAdjcHandOverProcedureEntry  31 }


	hoOutFailMLBToWrongCellType2		 OBJECT-TYPE
		SYNTAX					 Counter32
		MAX-ACCESS			 read-only
		STATUS					 current
		DESCRIPTION			 " -- "
		::=  { douAdjcHandOverProcedureEntry  32 }


	hoHoPreAttQci1		 OBJECT-TYPE
		SYNTAX					 Counter32
		MAX-ACCESS			 read-only
		STATUS					 current
		DESCRIPTION			 " -- "
		::=  { douAdjcHandOverProcedureEntry  33 }


	hoHoPreSuccQci1		 OBJECT-TYPE
		SYNTAX					 Counter32
		MAX-ACCESS			 read-only
		STATUS					 current
		DESCRIPTION			 " -- "
		::=  { douAdjcHandOverProcedureEntry  34 }


	hoOutAttQci1		 OBJECT-TYPE
		SYNTAX					 Counter32
		MAX-ACCESS			 read-only
		STATUS					 current
		DESCRIPTION			 " -- "
		::=  { douAdjcHandOverProcedureEntry  35 }


	hoOutSuccQci1		 OBJECT-TYPE
		SYNTAX					 Counter32
		MAX-ACCESS			 read-only
		STATUS					 current
		DESCRIPTION			 " -- "
		::=  { douAdjcHandOverProcedureEntry  36 }


	hoNcHoPreAttM		 OBJECT-TYPE
		SYNTAX					 Counter32
		MAX-ACCESS			 read-only
		STATUS					 current
		DESCRIPTION			 " -- "
		::=  { douAdjcHandOverProcedureEntry  37 }


	hoNcHoPreSuccM		 OBJECT-TYPE
		SYNTAX					 Counter32
		MAX-ACCESS			 read-only
		STATUS					 current
		DESCRIPTION			 " -- "
		::=  { douAdjcHandOverProcedureEntry  38 }


	hoNcHoPreAttLB		 OBJECT-TYPE
		SYNTAX					 Counter32
		MAX-ACCESS			 read-only
		STATUS					 current
		DESCRIPTION			 " -- "
		::=  { douAdjcHandOverProcedureEntry  39 }


	hoNcHoPreSuccLB		 OBJECT-TYPE
		SYNTAX					 Counter32
		MAX-ACCESS			 read-only
		STATUS					 current
		DESCRIPTION			 " -- "
		::=  { douAdjcHandOverProcedureEntry  40 }


	hoNcHoPreAttS		 OBJECT-TYPE
		SYNTAX					 Counter32
		MAX-ACCESS			 read-only
		STATUS					 current
		DESCRIPTION			 " -- "
		::=  { douAdjcHandOverProcedureEntry  41 }


	hoNcHoPreSuccS		 OBJECT-TYPE
		SYNTAX					 Counter32
		MAX-ACCESS			 read-only
		STATUS					 current
		DESCRIPTION			 " -- "
		::=  { douAdjcHandOverProcedureEntry  42 }


	hoOutAttS		 OBJECT-TYPE
		SYNTAX					 Counter32
		MAX-ACCESS			 read-only
		STATUS					 current
		DESCRIPTION			 " -- "
		::=  { douAdjcHandOverProcedureEntry  43 }


	hoOutSuccS		 OBJECT-TYPE
		SYNTAX					 Counter32
		MAX-ACCESS			 read-only
		STATUS					 current
		DESCRIPTION			 " -- "
		::=  { douAdjcHandOverProcedureEntry  44 }


	erabInterWithHandOverTable		 OBJECT-TYPE
		SYNTAX					 SEQUENCE  OF	 ErabInterWithHandOverEntry
		MAX-ACCESS			 not-accessible
		STATUS					 current
		DESCRIPTION			 " -- "
		::=  { rrcrelatedOriginCounter  16 }


	erabInterWithHandOverEntry		 OBJECT-TYPE
		SYNTAX					 ErabInterWithHandOverEntry
		MAX-ACCESS			 not-accessible
		STATUS					 current
		DESCRIPTION			 " -- "
		INDEX						{ erabInterWithHandOverLcId }
		::=  { erabInterWithHandOverTable  1 }


	ErabInterWithHandOverEntry		 ::=  SEQUENCE {
		erabInterWithHandOverLcId					Integer32,
		erabInterWithHandOverRowStatus					RowStatus,
		rrcErabSetupInteractWithHo					Counter32,
		rrcRecofigInteractWithHoErabFail					Counter32,
		rrcErabModInteractWithHo					Counter32,
		rrcErabDelInteractWithHo					Counter32
		}


	erabInterWithHandOverLcId		 OBJECT-TYPE
		SYNTAX					 Integer32( 0 .. 23 )
		MAX-ACCESS			 not-accessible
		STATUS					 current
		DESCRIPTION			 " -- "
		::=  { erabInterWithHandOverEntry  1 }


	erabInterWithHandOverRowStatus		 OBJECT-TYPE
		SYNTAX					 RowStatus
		MAX-ACCESS			 read-only
		STATUS					 current
		DESCRIPTION			 " -- "
		::=  { erabInterWithHandOverEntry  2 }


	rrcErabSetupInteractWithHo		 OBJECT-TYPE
		SYNTAX					 Counter32
		MAX-ACCESS			 read-only
		STATUS					 current
		DESCRIPTION			 " -- "
		::=  { erabInterWithHandOverEntry  3 }


	rrcRecofigInteractWithHoErabFail		 OBJECT-TYPE
		SYNTAX					 Counter32
		MAX-ACCESS			 read-only
		STATUS					 current
		DESCRIPTION			 " -- "
		::=  { erabInterWithHandOverEntry  4 }


	rrcErabModInteractWithHo		 OBJECT-TYPE
		SYNTAX					 Counter32
		MAX-ACCESS			 read-only
		STATUS					 current
		DESCRIPTION			 " -- "
		::=  { erabInterWithHandOverEntry  5 }


	rrcErabDelInteractWithHo		 OBJECT-TYPE
		SYNTAX					 Counter32
		MAX-ACCESS			 read-only
		STATUS					 current
		DESCRIPTION			 " -- "
		::=  { erabInterWithHandOverEntry  6 }


	vipSafeguardTable		 OBJECT-TYPE
		SYNTAX					 SEQUENCE  OF	 VipSafeguardEntry
		MAX-ACCESS			 not-accessible
		STATUS					 current
		DESCRIPTION			 " -- "
		::=  { rrcrelatedOriginCounter  17 }


	vipSafeguardEntry		 OBJECT-TYPE
		SYNTAX					 VipSafeguardEntry
		MAX-ACCESS			 not-accessible
		STATUS					 current
		DESCRIPTION			 " -- "
		INDEX						{ vipSafeguardLcId }
		::=  { vipSafeguardTable  1 }


	VipSafeguardEntry		 ::=  SEQUENCE {
		vipSafeguardLcId					Integer32,
		vipSafeguardRowStatus					RowStatus,
		rrcReduceCrsPowerReq					Counter32,
		rrcReduceCrsPowerSucc					Counter32,
		rrcRecoverCrsPowerRevRedPowReq					Counter32,
		rrcRecoverCrsPowerVipIn					Counter32,
		rrcRecoverCrsPowerTimeOut					Counter32
		}


	vipSafeguardLcId		 OBJECT-TYPE
		SYNTAX					 Integer32( 0 .. 23 )
		MAX-ACCESS			 not-accessible
		STATUS					 current
		DESCRIPTION			 " -- "
		::=  { vipSafeguardEntry  1 }


	vipSafeguardRowStatus		 OBJECT-TYPE
		SYNTAX					 RowStatus
		MAX-ACCESS			 read-only
		STATUS					 current
		DESCRIPTION			 " -- "
		::=  { vipSafeguardEntry  2 }


	rrcReduceCrsPowerReq		 OBJECT-TYPE
		SYNTAX					 Counter32
		MAX-ACCESS			 read-only
		STATUS					 current
		DESCRIPTION			 " -- "
		::=  { vipSafeguardEntry  3 }


	rrcReduceCrsPowerSucc		 OBJECT-TYPE
		SYNTAX					 Counter32
		MAX-ACCESS			 read-only
		STATUS					 current
		DESCRIPTION			 " -- "
		::=  { vipSafeguardEntry  4 }


	rrcRecoverCrsPowerRevRedPowReq		 OBJECT-TYPE
		SYNTAX					 Counter32
		MAX-ACCESS			 read-only
		STATUS					 current
		DESCRIPTION			 " -- "
		::=  { vipSafeguardEntry  5 }


	rrcRecoverCrsPowerVipIn		 OBJECT-TYPE
		SYNTAX					 Counter32
		MAX-ACCESS			 read-only
		STATUS					 current
		DESCRIPTION			 " -- "
		::=  { vipSafeguardEntry  6 }


	rrcRecoverCrsPowerTimeOut		 OBJECT-TYPE
		SYNTAX					 Counter32
		MAX-ACCESS			 read-only
		STATUS					 current
		DESCRIPTION			 " -- "
		::=  { vipSafeguardEntry  7 }


	pagingProcTable		 OBJECT-TYPE
		SYNTAX					 SEQUENCE  OF	 PagingProcEntry
		MAX-ACCESS			 not-accessible
		STATUS					 current
		DESCRIPTION			 " -- "
		::=  { rrcrelatedOriginCounter  18 }


	pagingProcEntry		 OBJECT-TYPE
		SYNTAX					 PagingProcEntry
		MAX-ACCESS			 not-accessible
		STATUS					 current
		DESCRIPTION			 " -- "
		INDEX						{ pagingProcLcId }
		::=  { pagingProcTable  1 }


	PagingProcEntry		 ::=  SEQUENCE {
		pagingProcLcId					Integer32,
		pagingProcRowStatus					RowStatus,
		pagingPagReceived					Counter32,
		pagingCongCellPaging					Counter32,
		pagingPagDiscarded					Counter32,
		pagingPagUu					Counter32
		}


	pagingProcLcId		 OBJECT-TYPE
		SYNTAX					 Integer32( 0 .. 23 )
		MAX-ACCESS			 not-accessible
		STATUS					 current
		DESCRIPTION			 " -- "
		::=  { pagingProcEntry  1 }


	pagingProcRowStatus		 OBJECT-TYPE
		SYNTAX					 RowStatus
		MAX-ACCESS			 read-only
		STATUS					 current
		DESCRIPTION			 " -- "
		::=  { pagingProcEntry  2 }


	pagingPagReceived		 OBJECT-TYPE
		SYNTAX					 Counter32
		MAX-ACCESS			 read-only
		STATUS					 current
		DESCRIPTION			 " -- "
		::=  { pagingProcEntry  3 }


	pagingCongCellPaging		 OBJECT-TYPE
		SYNTAX					 Counter32
		MAX-ACCESS			 read-only
		STATUS					 current
		DESCRIPTION			 " -- "
		::=  { pagingProcEntry  4 }


	pagingPagDiscarded		 OBJECT-TYPE
		SYNTAX					 Counter32
		MAX-ACCESS			 read-only
		STATUS					 current
		DESCRIPTION			 " -- "
		::=  { pagingProcEntry  5 }


	pagingPagUu		 OBJECT-TYPE
		SYNTAX					 Counter32
		MAX-ACCESS			 read-only
		STATUS					 current
		DESCRIPTION			 " -- "
		::=  { pagingProcEntry  6 }


	cellAvailCapTable		 OBJECT-TYPE
		SYNTAX					 SEQUENCE  OF	 CellAvailCapEntry
		MAX-ACCESS			 not-accessible
		STATUS					 current
		DESCRIPTION			 " -- "
		::=  { rrcrelatedOriginCounter  19 }


	cellAvailCapEntry		 OBJECT-TYPE
		SYNTAX					 CellAvailCapEntry
		MAX-ACCESS			 not-accessible
		STATUS					 current
		DESCRIPTION			 " -- "
		INDEX						{ cellAvailCapLcId }
		::=  { cellAvailCapTable  1 }


	CellAvailCapEntry		 ::=  SEQUENCE {
		cellAvailCapLcId					Integer32,
		cellAvailCapRowStatus					RowStatus,
		capacityAvailableUl					Counter32,
		capacityAvailableDl					Counter32
		}


	cellAvailCapLcId		 OBJECT-TYPE
		SYNTAX					 Integer32( 0 .. 23 )
		MAX-ACCESS			 not-accessible
		STATUS					 current
		DESCRIPTION			 " -- "
		::=  { cellAvailCapEntry  1 }


	cellAvailCapRowStatus		 OBJECT-TYPE
		SYNTAX					 RowStatus
		MAX-ACCESS			 read-only
		STATUS					 current
		DESCRIPTION			 " -- "
		::=  { cellAvailCapEntry  2 }


	capacityAvailableUl		 OBJECT-TYPE
		SYNTAX					 Counter32
		MAX-ACCESS			 read-only
		STATUS					 current
		DESCRIPTION			 " -- "
		::=  { cellAvailCapEntry  3 }


	capacityAvailableDl		 OBJECT-TYPE
		SYNTAX					 Counter32
		MAX-ACCESS			 read-only
		STATUS					 current
		DESCRIPTION			 " -- "
		::=  { cellAvailCapEntry  4 }


	erabRelHoProcTable		 OBJECT-TYPE
		SYNTAX					 SEQUENCE  OF	 ErabRelHoProcEntry
		MAX-ACCESS			 not-accessible
		STATUS					 current
		DESCRIPTION			 " -- "
		::=  { rrcrelatedOriginCounter  20 }


	erabRelHoProcEntry		 OBJECT-TYPE
		SYNTAX					 ErabRelHoProcEntry
		MAX-ACCESS			 not-accessible
		STATUS					 current
		DESCRIPTION			 " -- "
		INDEX						{ erabRelHoProcLcId }
		::=  { erabRelHoProcTable  1 }


	ErabRelHoProcEntry		 ::=  SEQUENCE {
		erabRelHoProcLcId					Integer32,
		erabRelHoProcRowStatus					RowStatus,
		erabHoFailQci1					Counter32,
		erabHoFailQci2					Counter32,
		erabHoFailQci3					Counter32,
		erabHoFailQci4					Counter32,
		erabHoFailQci5					Counter32,
		erabHoFailQci6					Counter32,
		erabHoFailQci7					Counter32,
		erabHoFailQci8					Counter32,
		erabHoFailQci9					Counter32
		}


	erabRelHoProcLcId		 OBJECT-TYPE
		SYNTAX					 Integer32( 0 .. 23 )
		MAX-ACCESS			 not-accessible
		STATUS					 current
		DESCRIPTION			 " -- "
		::=  { erabRelHoProcEntry  1 }


	erabRelHoProcRowStatus		 OBJECT-TYPE
		SYNTAX					 RowStatus
		MAX-ACCESS			 read-only
		STATUS					 current
		DESCRIPTION			 " -- "
		::=  { erabRelHoProcEntry  2 }


	erabHoFailQci1		 OBJECT-TYPE
		SYNTAX					 Counter32
		MAX-ACCESS			 read-only
		STATUS					 current
		DESCRIPTION			 " -- "
		::=  { erabRelHoProcEntry  3 }


	erabHoFailQci2		 OBJECT-TYPE
		SYNTAX					 Counter32
		MAX-ACCESS			 read-only
		STATUS					 current
		DESCRIPTION			 " -- "
		::=  { erabRelHoProcEntry  4 }


	erabHoFailQci3		 OBJECT-TYPE
		SYNTAX					 Counter32
		MAX-ACCESS			 read-only
		STATUS					 current
		DESCRIPTION			 " -- "
		::=  { erabRelHoProcEntry  5 }


	erabHoFailQci4		 OBJECT-TYPE
		SYNTAX					 Counter32
		MAX-ACCESS			 read-only
		STATUS					 current
		DESCRIPTION			 " -- "
		::=  { erabRelHoProcEntry  6 }


	erabHoFailQci5		 OBJECT-TYPE
		SYNTAX					 Counter32
		MAX-ACCESS			 read-only
		STATUS					 current
		DESCRIPTION			 " -- "
		::=  { erabRelHoProcEntry  7 }


	erabHoFailQci6		 OBJECT-TYPE
		SYNTAX					 Counter32
		MAX-ACCESS			 read-only
		STATUS					 current
		DESCRIPTION			 " -- "
		::=  { erabRelHoProcEntry  8 }


	erabHoFailQci7		 OBJECT-TYPE
		SYNTAX					 Counter32
		MAX-ACCESS			 read-only
		STATUS					 current
		DESCRIPTION			 " -- "
		::=  { erabRelHoProcEntry  9 }


	erabHoFailQci8		 OBJECT-TYPE
		SYNTAX					 Counter32
		MAX-ACCESS			 read-only
		STATUS					 current
		DESCRIPTION			 " -- "
		::=  { erabRelHoProcEntry  10 }


	erabHoFailQci9		 OBJECT-TYPE
		SYNTAX					 Counter32
		MAX-ACCESS			 read-only
		STATUS					 current
		DESCRIPTION			 " -- "
		::=  { erabRelHoProcEntry  11 }


	holbcProcInterEnbTable		 OBJECT-TYPE
		SYNTAX					 SEQUENCE  OF	 HolbcProcInterEnbEntry
		MAX-ACCESS			 not-accessible
		STATUS					 current
		DESCRIPTION			 " -- "
		::=  { rrcrelatedOriginCounter  21 }


	holbcProcInterEnbEntry		 OBJECT-TYPE
		SYNTAX					 HolbcProcInterEnbEntry
		MAX-ACCESS			 not-accessible
		STATUS					 current
		DESCRIPTION			 " -- "
		INDEX						{ holbcProcInterEnbLcId }
		::=  { holbcProcInterEnbTable  1 }


	HolbcProcInterEnbEntry		 ::=  SEQUENCE {
		holbcProcInterEnbLcId					Integer32,
		holbcProcInterEnbRowStatus					RowStatus,
		hoInterEnbX2LBCPrepOut					Counter32,
		hoInterEnbX2LBCPrepOutSucc					Counter32,
		hoInterEnbX2LBCOutSucc					Counter32,
		hoInterEnbX2LBCOutAtt					Counter32,
		hoInterEnbX2LBCOutCancel					Counter32,
		hoIntraEnbLBCOutAtt					Counter32,
		hoInterEnbX2LBCPrepIn					Counter32,
		hoInterEnbX2LBCPrepInSucc					Counter32,
		hoInterEnbX2LBCInSucc					Counter32,
		hoIntraEnbLBCOutSucc					Counter32,
		hoInterEnbX2LBCInCancel					Counter32,
		hoIntraSysVolteLBCOutAtt					Counter32,
		hoIntraSysVolteLBCOutSucc					Counter32,
		hoInterSysVolteLBCOutAtt					Counter32,
		hoInterSysVolteLBCOutSucc					Counter32,
		lbcPrbMeasurementControl					Counter32,
		lbcPrbMeasurementReport					Counter32,
		lbcPrbPeriodNum					Counter32,
		lbcPrbHighLoadTime					Counter32,
		lbcHoOutPRBUsageUl					Counter32,
		lbcHoOutPRBUsageDl					Counter32,
		lbcUserMeasurementControl					Counter32,
		lbcUserMeasurementReport					Counter32,
		lbcUserPeriodNum					Counter32,
		lbcUserHighLoadTime					Counter32
		}


	holbcProcInterEnbLcId		 OBJECT-TYPE
		SYNTAX					 Integer32( 0 .. 23 )
		MAX-ACCESS			 not-accessible
		STATUS					 current
		DESCRIPTION			 " -- "
		::=  { holbcProcInterEnbEntry  1 }


	holbcProcInterEnbRowStatus		 OBJECT-TYPE
		SYNTAX					 RowStatus
		MAX-ACCESS			 read-only
		STATUS					 current
		DESCRIPTION			 " -- "
		::=  { holbcProcInterEnbEntry  2 }


	hoInterEnbX2LBCPrepOut		 OBJECT-TYPE
		SYNTAX					 Counter32
		MAX-ACCESS			 read-only
		STATUS					 current
		DESCRIPTION			 " -- "
		::=  { holbcProcInterEnbEntry  3 }


	hoInterEnbX2LBCPrepOutSucc		 OBJECT-TYPE
		SYNTAX					 Counter32
		MAX-ACCESS			 read-only
		STATUS					 current
		DESCRIPTION			 " -- "
		::=  { holbcProcInterEnbEntry  4 }


	hoInterEnbX2LBCOutSucc		 OBJECT-TYPE
		SYNTAX					 Counter32
		MAX-ACCESS			 read-only
		STATUS					 current
		DESCRIPTION			 " -- "
		::=  { holbcProcInterEnbEntry  5 }


	hoInterEnbX2LBCOutAtt		 OBJECT-TYPE
		SYNTAX					 Counter32
		MAX-ACCESS			 read-only
		STATUS					 current
		DESCRIPTION			 " -- "
		::=  { holbcProcInterEnbEntry  6 }


	hoInterEnbX2LBCOutCancel		 OBJECT-TYPE
		SYNTAX					 Counter32
		MAX-ACCESS			 read-only
		STATUS					 current
		DESCRIPTION			 " -- "
		::=  { holbcProcInterEnbEntry  7 }


	hoIntraEnbLBCOutAtt		 OBJECT-TYPE
		SYNTAX					 Counter32
		MAX-ACCESS			 read-only
		STATUS					 current
		DESCRIPTION			 " -- "
		::=  { holbcProcInterEnbEntry  8 }


	hoInterEnbX2LBCPrepIn		 OBJECT-TYPE
		SYNTAX					 Counter32
		MAX-ACCESS			 read-only
		STATUS					 current
		DESCRIPTION			 " -- "
		::=  { holbcProcInterEnbEntry  9 }


	hoInterEnbX2LBCPrepInSucc		 OBJECT-TYPE
		SYNTAX					 Counter32
		MAX-ACCESS			 read-only
		STATUS					 current
		DESCRIPTION			 " -- "
		::=  { holbcProcInterEnbEntry  10 }


	hoInterEnbX2LBCInSucc		 OBJECT-TYPE
		SYNTAX					 Counter32
		MAX-ACCESS			 read-only
		STATUS					 current
		DESCRIPTION			 " -- "
		::=  { holbcProcInterEnbEntry  11 }


	hoIntraEnbLBCOutSucc		 OBJECT-TYPE
		SYNTAX					 Counter32
		MAX-ACCESS			 read-only
		STATUS					 current
		DESCRIPTION			 " -- "
		::=  { holbcProcInterEnbEntry  12 }


	hoInterEnbX2LBCInCancel		 OBJECT-TYPE
		SYNTAX					 Counter32
		MAX-ACCESS			 read-only
		STATUS					 current
		DESCRIPTION			 " -- "
		::=  { holbcProcInterEnbEntry  13 }


	hoIntraSysVolteLBCOutAtt		 OBJECT-TYPE
		SYNTAX					 Counter32
		MAX-ACCESS			 read-only
		STATUS					 current
		DESCRIPTION			 " -- "
		::=  { holbcProcInterEnbEntry  14 }


	hoIntraSysVolteLBCOutSucc		 OBJECT-TYPE
		SYNTAX					 Counter32
		MAX-ACCESS			 read-only
		STATUS					 current
		DESCRIPTION			 " -- "
		::=  { holbcProcInterEnbEntry  15 }


	hoInterSysVolteLBCOutAtt		 OBJECT-TYPE
		SYNTAX					 Counter32
		MAX-ACCESS			 read-only
		STATUS					 current
		DESCRIPTION			 " -- "
		::=  { holbcProcInterEnbEntry  16 }


	hoInterSysVolteLBCOutSucc		 OBJECT-TYPE
		SYNTAX					 Counter32
		MAX-ACCESS			 read-only
		STATUS					 current
		DESCRIPTION			 " -- "
		::=  { holbcProcInterEnbEntry  17 }


	lbcPrbMeasurementControl		 OBJECT-TYPE
		SYNTAX					 Counter32
		MAX-ACCESS			 read-only
		STATUS					 current
		DESCRIPTION			 " -- "
		::=  { holbcProcInterEnbEntry  18 }


	lbcPrbMeasurementReport		 OBJECT-TYPE
		SYNTAX					 Counter32
		MAX-ACCESS			 read-only
		STATUS					 current
		DESCRIPTION			 " -- "
		::=  { holbcProcInterEnbEntry  19 }


	lbcPrbPeriodNum		 OBJECT-TYPE
		SYNTAX					 Counter32
		MAX-ACCESS			 read-only
		STATUS					 current
		DESCRIPTION			 " -- "
		::=  { holbcProcInterEnbEntry  20 }


	lbcPrbHighLoadTime		 OBJECT-TYPE
		SYNTAX					 Counter32
		MAX-ACCESS			 read-only
		STATUS					 current
		DESCRIPTION			 " -- "
		::=  { holbcProcInterEnbEntry  21 }


	lbcHoOutPRBUsageUl		 OBJECT-TYPE
		SYNTAX					 Counter32
		MAX-ACCESS			 read-only
		STATUS					 current
		DESCRIPTION			 " -- "
		::=  { holbcProcInterEnbEntry  22 }


	lbcHoOutPRBUsageDl		 OBJECT-TYPE
		SYNTAX					 Counter32
		MAX-ACCESS			 read-only
		STATUS					 current
		DESCRIPTION			 " -- "
		::=  { holbcProcInterEnbEntry  23 }


	lbcUserMeasurementControl		 OBJECT-TYPE
		SYNTAX					 Counter32
		MAX-ACCESS			 read-only
		STATUS					 current
		DESCRIPTION			 " -- "
		::=  { holbcProcInterEnbEntry  24 }


	lbcUserMeasurementReport		 OBJECT-TYPE
		SYNTAX					 Counter32
		MAX-ACCESS			 read-only
		STATUS					 current
		DESCRIPTION			 " -- "
		::=  { holbcProcInterEnbEntry  25 }


	lbcUserPeriodNum		 OBJECT-TYPE
		SYNTAX					 Counter32
		MAX-ACCESS			 read-only
		STATUS					 current
		DESCRIPTION			 " -- "
		::=  { holbcProcInterEnbEntry  26 }


	lbcUserHighLoadTime		 OBJECT-TYPE
		SYNTAX					 Counter32
		MAX-ACCESS			 read-only
		STATUS					 current
		DESCRIPTION			 " -- "
		::=  { holbcProcInterEnbEntry  27 }


	handOverProcTimeInterEnbTable		 OBJECT-TYPE
		SYNTAX					 SEQUENCE  OF	 HandOverProcTimeInterEnbEntry
		MAX-ACCESS			 not-accessible
		STATUS					 current
		DESCRIPTION			 " -- "
		::=  { rrcrelatedOriginCounter  22 }


	handOverProcTimeInterEnbEntry		 OBJECT-TYPE
		SYNTAX					 HandOverProcTimeInterEnbEntry
		MAX-ACCESS			 not-accessible
		STATUS					 current
		DESCRIPTION			 " -- "
		INDEX						{ handOverProcTimeInterEnbLcId }
		::=  { handOverProcTimeInterEnbTable  1 }


	HandOverProcTimeInterEnbEntry		 ::=  SEQUENCE {
		handOverProcTimeInterEnbLcId					Integer32,
		handOverProcTimeInterEnbRowStatus					RowStatus,
		hoAvgTimeInterEnbS1					Counter32,
		hoAvgTimeInterEnbX2					Counter32,
		irathoAvgTimeOutGeran					Counter32,
		irathoAvgTimeOutUtran					Counter32,
		irathoAvgTimeOutExecGeran					Counter32
		}


	handOverProcTimeInterEnbLcId		 OBJECT-TYPE
		SYNTAX					 Integer32( 0 .. 23 )
		MAX-ACCESS			 not-accessible
		STATUS					 current
		DESCRIPTION			 " -- "
		::=  { handOverProcTimeInterEnbEntry  1 }


	handOverProcTimeInterEnbRowStatus		 OBJECT-TYPE
		SYNTAX					 RowStatus
		MAX-ACCESS			 read-only
		STATUS					 current
		DESCRIPTION			 " -- "
		::=  { handOverProcTimeInterEnbEntry  2 }


	hoAvgTimeInterEnbS1		 OBJECT-TYPE
		SYNTAX					 Counter32
		MAX-ACCESS			 read-only
		STATUS					 current
		DESCRIPTION			 " -- "
		::=  { handOverProcTimeInterEnbEntry  3 }


	hoAvgTimeInterEnbX2		 OBJECT-TYPE
		SYNTAX					 Counter32
		MAX-ACCESS			 read-only
		STATUS					 current
		DESCRIPTION			 " -- "
		::=  { handOverProcTimeInterEnbEntry  4 }


	irathoAvgTimeOutGeran		 OBJECT-TYPE
		SYNTAX					 Counter32
		MAX-ACCESS			 read-only
		STATUS					 current
		DESCRIPTION			 " -- "
		::=  { handOverProcTimeInterEnbEntry  5 }


	irathoAvgTimeOutUtran		 OBJECT-TYPE
		SYNTAX					 Counter32
		MAX-ACCESS			 read-only
		STATUS					 current
		DESCRIPTION			 " -- "
		::=  { handOverProcTimeInterEnbEntry  6 }


	irathoAvgTimeOutExecGeran		 OBJECT-TYPE
		SYNTAX					 Counter32
		MAX-ACCESS			 read-only
		STATUS					 current
		DESCRIPTION			 " -- "
		::=  { handOverProcTimeInterEnbEntry  7 }


	lteFddTddHOTable		 OBJECT-TYPE
		SYNTAX					 SEQUENCE  OF	 LteFddTddHOEntry
		MAX-ACCESS			 not-accessible
		STATUS					 current
		DESCRIPTION			 " -- "
		::=  { rrcrelatedOriginCounter  23 }


	lteFddTddHOEntry		 OBJECT-TYPE
		SYNTAX					 LteFddTddHOEntry
		MAX-ACCESS			 not-accessible
		STATUS					 current
		DESCRIPTION			 " -- "
		INDEX						{ lteFddTddHOLcId }
		::=  { lteFddTddHOTable  1 }


	LteFddTddHOEntry		 ::=  SEQUENCE {
		lteFddTddHOLcId					Integer32,
		lteFddTddHORowStatus					RowStatus,
		hoAttOutFddTddS1					Counter32,
		hoSuccPrepOutFddTddS1					Counter32,
		hoSuccOutFddTddS1					Counter32,
		hoAttOutFddTddX2					Counter32,
		hoSuccPrepOutFddTddX2					Counter32,
		hoSuccOutFddTddX2					Counter32,
		hoAttIncFddTddS1					Counter32,
		hoSuccPrepIncFddTddS1					Counter32,
		hoSuccIncFddTddS1					Counter32,
		hoAttIncFddTddX2					Counter32,
		hoSuccPrepIncFddTddX2					Counter32,
		hoSuccIncFddTddX2					Counter32,
		hoAttOutFddTddIntraEnb					Counter32,
		hoSuccOutFddTddIntraEnb					Counter32
		}


	lteFddTddHOLcId		 OBJECT-TYPE
		SYNTAX					 Integer32( 0 .. 23 )
		MAX-ACCESS			 not-accessible
		STATUS					 current
		DESCRIPTION			 " -- "
		::=  { lteFddTddHOEntry  1 }


	lteFddTddHORowStatus		 OBJECT-TYPE
		SYNTAX					 RowStatus
		MAX-ACCESS			 read-only
		STATUS					 current
		DESCRIPTION			 " -- "
		::=  { lteFddTddHOEntry  2 }


	hoAttOutFddTddS1		 OBJECT-TYPE
		SYNTAX					 Counter32
		MAX-ACCESS			 read-only
		STATUS					 current
		DESCRIPTION			 " -- "
		::=  { lteFddTddHOEntry  3 }


	hoSuccPrepOutFddTddS1		 OBJECT-TYPE
		SYNTAX					 Counter32
		MAX-ACCESS			 read-only
		STATUS					 current
		DESCRIPTION			 " -- "
		::=  { lteFddTddHOEntry  4 }


	hoSuccOutFddTddS1		 OBJECT-TYPE
		SYNTAX					 Counter32
		MAX-ACCESS			 read-only
		STATUS					 current
		DESCRIPTION			 " -- "
		::=  { lteFddTddHOEntry  5 }


	hoAttOutFddTddX2		 OBJECT-TYPE
		SYNTAX					 Counter32
		MAX-ACCESS			 read-only
		STATUS					 current
		DESCRIPTION			 " -- "
		::=  { lteFddTddHOEntry  6 }


	hoSuccPrepOutFddTddX2		 OBJECT-TYPE
		SYNTAX					 Counter32
		MAX-ACCESS			 read-only
		STATUS					 current
		DESCRIPTION			 " -- "
		::=  { lteFddTddHOEntry  7 }


	hoSuccOutFddTddX2		 OBJECT-TYPE
		SYNTAX					 Counter32
		MAX-ACCESS			 read-only
		STATUS					 current
		DESCRIPTION			 " -- "
		::=  { lteFddTddHOEntry  8 }


	hoAttIncFddTddS1		 OBJECT-TYPE
		SYNTAX					 Counter32
		MAX-ACCESS			 read-only
		STATUS					 current
		DESCRIPTION			 " -- "
		::=  { lteFddTddHOEntry  9 }


	hoSuccPrepIncFddTddS1		 OBJECT-TYPE
		SYNTAX					 Counter32
		MAX-ACCESS			 read-only
		STATUS					 current
		DESCRIPTION			 " -- "
		::=  { lteFddTddHOEntry  10 }


	hoSuccIncFddTddS1		 OBJECT-TYPE
		SYNTAX					 Counter32
		MAX-ACCESS			 read-only
		STATUS					 current
		DESCRIPTION			 " -- "
		::=  { lteFddTddHOEntry  11 }


	hoAttIncFddTddX2		 OBJECT-TYPE
		SYNTAX					 Counter32
		MAX-ACCESS			 read-only
		STATUS					 current
		DESCRIPTION			 " -- "
		::=  { lteFddTddHOEntry  12 }


	hoSuccPrepIncFddTddX2		 OBJECT-TYPE
		SYNTAX					 Counter32
		MAX-ACCESS			 read-only
		STATUS					 current
		DESCRIPTION			 " -- "
		::=  { lteFddTddHOEntry  13 }


	hoSuccIncFddTddX2		 OBJECT-TYPE
		SYNTAX					 Counter32
		MAX-ACCESS			 read-only
		STATUS					 current
		DESCRIPTION			 " -- "
		::=  { lteFddTddHOEntry  14 }


	hoAttOutFddTddIntraEnb		 OBJECT-TYPE
		SYNTAX					 Counter32
		MAX-ACCESS			 read-only
		STATUS					 current
		DESCRIPTION			 " -- "
		::=  { lteFddTddHOEntry  15 }


	hoSuccOutFddTddIntraEnb		 OBJECT-TYPE
		SYNTAX					 Counter32
		MAX-ACCESS			 read-only
		STATUS					 current
		DESCRIPTION			 " -- "
		::=  { lteFddTddHOEntry  16 }


	voLTEHandOverInTDLTETable		 OBJECT-TYPE
		SYNTAX					 SEQUENCE  OF	 VoLTEHandOverInTDLTEEntry
		MAX-ACCESS			 not-accessible
		STATUS					 current
		DESCRIPTION			 " -- "
		::=  { rrcrelatedOriginCounter  24 }


	voLTEHandOverInTDLTEEntry		 OBJECT-TYPE
		SYNTAX					 VoLTEHandOverInTDLTEEntry
		MAX-ACCESS			 not-accessible
		STATUS					 current
		DESCRIPTION			 " -- "
		INDEX						{ voLTEHandOverInTDLTELcId }
		::=  { voLTEHandOverInTDLTETable  1 }


	VoLTEHandOverInTDLTEEntry		 ::=  SEQUENCE {
		voLTEHandOverInTDLTELcId					Integer32,
		voLTEHandOverInTDLTERowStatus					RowStatus,
		volteHOAttOutInterEnbS1IntraFreq					Counter32,
		volteHOAttOutInterEnbS1InterFreq					Counter32,
		volteHOAttOutInterEnbS1IntraFreqN					Counter32,
		volteHOAttOutInterEnbS1InterFreqN					Counter32,
		volteHOSuccOutPrepInterEnbS1IntraFreq					Counter32,
		volteHOSuccOutPrepInterEnbS1InterFreq					Counter32,
		volteHOAttOutExecInterEnbS1IntraFreq					Counter32,
		volteHOAttOutExecInterEnbS1InterFreq					Counter32,
		volteHOSuccOutInterEnbS1IntraFreq					Counter32,
		volteHOSuccOutInterEnbS1InterFreq					Counter32,
		volteHOCancelOutInterEnbS1					Counter32,
		volteHOAttOutInterEnbX2IntraFreq					Counter32,
		volteHOAttOutInterEnbX2InterFreq					Counter32,
		volteHOAttOutInterEnbX2IntraFreqN					Counter32,
		volteHOAttOutInterEnbX2InterFreqN					Counter32,
		volteHOSuccOutPrepInterEnbX2IntraFreq					Counter32,
		volteHOSuccOutPrepInterEnbX2InterFreq					Counter32,
		volteHOAttOutExecInterEnbX2IntraFreq					Counter32,
		volteHOAttOutExecInterEnbX2InterFreq					Counter32,
		volteHOSuccOutInterEnbX2IntraFreq					Counter32,
		volteHOSuccOutInterEnbX2InterFreq					Counter32,
		volteHOCancelOutInterEnbX2					Counter32,
		volteHOAttOutIntraEnbIntraFreq					Counter32,
		volteHOAttOutIntraEnbInterFreq					Counter32,
		volteHOSuccOutIntraEnbIntraFreq					Counter32,
		volteHOSuccOutIntraEnbInterFreq					Counter32,
		hoAttOutInterEnbS1IntraFreqQci2					Counter32,
		hoAttOutInterEnbS1InterFreqQci2					Counter32,
		hoSuccOutPrepInterEnbS1IntraFreqQci2					Counter32,
		hoSuccOutPrepInterEnbS1InterFreqQci2					Counter32,
		hoAttOutExecInterEnbS1IntraFreqQci2					Counter32,
		hoAttOutExecInterEnbS1InterFreqQci2					Counter32,
		hoSuccOutInterEnbS1IntraFreqQci2					Counter32,
		hoSuccOutInterEnbS1InterFreqQci2					Counter32,
		hoAttOutInterEnbX2IntraFreqQci2					Counter32,
		hoAttOutInterEnbX2InterFreqQci2					Counter32,
		hoSuccOutPrepInterEnbX2IntraFreqQci2					Counter32,
		hoSuccOutPrepInterEnbX2InterFreqQci2					Counter32,
		hoAttOutExecInterEnbX2IntraFreqQci2					Counter32,
		hoAttOutExecInterEnbX2InterFreqQci2					Counter32,
		hoSuccOutInterEnbX2IntraFreqQci2					Counter32,
		hoSuccOutInterEnbX2InterFreqQci2					Counter32,
		hoAttOutIntraEnbIntraFreqQci2					Counter32,
		hoAttOutIntraEnbInterFreqQci2					Counter32,
		hoSuccOutIntraEnbIntraFreqQci2					Counter32,
		hoSuccOutIntraEnbInterFreqQci2					Counter32,
		volteHOFailOutPrepFail					Counter32,
		volteHOFailOutPrepTimeOut					Counter32,
		volteHOFailOutExecTimeOut					Counter32,
		volteHOFailOutRRCReConn					Counter32,
		volteHOFailOutMme					Counter32,
		hoAttOutPrepInterEnbX2Quality					Counter32,
		hoSuccOutPrepInterEnbX2Quality					Counter32,
		hoSuccOutInterEnbX2Quality					Counter32,
		hoAttOutPrepIntraEnbQuality					Counter32,
		hoAttOutExecIntraEnbQuality					Counter32,
		hoSuccOutIntraEnbQuality					Counter32,
		hoFailPrepOutX2QuaNoRRinTc					Counter32,
		hoFailPrepOutX2QuaUnknownMme					Counter32,
		hoFailPrepOutX2QuaOtherTf					Counter32,
		hoFailOutX2QuaReEtOenbHof					Counter32,
		hoFailOutX2QuaReEtOenbRcf					Counter32,
		hoFailOutX2QuaReEtOenbOther					Counter32,
		hoFailOutX2QuaReEtPrepSetEnb					Counter32
		}


	voLTEHandOverInTDLTELcId		 OBJECT-TYPE
		SYNTAX					 Integer32( 0 .. 23 )
		MAX-ACCESS			 not-accessible
		STATUS					 current
		DESCRIPTION			 " -- "
		::=  { voLTEHandOverInTDLTEEntry  1 }


	voLTEHandOverInTDLTERowStatus		 OBJECT-TYPE
		SYNTAX					 RowStatus
		MAX-ACCESS			 read-only
		STATUS					 current
		DESCRIPTION			 " -- "
		::=  { voLTEHandOverInTDLTEEntry  2 }


	volteHOAttOutInterEnbS1IntraFreq		 OBJECT-TYPE
		SYNTAX					 Counter32
		MAX-ACCESS			 read-only
		STATUS					 current
		DESCRIPTION			 " -- "
		::=  { voLTEHandOverInTDLTEEntry  3 }


	volteHOAttOutInterEnbS1InterFreq		 OBJECT-TYPE
		SYNTAX					 Counter32
		MAX-ACCESS			 read-only
		STATUS					 current
		DESCRIPTION			 " -- "
		::=  { voLTEHandOverInTDLTEEntry  4 }


	volteHOAttOutInterEnbS1IntraFreqN		 OBJECT-TYPE
		SYNTAX					 Counter32
		MAX-ACCESS			 read-only
		STATUS					 current
		DESCRIPTION			 " -- "
		::=  { voLTEHandOverInTDLTEEntry  5 }


	volteHOAttOutInterEnbS1InterFreqN		 OBJECT-TYPE
		SYNTAX					 Counter32
		MAX-ACCESS			 read-only
		STATUS					 current
		DESCRIPTION			 " -- "
		::=  { voLTEHandOverInTDLTEEntry  6 }


	volteHOSuccOutPrepInterEnbS1IntraFreq		 OBJECT-TYPE
		SYNTAX					 Counter32
		MAX-ACCESS			 read-only
		STATUS					 current
		DESCRIPTION			 " -- "
		::=  { voLTEHandOverInTDLTEEntry  7 }


	volteHOSuccOutPrepInterEnbS1InterFreq		 OBJECT-TYPE
		SYNTAX					 Counter32
		MAX-ACCESS			 read-only
		STATUS					 current
		DESCRIPTION			 " -- "
		::=  { voLTEHandOverInTDLTEEntry  8 }


	volteHOAttOutExecInterEnbS1IntraFreq		 OBJECT-TYPE
		SYNTAX					 Counter32
		MAX-ACCESS			 read-only
		STATUS					 current
		DESCRIPTION			 " -- "
		::=  { voLTEHandOverInTDLTEEntry  9 }


	volteHOAttOutExecInterEnbS1InterFreq		 OBJECT-TYPE
		SYNTAX					 Counter32
		MAX-ACCESS			 read-only
		STATUS					 current
		DESCRIPTION			 " -- "
		::=  { voLTEHandOverInTDLTEEntry  10 }


	volteHOSuccOutInterEnbS1IntraFreq		 OBJECT-TYPE
		SYNTAX					 Counter32
		MAX-ACCESS			 read-only
		STATUS					 current
		DESCRIPTION			 " -- "
		::=  { voLTEHandOverInTDLTEEntry  11 }


	volteHOSuccOutInterEnbS1InterFreq		 OBJECT-TYPE
		SYNTAX					 Counter32
		MAX-ACCESS			 read-only
		STATUS					 current
		DESCRIPTION			 " -- "
		::=  { voLTEHandOverInTDLTEEntry  12 }


	volteHOCancelOutInterEnbS1		 OBJECT-TYPE
		SYNTAX					 Counter32
		MAX-ACCESS			 read-only
		STATUS					 current
		DESCRIPTION			 " -- "
		::=  { voLTEHandOverInTDLTEEntry  13 }


	volteHOAttOutInterEnbX2IntraFreq		 OBJECT-TYPE
		SYNTAX					 Counter32
		MAX-ACCESS			 read-only
		STATUS					 current
		DESCRIPTION			 " -- "
		::=  { voLTEHandOverInTDLTEEntry  14 }


	volteHOAttOutInterEnbX2InterFreq		 OBJECT-TYPE
		SYNTAX					 Counter32
		MAX-ACCESS			 read-only
		STATUS					 current
		DESCRIPTION			 " -- "
		::=  { voLTEHandOverInTDLTEEntry  15 }


	volteHOAttOutInterEnbX2IntraFreqN		 OBJECT-TYPE
		SYNTAX					 Counter32
		MAX-ACCESS			 read-only
		STATUS					 current
		DESCRIPTION			 " -- "
		::=  { voLTEHandOverInTDLTEEntry  16 }


	volteHOAttOutInterEnbX2InterFreqN		 OBJECT-TYPE
		SYNTAX					 Counter32
		MAX-ACCESS			 read-only
		STATUS					 current
		DESCRIPTION			 " -- "
		::=  { voLTEHandOverInTDLTEEntry  17 }


	volteHOSuccOutPrepInterEnbX2IntraFreq		 OBJECT-TYPE
		SYNTAX					 Counter32
		MAX-ACCESS			 read-only
		STATUS					 current
		DESCRIPTION			 " -- "
		::=  { voLTEHandOverInTDLTEEntry  18 }


	volteHOSuccOutPrepInterEnbX2InterFreq		 OBJECT-TYPE
		SYNTAX					 Counter32
		MAX-ACCESS			 read-only
		STATUS					 current
		DESCRIPTION			 " -- "
		::=  { voLTEHandOverInTDLTEEntry  19 }


	volteHOAttOutExecInterEnbX2IntraFreq		 OBJECT-TYPE
		SYNTAX					 Counter32
		MAX-ACCESS			 read-only
		STATUS					 current
		DESCRIPTION			 " -- "
		::=  { voLTEHandOverInTDLTEEntry  20 }


	volteHOAttOutExecInterEnbX2InterFreq		 OBJECT-TYPE
		SYNTAX					 Counter32
		MAX-ACCESS			 read-only
		STATUS					 current
		DESCRIPTION			 " -- "
		::=  { voLTEHandOverInTDLTEEntry  21 }


	volteHOSuccOutInterEnbX2IntraFreq		 OBJECT-TYPE
		SYNTAX					 Counter32
		MAX-ACCESS			 read-only
		STATUS					 current
		DESCRIPTION			 " -- "
		::=  { voLTEHandOverInTDLTEEntry  22 }


	volteHOSuccOutInterEnbX2InterFreq		 OBJECT-TYPE
		SYNTAX					 Counter32
		MAX-ACCESS			 read-only
		STATUS					 current
		DESCRIPTION			 " -- "
		::=  { voLTEHandOverInTDLTEEntry  23 }


	volteHOCancelOutInterEnbX2		 OBJECT-TYPE
		SYNTAX					 Counter32
		MAX-ACCESS			 read-only
		STATUS					 current
		DESCRIPTION			 " -- "
		::=  { voLTEHandOverInTDLTEEntry  24 }


	volteHOAttOutIntraEnbIntraFreq		 OBJECT-TYPE
		SYNTAX					 Counter32
		MAX-ACCESS			 read-only
		STATUS					 current
		DESCRIPTION			 " -- "
		::=  { voLTEHandOverInTDLTEEntry  25 }


	volteHOAttOutIntraEnbInterFreq		 OBJECT-TYPE
		SYNTAX					 Counter32
		MAX-ACCESS			 read-only
		STATUS					 current
		DESCRIPTION			 " -- "
		::=  { voLTEHandOverInTDLTEEntry  26 }


	volteHOSuccOutIntraEnbIntraFreq		 OBJECT-TYPE
		SYNTAX					 Counter32
		MAX-ACCESS			 read-only
		STATUS					 current
		DESCRIPTION			 " -- "
		::=  { voLTEHandOverInTDLTEEntry  27 }


	volteHOSuccOutIntraEnbInterFreq		 OBJECT-TYPE
		SYNTAX					 Counter32
		MAX-ACCESS			 read-only
		STATUS					 current
		DESCRIPTION			 " -- "
		::=  { voLTEHandOverInTDLTEEntry  28 }


	hoAttOutInterEnbS1IntraFreqQci2		 OBJECT-TYPE
		SYNTAX					 Counter32
		MAX-ACCESS			 read-only
		STATUS					 current
		DESCRIPTION			 " -- "
		::=  { voLTEHandOverInTDLTEEntry  29 }


	hoAttOutInterEnbS1InterFreqQci2		 OBJECT-TYPE
		SYNTAX					 Counter32
		MAX-ACCESS			 read-only
		STATUS					 current
		DESCRIPTION			 " -- "
		::=  { voLTEHandOverInTDLTEEntry  30 }


	hoSuccOutPrepInterEnbS1IntraFreqQci2		 OBJECT-TYPE
		SYNTAX					 Counter32
		MAX-ACCESS			 read-only
		STATUS					 current
		DESCRIPTION			 " -- "
		::=  { voLTEHandOverInTDLTEEntry  31 }


	hoSuccOutPrepInterEnbS1InterFreqQci2		 OBJECT-TYPE
		SYNTAX					 Counter32
		MAX-ACCESS			 read-only
		STATUS					 current
		DESCRIPTION			 " -- "
		::=  { voLTEHandOverInTDLTEEntry  32 }


	hoAttOutExecInterEnbS1IntraFreqQci2		 OBJECT-TYPE
		SYNTAX					 Counter32
		MAX-ACCESS			 read-only
		STATUS					 current
		DESCRIPTION			 " -- "
		::=  { voLTEHandOverInTDLTEEntry  33 }


	hoAttOutExecInterEnbS1InterFreqQci2		 OBJECT-TYPE
		SYNTAX					 Counter32
		MAX-ACCESS			 read-only
		STATUS					 current
		DESCRIPTION			 " -- "
		::=  { voLTEHandOverInTDLTEEntry  34 }


	hoSuccOutInterEnbS1IntraFreqQci2		 OBJECT-TYPE
		SYNTAX					 Counter32
		MAX-ACCESS			 read-only
		STATUS					 current
		DESCRIPTION			 " -- "
		::=  { voLTEHandOverInTDLTEEntry  35 }


	hoSuccOutInterEnbS1InterFreqQci2		 OBJECT-TYPE
		SYNTAX					 Counter32
		MAX-ACCESS			 read-only
		STATUS					 current
		DESCRIPTION			 " -- "
		::=  { voLTEHandOverInTDLTEEntry  36 }


	hoAttOutInterEnbX2IntraFreqQci2		 OBJECT-TYPE
		SYNTAX					 Counter32
		MAX-ACCESS			 read-only
		STATUS					 current
		DESCRIPTION			 " -- "
		::=  { voLTEHandOverInTDLTEEntry  37 }


	hoAttOutInterEnbX2InterFreqQci2		 OBJECT-TYPE
		SYNTAX					 Counter32
		MAX-ACCESS			 read-only
		STATUS					 current
		DESCRIPTION			 " -- "
		::=  { voLTEHandOverInTDLTEEntry  38 }


	hoSuccOutPrepInterEnbX2IntraFreqQci2		 OBJECT-TYPE
		SYNTAX					 Counter32
		MAX-ACCESS			 read-only
		STATUS					 current
		DESCRIPTION			 " -- "
		::=  { voLTEHandOverInTDLTEEntry  39 }


	hoSuccOutPrepInterEnbX2InterFreqQci2		 OBJECT-TYPE
		SYNTAX					 Counter32
		MAX-ACCESS			 read-only
		STATUS					 current
		DESCRIPTION			 " -- "
		::=  { voLTEHandOverInTDLTEEntry  40 }


	hoAttOutExecInterEnbX2IntraFreqQci2		 OBJECT-TYPE
		SYNTAX					 Counter32
		MAX-ACCESS			 read-only
		STATUS					 current
		DESCRIPTION			 " -- "
		::=  { voLTEHandOverInTDLTEEntry  41 }


	hoAttOutExecInterEnbX2InterFreqQci2		 OBJECT-TYPE
		SYNTAX					 Counter32
		MAX-ACCESS			 read-only
		STATUS					 current
		DESCRIPTION			 " -- "
		::=  { voLTEHandOverInTDLTEEntry  42 }


	hoSuccOutInterEnbX2IntraFreqQci2		 OBJECT-TYPE
		SYNTAX					 Counter32
		MAX-ACCESS			 read-only
		STATUS					 current
		DESCRIPTION			 " -- "
		::=  { voLTEHandOverInTDLTEEntry  43 }


	hoSuccOutInterEnbX2InterFreqQci2		 OBJECT-TYPE
		SYNTAX					 Counter32
		MAX-ACCESS			 read-only
		STATUS					 current
		DESCRIPTION			 " -- "
		::=  { voLTEHandOverInTDLTEEntry  44 }


	hoAttOutIntraEnbIntraFreqQci2		 OBJECT-TYPE
		SYNTAX					 Counter32
		MAX-ACCESS			 read-only
		STATUS					 current
		DESCRIPTION			 " -- "
		::=  { voLTEHandOverInTDLTEEntry  45 }


	hoAttOutIntraEnbInterFreqQci2		 OBJECT-TYPE
		SYNTAX					 Counter32
		MAX-ACCESS			 read-only
		STATUS					 current
		DESCRIPTION			 " -- "
		::=  { voLTEHandOverInTDLTEEntry  46 }


	hoSuccOutIntraEnbIntraFreqQci2		 OBJECT-TYPE
		SYNTAX					 Counter32
		MAX-ACCESS			 read-only
		STATUS					 current
		DESCRIPTION			 " -- "
		::=  { voLTEHandOverInTDLTEEntry  47 }


	hoSuccOutIntraEnbInterFreqQci2		 OBJECT-TYPE
		SYNTAX					 Counter32
		MAX-ACCESS			 read-only
		STATUS					 current
		DESCRIPTION			 " -- "
		::=  { voLTEHandOverInTDLTEEntry  48 }


	volteHOFailOutPrepFail		 OBJECT-TYPE
		SYNTAX					 Counter32
		MAX-ACCESS			 read-only
		STATUS					 current
		DESCRIPTION			 " -- "
		::=  { voLTEHandOverInTDLTEEntry  49 }


	volteHOFailOutPrepTimeOut		 OBJECT-TYPE
		SYNTAX					 Counter32
		MAX-ACCESS			 read-only
		STATUS					 current
		DESCRIPTION			 " -- "
		::=  { voLTEHandOverInTDLTEEntry  50 }


	volteHOFailOutExecTimeOut		 OBJECT-TYPE
		SYNTAX					 Counter32
		MAX-ACCESS			 read-only
		STATUS					 current
		DESCRIPTION			 " -- "
		::=  { voLTEHandOverInTDLTEEntry  51 }


	volteHOFailOutRRCReConn		 OBJECT-TYPE
		SYNTAX					 Counter32
		MAX-ACCESS			 read-only
		STATUS					 current
		DESCRIPTION			 " -- "
		::=  { voLTEHandOverInTDLTEEntry  52 }


	volteHOFailOutMme		 OBJECT-TYPE
		SYNTAX					 Counter32
		MAX-ACCESS			 read-only
		STATUS					 current
		DESCRIPTION			 " -- "
		::=  { voLTEHandOverInTDLTEEntry  53 }


	hoAttOutPrepInterEnbX2Quality		 OBJECT-TYPE
		SYNTAX					 Counter32
		MAX-ACCESS			 read-only
		STATUS					 current
		DESCRIPTION			 " -- "
		::=  { voLTEHandOverInTDLTEEntry  54 }


	hoSuccOutPrepInterEnbX2Quality		 OBJECT-TYPE
		SYNTAX					 Counter32
		MAX-ACCESS			 read-only
		STATUS					 current
		DESCRIPTION			 " -- "
		::=  { voLTEHandOverInTDLTEEntry  55 }


	hoSuccOutInterEnbX2Quality		 OBJECT-TYPE
		SYNTAX					 Counter32
		MAX-ACCESS			 read-only
		STATUS					 current
		DESCRIPTION			 " -- "
		::=  { voLTEHandOverInTDLTEEntry  56 }


	hoAttOutPrepIntraEnbQuality		 OBJECT-TYPE
		SYNTAX					 Counter32
		MAX-ACCESS			 read-only
		STATUS					 current
		DESCRIPTION			 " -- "
		::=  { voLTEHandOverInTDLTEEntry  57 }


	hoAttOutExecIntraEnbQuality		 OBJECT-TYPE
		SYNTAX					 Counter32
		MAX-ACCESS			 read-only
		STATUS					 current
		DESCRIPTION			 " -- "
		::=  { voLTEHandOverInTDLTEEntry  58 }


	hoSuccOutIntraEnbQuality		 OBJECT-TYPE
		SYNTAX					 Counter32
		MAX-ACCESS			 read-only
		STATUS					 current
		DESCRIPTION			 " -- "
		::=  { voLTEHandOverInTDLTEEntry  59 }


	hoFailPrepOutX2QuaNoRRinTc		 OBJECT-TYPE
		SYNTAX					 Counter32
		MAX-ACCESS			 read-only
		STATUS					 current
		DESCRIPTION			 " -- "
		::=  { voLTEHandOverInTDLTEEntry  60 }


	hoFailPrepOutX2QuaUnknownMme		 OBJECT-TYPE
		SYNTAX					 Counter32
		MAX-ACCESS			 read-only
		STATUS					 current
		DESCRIPTION			 " -- "
		::=  { voLTEHandOverInTDLTEEntry  61 }


	hoFailPrepOutX2QuaOtherTf		 OBJECT-TYPE
		SYNTAX					 Counter32
		MAX-ACCESS			 read-only
		STATUS					 current
		DESCRIPTION			 " -- "
		::=  { voLTEHandOverInTDLTEEntry  62 }


	hoFailOutX2QuaReEtOenbHof		 OBJECT-TYPE
		SYNTAX					 Counter32
		MAX-ACCESS			 read-only
		STATUS					 current
		DESCRIPTION			 " -- "
		::=  { voLTEHandOverInTDLTEEntry  63 }


	hoFailOutX2QuaReEtOenbRcf		 OBJECT-TYPE
		SYNTAX					 Counter32
		MAX-ACCESS			 read-only
		STATUS					 current
		DESCRIPTION			 " -- "
		::=  { voLTEHandOverInTDLTEEntry  64 }


	hoFailOutX2QuaReEtOenbOther		 OBJECT-TYPE
		SYNTAX					 Counter32
		MAX-ACCESS			 read-only
		STATUS					 current
		DESCRIPTION			 " -- "
		::=  { voLTEHandOverInTDLTEEntry  65 }


	hoFailOutX2QuaReEtPrepSetEnb		 OBJECT-TYPE
		SYNTAX					 Counter32
		MAX-ACCESS			 read-only
		STATUS					 current
		DESCRIPTION			 " -- "
		::=  { voLTEHandOverInTDLTEEntry  66 }


	srvccTable		 OBJECT-TYPE
		SYNTAX					 SEQUENCE  OF	 SrvccEntry
		MAX-ACCESS			 not-accessible
		STATUS					 current
		DESCRIPTION			 " -- "
		::=  { rrcrelatedOriginCounter  25 }


	srvccEntry		 OBJECT-TYPE
		SYNTAX					 SrvccEntry
		MAX-ACCESS			 not-accessible
		STATUS					 current
		DESCRIPTION			 " -- "
		INDEX						{ srvccLcId }
		::=  { srvccTable  1 }


	SrvccEntry		 ::=  SEQUENCE {
		srvccLcId					Integer32,
		srvccRowStatus					RowStatus,
		srvccAttOutGeranCoverage					Counter32,
		srvccSuccOutPrepGeranCoverage					Counter32,
		srvccAttOutExecGeranCoverage					Counter32,
		srvccSuccOutGeranCoverage					Counter32,
		srvccFailPrepOutGeranCovNoResponse					Counter32,
		srvccFailPrepOutGeranCovTgtFailure					Counter32,
		srvccFailPrepOutGeranCovOther					Counter32,
		srvccAttOutUtran					Counter32,
		srvccSuccOutPrepUtran					Counter32,
		srvccAttOutExecUtran					Counter32,
		srvccSuccOutUtran					Counter32,
		srvccFailPrepOutUtranNoResponse					Counter32,
		srvccFailPrepOutUtranTgtFailure					Counter32,
		srvccFailPrepOutUtranOther					Counter32,
		srvccAttOutGeranQuality					Counter32,
		srvccSuccOutPrepGeranQuality					Counter32,
		srvccAttOutExecGeranQuality					Counter32,
		srvccSuccOutGeranQuality					Counter32,
		srvccFailPrepOutGeranQuaNoResponse					Counter32,
		srvccFailPrepOutGeranQuaTgtFailure					Counter32,
		srvccFailPrepOutGeranQuaOther					Counter32,
		srvccFailOutGeranCovMme					Counter32,
		srvccFailOutGeranQuaMme					Counter32,
		srvccFailOutUtranMme					Counter32,
		srvccAttOutDelay					Counter32,
		srvccSuccOutDelay					Counter32,
		srvccOutExecPenalty					Counter32,
		measVolteDelInterFreqMeasNum					Counter32,
		measVolteReconfMeasNum					Counter32,
		measVolteDelInterRatMeasNum					Counter32
		}


	srvccLcId		 OBJECT-TYPE
		SYNTAX					 Integer32( 0 .. 23 )
		MAX-ACCESS			 not-accessible
		STATUS					 current
		DESCRIPTION			 " -- "
		::=  { srvccEntry  1 }


	srvccRowStatus		 OBJECT-TYPE
		SYNTAX					 RowStatus
		MAX-ACCESS			 read-only
		STATUS					 current
		DESCRIPTION			 " -- "
		::=  { srvccEntry  2 }


	srvccAttOutGeranCoverage		 OBJECT-TYPE
		SYNTAX					 Counter32
		MAX-ACCESS			 read-only
		STATUS					 current
		DESCRIPTION			 " -- "
		::=  { srvccEntry  3 }


	srvccSuccOutPrepGeranCoverage		 OBJECT-TYPE
		SYNTAX					 Counter32
		MAX-ACCESS			 read-only
		STATUS					 current
		DESCRIPTION			 " -- "
		::=  { srvccEntry  4 }


	srvccAttOutExecGeranCoverage		 OBJECT-TYPE
		SYNTAX					 Counter32
		MAX-ACCESS			 read-only
		STATUS					 current
		DESCRIPTION			 " -- "
		::=  { srvccEntry  5 }


	srvccSuccOutGeranCoverage		 OBJECT-TYPE
		SYNTAX					 Counter32
		MAX-ACCESS			 read-only
		STATUS					 current
		DESCRIPTION			 " -- "
		::=  { srvccEntry  6 }


	srvccFailPrepOutGeranCovNoResponse		 OBJECT-TYPE
		SYNTAX					 Counter32
		MAX-ACCESS			 read-only
		STATUS					 current
		DESCRIPTION			 " -- "
		::=  { srvccEntry  7 }


	srvccFailPrepOutGeranCovTgtFailure		 OBJECT-TYPE
		SYNTAX					 Counter32
		MAX-ACCESS			 read-only
		STATUS					 current
		DESCRIPTION			 " -- "
		::=  { srvccEntry  8 }


	srvccFailPrepOutGeranCovOther		 OBJECT-TYPE
		SYNTAX					 Counter32
		MAX-ACCESS			 read-only
		STATUS					 current
		DESCRIPTION			 " -- "
		::=  { srvccEntry  9 }


	srvccAttOutUtran		 OBJECT-TYPE
		SYNTAX					 Counter32
		MAX-ACCESS			 read-only
		STATUS					 current
		DESCRIPTION			 " -- "
		::=  { srvccEntry  10 }


	srvccSuccOutPrepUtran		 OBJECT-TYPE
		SYNTAX					 Counter32
		MAX-ACCESS			 read-only
		STATUS					 current
		DESCRIPTION			 " -- "
		::=  { srvccEntry  11 }


	srvccAttOutExecUtran		 OBJECT-TYPE
		SYNTAX					 Counter32
		MAX-ACCESS			 read-only
		STATUS					 current
		DESCRIPTION			 " -- "
		::=  { srvccEntry  12 }


	srvccSuccOutUtran		 OBJECT-TYPE
		SYNTAX					 Counter32
		MAX-ACCESS			 read-only
		STATUS					 current
		DESCRIPTION			 " -- "
		::=  { srvccEntry  13 }


	srvccFailPrepOutUtranNoResponse		 OBJECT-TYPE
		SYNTAX					 Counter32
		MAX-ACCESS			 read-only
		STATUS					 current
		DESCRIPTION			 " -- "
		::=  { srvccEntry  14 }


	srvccFailPrepOutUtranTgtFailure		 OBJECT-TYPE
		SYNTAX					 Counter32
		MAX-ACCESS			 read-only
		STATUS					 current
		DESCRIPTION			 " -- "
		::=  { srvccEntry  15 }


	srvccFailPrepOutUtranOther		 OBJECT-TYPE
		SYNTAX					 Counter32
		MAX-ACCESS			 read-only
		STATUS					 current
		DESCRIPTION			 " -- "
		::=  { srvccEntry  16 }


	srvccAttOutGeranQuality		 OBJECT-TYPE
		SYNTAX					 Counter32
		MAX-ACCESS			 read-only
		STATUS					 current
		DESCRIPTION			 " -- "
		::=  { srvccEntry  17 }


	srvccSuccOutPrepGeranQuality		 OBJECT-TYPE
		SYNTAX					 Counter32
		MAX-ACCESS			 read-only
		STATUS					 current
		DESCRIPTION			 " -- "
		::=  { srvccEntry  18 }


	srvccAttOutExecGeranQuality		 OBJECT-TYPE
		SYNTAX					 Counter32
		MAX-ACCESS			 read-only
		STATUS					 current
		DESCRIPTION			 " -- "
		::=  { srvccEntry  19 }


	srvccSuccOutGeranQuality		 OBJECT-TYPE
		SYNTAX					 Counter32
		MAX-ACCESS			 read-only
		STATUS					 current
		DESCRIPTION			 " -- "
		::=  { srvccEntry  20 }


	srvccFailPrepOutGeranQuaNoResponse		 OBJECT-TYPE
		SYNTAX					 Counter32
		MAX-ACCESS			 read-only
		STATUS					 current
		DESCRIPTION			 " -- "
		::=  { srvccEntry  21 }


	srvccFailPrepOutGeranQuaTgtFailure		 OBJECT-TYPE
		SYNTAX					 Counter32
		MAX-ACCESS			 read-only
		STATUS					 current
		DESCRIPTION			 " -- "
		::=  { srvccEntry  22 }


	srvccFailPrepOutGeranQuaOther		 OBJECT-TYPE
		SYNTAX					 Counter32
		MAX-ACCESS			 read-only
		STATUS					 current
		DESCRIPTION			 " -- "
		::=  { srvccEntry  23 }


	srvccFailOutGeranCovMme		 OBJECT-TYPE
		SYNTAX					 Counter32
		MAX-ACCESS			 read-only
		STATUS					 current
		DESCRIPTION			 " -- "
		::=  { srvccEntry  24 }


	srvccFailOutGeranQuaMme		 OBJECT-TYPE
		SYNTAX					 Counter32
		MAX-ACCESS			 read-only
		STATUS					 current
		DESCRIPTION			 " -- "
		::=  { srvccEntry  25 }


	srvccFailOutUtranMme		 OBJECT-TYPE
		SYNTAX					 Counter32
		MAX-ACCESS			 read-only
		STATUS					 current
		DESCRIPTION			 " -- "
		::=  { srvccEntry  26 }


	srvccAttOutDelay		 OBJECT-TYPE
		SYNTAX					 Counter32
		MAX-ACCESS			 read-only
		STATUS					 current
		DESCRIPTION			 " -- "
		::=  { srvccEntry  27 }


	srvccSuccOutDelay		 OBJECT-TYPE
		SYNTAX					 Counter32
		MAX-ACCESS			 read-only
		STATUS					 current
		DESCRIPTION			 " -- "
		::=  { srvccEntry  28 }


	srvccOutExecPenalty		 OBJECT-TYPE
		SYNTAX					 Counter32
		MAX-ACCESS			 read-only
		STATUS					 current
		DESCRIPTION			 " -- "
		::=  { srvccEntry  29 }


	measVolteDelInterFreqMeasNum		 OBJECT-TYPE
		SYNTAX					 Counter32
		MAX-ACCESS			 read-only
		STATUS					 current
		DESCRIPTION			 " -- "
		::=  { srvccEntry  30 }


	measVolteReconfMeasNum		 OBJECT-TYPE
		SYNTAX					 Counter32
		MAX-ACCESS			 read-only
		STATUS					 current
		DESCRIPTION			 " -- "
		::=  { srvccEntry  31 }


	measVolteDelInterRatMeasNum		 OBJECT-TYPE
		SYNTAX					 Counter32
		MAX-ACCESS			 read-only
		STATUS					 current
		DESCRIPTION			 " -- "
		::=  { srvccEntry  32 }


	equivalentPRBUsageTable		 OBJECT-TYPE
		SYNTAX					 SEQUENCE  OF	 EquivalentPRBUsageEntry
		MAX-ACCESS			 not-accessible
		STATUS					 current
		DESCRIPTION			 " -- "
		::=  { rrcrelatedOriginCounter  26 }


	equivalentPRBUsageEntry		 OBJECT-TYPE
		SYNTAX					 EquivalentPRBUsageEntry
		MAX-ACCESS			 not-accessible
		STATUS					 current
		DESCRIPTION			 " -- "
		INDEX						{ equivalentPRBUsageLcId }
		::=  { equivalentPRBUsageTable  1 }


	EquivalentPRBUsageEntry		 ::=  SEQUENCE {
		equivalentPRBUsageLcId					Integer32,
		equivalentPRBUsageRowStatus					RowStatus,
		equivalentprbusageulmean					Counter32,
		equivalentprbusagedlmean					Counter32
		}


	equivalentPRBUsageLcId		 OBJECT-TYPE
		SYNTAX					 Integer32( 0 .. 23 )
		MAX-ACCESS			 not-accessible
		STATUS					 current
		DESCRIPTION			 " -- "
		::=  { equivalentPRBUsageEntry  1 }


	equivalentPRBUsageRowStatus		 OBJECT-TYPE
		SYNTAX					 RowStatus
		MAX-ACCESS			 read-only
		STATUS					 current
		DESCRIPTION			 " -- "
		::=  { equivalentPRBUsageEntry  2 }


	equivalentprbusageulmean		 OBJECT-TYPE
		SYNTAX					 Counter32
		MAX-ACCESS			 read-only
		STATUS					 current
		DESCRIPTION			 " -- "
		::=  { equivalentPRBUsageEntry  3 }


	equivalentprbusagedlmean		 OBJECT-TYPE
		SYNTAX					 Counter32
		MAX-ACCESS			 read-only
		STATUS					 current
		DESCRIPTION			 " -- "
		::=  { equivalentPRBUsageEntry  4 }


	coMPUeNumberTable		 OBJECT-TYPE
		SYNTAX					 SEQUENCE  OF	 CoMPUeNumberEntry
		MAX-ACCESS			 not-accessible
		STATUS					 current
		DESCRIPTION			 " -- "
		::=  { rrcrelatedOriginCounter  27 }


	coMPUeNumberEntry		 OBJECT-TYPE
		SYNTAX					 CoMPUeNumberEntry
		MAX-ACCESS			 not-accessible
		STATUS					 current
		DESCRIPTION			 " -- "
		INDEX						{ coMPUeNumberLcId }
		::=  { coMPUeNumberTable  1 }


	CoMPUeNumberEntry		 ::=  SEQUENCE {
		coMPUeNumberLcId					Integer32,
		coMPUeNumberRowStatus					RowStatus,
		rrcMeanNbrCoMPUl					Counter32,
		rrcMeanNbrCoMPDl					Counter32
		}


	coMPUeNumberLcId		 OBJECT-TYPE
		SYNTAX					 Integer32( 0 .. 23 )
		MAX-ACCESS			 not-accessible
		STATUS					 current
		DESCRIPTION			 " -- "
		::=  { coMPUeNumberEntry  1 }


	coMPUeNumberRowStatus		 OBJECT-TYPE
		SYNTAX					 RowStatus
		MAX-ACCESS			 read-only
		STATUS					 current
		DESCRIPTION			 " -- "
		::=  { coMPUeNumberEntry  2 }


	rrcMeanNbrCoMPUl		 OBJECT-TYPE
		SYNTAX					 Counter32
		MAX-ACCESS			 read-only
		STATUS					 current
		DESCRIPTION			 " -- "
		::=  { coMPUeNumberEntry  3 }


	rrcMeanNbrCoMPDl		 OBJECT-TYPE
		SYNTAX					 Counter32
		MAX-ACCESS			 read-only
		STATUS					 current
		DESCRIPTION			 " -- "
		::=  { coMPUeNumberEntry  4 }


	douAdjcHOProToGsmTable		 OBJECT-TYPE
		SYNTAX					 SEQUENCE  OF	 DouAdjcHOProToGsmEntry
		MAX-ACCESS			 not-accessible
		STATUS					 current
		DESCRIPTION			 " -- "
		::=  { rrcrelatedOriginCounter  28 }


	douAdjcHOProToGsmEntry		 OBJECT-TYPE
		SYNTAX					 DouAdjcHOProToGsmEntry
		MAX-ACCESS			 not-accessible
		STATUS					 current
		DESCRIPTION			 " -- "
		INDEX						{ douAdjcHOProToGsmCellAdjCellLcId,douAdjcHOProToGsmCellAdjCellIndex }
		::=  { douAdjcHOProToGsmTable  1 }


	DouAdjcHOProToGsmEntry		 ::=  SEQUENCE {
		douAdjcHOProToGsmCellAdjCellLcId					Integer32,
		douAdjcHOProToGsmCellAdjCellIndex					Integer32,
		douAdjcHOProToGsmRowStatus					RowStatus,
		hoToGsmAttOutPerRelation					Counter32,
		hoToGsmSuccOutPrepPerRelation					Counter32,
		hoToGsmSuccOutPerRelation					Counter32
		}


	douAdjcHOProToGsmCellAdjCellLcId		 OBJECT-TYPE
		SYNTAX					 Integer32( 0 .. 23 )
		MAX-ACCESS			 not-accessible
		STATUS					 current
		DESCRIPTION			 " -- "
		::=  { douAdjcHOProToGsmEntry  1 }


	douAdjcHOProToGsmCellAdjCellIndex		 OBJECT-TYPE
		SYNTAX					 Integer32( 1 .. 256 )
		MAX-ACCESS			 not-accessible
		STATUS					 current
		DESCRIPTION			 " -- "
		::=  { douAdjcHOProToGsmEntry  2 }


	douAdjcHOProToGsmRowStatus		 OBJECT-TYPE
		SYNTAX					 RowStatus
		MAX-ACCESS			 read-only
		STATUS					 current
		DESCRIPTION			 " -- "
		::=  { douAdjcHOProToGsmEntry  3 }


	hoToGsmAttOutPerRelation		 OBJECT-TYPE
		SYNTAX					 Counter32
		MAX-ACCESS			 read-only
		STATUS					 current
		DESCRIPTION			 " -- "
		::=  { douAdjcHOProToGsmEntry  4 }


	hoToGsmSuccOutPrepPerRelation		 OBJECT-TYPE
		SYNTAX					 Counter32
		MAX-ACCESS			 read-only
		STATUS					 current
		DESCRIPTION			 " -- "
		::=  { douAdjcHOProToGsmEntry  5 }


	hoToGsmSuccOutPerRelation		 OBJECT-TYPE
		SYNTAX					 Counter32
		MAX-ACCESS			 read-only
		STATUS					 current
		DESCRIPTION			 " -- "
		::=  { douAdjcHOProToGsmEntry  6 }


	eutraAdjCellMeasTable		 OBJECT-TYPE
		SYNTAX					 SEQUENCE  OF	 EutraAdjCellMeasEntry
		MAX-ACCESS			 not-accessible
		STATUS					 current
		DESCRIPTION			 " -- "
		::=  { rrcrelatedOriginCounter  29 }


	eutraAdjCellMeasEntry		 OBJECT-TYPE
		SYNTAX					 EutraAdjCellMeasEntry
		MAX-ACCESS			 not-accessible
		STATUS					 current
		DESCRIPTION			 " -- "
		INDEX						{ eutraAdjCellMeasCellAdjEutraCellIndex }
		::=  { eutraAdjCellMeasTable  1 }


	EutraAdjCellMeasEntry		 ::=  SEQUENCE {
		eutraAdjCellMeasCellAdjEutraCellIndex					Integer32,
		eutraAdjCellMeasRowStatus					RowStatus,
		hoPenaltyEutra					Counter32
		}


	eutraAdjCellMeasCellAdjEutraCellIndex		 OBJECT-TYPE
		SYNTAX					 Integer32( 0 .. 383 )
		MAX-ACCESS			 not-accessible
		STATUS					 current
		DESCRIPTION			 " -- "
		::=  { eutraAdjCellMeasEntry  1 }


	eutraAdjCellMeasRowStatus		 OBJECT-TYPE
		SYNTAX					 RowStatus
		MAX-ACCESS			 read-only
		STATUS					 current
		DESCRIPTION			 " -- "
		::=  { eutraAdjCellMeasEntry  2 }


	hoPenaltyEutra		 OBJECT-TYPE
		SYNTAX					 Counter32
		MAX-ACCESS			 read-only
		STATUS					 current
		DESCRIPTION			 " -- "
		::=  { eutraAdjCellMeasEntry  3 }


	rrcProcofRUETable		 OBJECT-TYPE
		SYNTAX					 SEQUENCE  OF	 RrcProcofRUEEntry
		MAX-ACCESS			 not-accessible
		STATUS					 current
		DESCRIPTION			 " -- "
		::=  { rrcrelatedOriginCounter  30 }


	rrcProcofRUEEntry		 OBJECT-TYPE
		SYNTAX					 RrcProcofRUEEntry
		MAX-ACCESS			 not-accessible
		STATUS					 current
		DESCRIPTION			 " -- "
		INDEX						{ rrcProcofRUELcId }
		::=  { rrcProcofRUETable  1 }


	RrcProcofRUEEntry		 ::=  SEQUENCE {
		rrcProcofRUELcId					Integer32,
		rrcProcofRUERowStatus					RowStatus,
		rueRRCConnReEstabAtt					Counter32,
		rueRRCConnReEstabSucc					Counter32,
		rueRRCAttConnReconfig					Counter32,
		rueRRCSuccConnReconfig					Counter32,
		rueRRCConnMax					Counter32
		}


	rrcProcofRUELcId		 OBJECT-TYPE
		SYNTAX					 Integer32( 0 .. 23 )
		MAX-ACCESS			 not-accessible
		STATUS					 current
		DESCRIPTION			 " -- "
		::=  { rrcProcofRUEEntry  1 }


	rrcProcofRUERowStatus		 OBJECT-TYPE
		SYNTAX					 RowStatus
		MAX-ACCESS			 read-only
		STATUS					 current
		DESCRIPTION			 " -- "
		::=  { rrcProcofRUEEntry  2 }


	rueRRCConnReEstabAtt		 OBJECT-TYPE
		SYNTAX					 Counter32
		MAX-ACCESS			 read-only
		STATUS					 current
		DESCRIPTION			 " -- "
		::=  { rrcProcofRUEEntry  3 }


	rueRRCConnReEstabSucc		 OBJECT-TYPE
		SYNTAX					 Counter32
		MAX-ACCESS			 read-only
		STATUS					 current
		DESCRIPTION			 " -- "
		::=  { rrcProcofRUEEntry  4 }


	rueRRCAttConnReconfig		 OBJECT-TYPE
		SYNTAX					 Counter32
		MAX-ACCESS			 read-only
		STATUS					 current
		DESCRIPTION			 " -- "
		::=  { rrcProcofRUEEntry  5 }


	rueRRCSuccConnReconfig		 OBJECT-TYPE
		SYNTAX					 Counter32
		MAX-ACCESS			 read-only
		STATUS					 current
		DESCRIPTION			 " -- "
		::=  { rrcProcofRUEEntry  6 }


	rueRRCConnMax		 OBJECT-TYPE
		SYNTAX					 Counter32
		MAX-ACCESS			 read-only
		STATUS					 current
		DESCRIPTION			 " -- "
		::=  { rrcProcofRUEEntry  7 }


	highSpeedStatisticTable		 OBJECT-TYPE
		SYNTAX					 SEQUENCE  OF	 HighSpeedStatisticEntry
		MAX-ACCESS			 not-accessible
		STATUS					 current
		DESCRIPTION			 " -- "
		::=  { rrcrelatedOriginCounter  31 }


	highSpeedStatisticEntry		 OBJECT-TYPE
		SYNTAX					 HighSpeedStatisticEntry
		MAX-ACCESS			 not-accessible
		STATUS					 current
		DESCRIPTION			 " -- "
		INDEX						{ highSpeedStatisticLcId }
		::=  { highSpeedStatisticTable  1 }


	HighSpeedStatisticEntry		 ::=  SEQUENCE {
		highSpeedStatisticLcId					Integer32,
		highSpeedStatisticRowStatus					RowStatus,
		hsLowSpeedUserHoAttOut					Counter32,
		hsLowSpeedUserHoSuccOut					Counter32,
		hsLowSpeedUserRelocation					Counter32,
		hsHighSpeedUserRelocation					Counter32,
		hsDirectionalHoAttOut					Counter32,
		hsDirectionalHoSuccOut					Counter32
		}


	highSpeedStatisticLcId		 OBJECT-TYPE
		SYNTAX					 Integer32( 0 .. 23 )
		MAX-ACCESS			 not-accessible
		STATUS					 current
		DESCRIPTION			 " -- "
		::=  { highSpeedStatisticEntry  1 }


	highSpeedStatisticRowStatus		 OBJECT-TYPE
		SYNTAX					 RowStatus
		MAX-ACCESS			 read-only
		STATUS					 current
		DESCRIPTION			 " -- "
		::=  { highSpeedStatisticEntry  2 }


	hsLowSpeedUserHoAttOut		 OBJECT-TYPE
		SYNTAX					 Counter32
		MAX-ACCESS			 read-only
		STATUS					 current
		DESCRIPTION			 " -- "
		::=  { highSpeedStatisticEntry  3 }


	hsLowSpeedUserHoSuccOut		 OBJECT-TYPE
		SYNTAX					 Counter32
		MAX-ACCESS			 read-only
		STATUS					 current
		DESCRIPTION			 " -- "
		::=  { highSpeedStatisticEntry  4 }


	hsLowSpeedUserRelocation		 OBJECT-TYPE
		SYNTAX					 Counter32
		MAX-ACCESS			 read-only
		STATUS					 current
		DESCRIPTION			 " -- "
		::=  { highSpeedStatisticEntry  5 }


	hsHighSpeedUserRelocation		 OBJECT-TYPE
		SYNTAX					 Counter32
		MAX-ACCESS			 read-only
		STATUS					 current
		DESCRIPTION			 " -- "
		::=  { highSpeedStatisticEntry  6 }


	hsDirectionalHoAttOut		 OBJECT-TYPE
		SYNTAX					 Counter32
		MAX-ACCESS			 read-only
		STATUS					 current
		DESCRIPTION			 " -- "
		::=  { highSpeedStatisticEntry  7 }


	hsDirectionalHoSuccOut		 OBJECT-TYPE
		SYNTAX					 Counter32
		MAX-ACCESS			 read-only
		STATUS					 current
		DESCRIPTION			 " -- "
		::=  { highSpeedStatisticEntry  8 }


	caPerformanceByRRCTable		 OBJECT-TYPE
		SYNTAX					 SEQUENCE  OF	 CaPerformanceByRRCEntry
		MAX-ACCESS			 not-accessible
		STATUS					 current
		DESCRIPTION			 " -- "
		::=  { rrcrelatedOriginCounter  32 }


	caPerformanceByRRCEntry		 OBJECT-TYPE
		SYNTAX					 CaPerformanceByRRCEntry
		MAX-ACCESS			 not-accessible
		STATUS					 current
		DESCRIPTION			 " -- "
		INDEX						{ caPerformanceByRRCLcId }
		::=  { caPerformanceByRRCTable  1 }


	CaPerformanceByRRCEntry		 ::=  SEQUENCE {
		caPerformanceByRRCLcId					Integer32,
		caPerformanceByRRCRowStatus					RowStatus,
		rrcCAConfigNbrPCellDl2CC					Counter32,
		rrcCAConfigMaxNbrPCellDl2CC					Counter32,
		rrcCAConfigSampNbr					Counter32,
		rrcCAConfigNbrPCellUl2CC					Counter32,
		rrcCAConfigMaxNbrPCellUl2CC					Counter32,
		rrcCASCellConfigAtt					Counter32,
		rrcCASCellConfigSucc					Counter32,
		rrcCASCellReleaseAtt					Counter32,
		rrcCASCellReleaseSucc					Counter32,
		rrcCAConfigNbrSCellDl2CC					Counter32,
		rrcCAConfigMaxNbrSCellDl2CC					Counter32,
		rrcCAConfigNbrSCellUl2CC					Counter32,
		rrcCAConfigMaxNbrSCellUl2CC					Counter32,
		rrcCAConfigNbrPCellDl2CCTF					Counter32,
		rrcCAConfigMaxNbrPCellDl2CCTF					Counter32,
		rrcTFCACapUserNbrFddPCell					Counter32,
		rrcTFCACapUserMaxNbrFddPCell					Counter32,
		rrcTFCACapUserNbrTddPCell					Counter32,
		rrcTFCACapUserMaxNbrTddPCell					Counter32
		}


	caPerformanceByRRCLcId		 OBJECT-TYPE
		SYNTAX					 Integer32( 0 .. 23 )
		MAX-ACCESS			 not-accessible
		STATUS					 current
		DESCRIPTION			 " -- "
		::=  { caPerformanceByRRCEntry  1 }


	caPerformanceByRRCRowStatus		 OBJECT-TYPE
		SYNTAX					 RowStatus
		MAX-ACCESS			 read-only
		STATUS					 current
		DESCRIPTION			 " -- "
		::=  { caPerformanceByRRCEntry  2 }


	rrcCAConfigNbrPCellDl2CC		 OBJECT-TYPE
		SYNTAX					 Counter32
		MAX-ACCESS			 read-only
		STATUS					 current
		DESCRIPTION			 " -- "
		::=  { caPerformanceByRRCEntry  3 }


	rrcCAConfigMaxNbrPCellDl2CC		 OBJECT-TYPE
		SYNTAX					 Counter32
		MAX-ACCESS			 read-only
		STATUS					 current
		DESCRIPTION			 " -- "
		::=  { caPerformanceByRRCEntry  4 }


	rrcCAConfigSampNbr		 OBJECT-TYPE
		SYNTAX					 Counter32
		MAX-ACCESS			 read-only
		STATUS					 current
		DESCRIPTION			 " -- "
		::=  { caPerformanceByRRCEntry  5 }


	rrcCAConfigNbrPCellUl2CC		 OBJECT-TYPE
		SYNTAX					 Counter32
		MAX-ACCESS			 read-only
		STATUS					 current
		DESCRIPTION			 " -- "
		::=  { caPerformanceByRRCEntry  6 }


	rrcCAConfigMaxNbrPCellUl2CC		 OBJECT-TYPE
		SYNTAX					 Counter32
		MAX-ACCESS			 read-only
		STATUS					 current
		DESCRIPTION			 " -- "
		::=  { caPerformanceByRRCEntry  7 }


	rrcCASCellConfigAtt		 OBJECT-TYPE
		SYNTAX					 Counter32
		MAX-ACCESS			 read-only
		STATUS					 current
		DESCRIPTION			 " -- "
		::=  { caPerformanceByRRCEntry  8 }


	rrcCASCellConfigSucc		 OBJECT-TYPE
		SYNTAX					 Counter32
		MAX-ACCESS			 read-only
		STATUS					 current
		DESCRIPTION			 " -- "
		::=  { caPerformanceByRRCEntry  9 }


	rrcCASCellReleaseAtt		 OBJECT-TYPE
		SYNTAX					 Counter32
		MAX-ACCESS			 read-only
		STATUS					 current
		DESCRIPTION			 " -- "
		::=  { caPerformanceByRRCEntry  10 }


	rrcCASCellReleaseSucc		 OBJECT-TYPE
		SYNTAX					 Counter32
		MAX-ACCESS			 read-only
		STATUS					 current
		DESCRIPTION			 " -- "
		::=  { caPerformanceByRRCEntry  11 }


	rrcCAConfigNbrSCellDl2CC		 OBJECT-TYPE
		SYNTAX					 Counter32
		MAX-ACCESS			 read-only
		STATUS					 current
		DESCRIPTION			 " -- "
		::=  { caPerformanceByRRCEntry  12 }


	rrcCAConfigMaxNbrSCellDl2CC		 OBJECT-TYPE
		SYNTAX					 Counter32
		MAX-ACCESS			 read-only
		STATUS					 current
		DESCRIPTION			 " -- "
		::=  { caPerformanceByRRCEntry  13 }


	rrcCAConfigNbrSCellUl2CC		 OBJECT-TYPE
		SYNTAX					 Counter32
		MAX-ACCESS			 read-only
		STATUS					 current
		DESCRIPTION			 " -- "
		::=  { caPerformanceByRRCEntry  14 }


	rrcCAConfigMaxNbrSCellUl2CC		 OBJECT-TYPE
		SYNTAX					 Counter32
		MAX-ACCESS			 read-only
		STATUS					 current
		DESCRIPTION			 " -- "
		::=  { caPerformanceByRRCEntry  15 }


	rrcCAConfigNbrPCellDl2CCTF		 OBJECT-TYPE
		SYNTAX					 Counter32
		MAX-ACCESS			 read-only
		STATUS					 current
		DESCRIPTION			 " -- "
		::=  { caPerformanceByRRCEntry  16 }


	rrcCAConfigMaxNbrPCellDl2CCTF		 OBJECT-TYPE
		SYNTAX					 Counter32
		MAX-ACCESS			 read-only
		STATUS					 current
		DESCRIPTION			 " -- "
		::=  { caPerformanceByRRCEntry  17 }


	rrcTFCACapUserNbrFddPCell		 OBJECT-TYPE
		SYNTAX					 Counter32
		MAX-ACCESS			 read-only
		STATUS					 current
		DESCRIPTION			 " -- "
		::=  { caPerformanceByRRCEntry  18 }


	rrcTFCACapUserMaxNbrFddPCell		 OBJECT-TYPE
		SYNTAX					 Counter32
		MAX-ACCESS			 read-only
		STATUS					 current
		DESCRIPTION			 " -- "
		::=  { caPerformanceByRRCEntry  19 }


	rrcTFCACapUserNbrTddPCell		 OBJECT-TYPE
		SYNTAX					 Counter32
		MAX-ACCESS			 read-only
		STATUS					 current
		DESCRIPTION			 " -- "
		::=  { caPerformanceByRRCEntry  20 }


	rrcTFCACapUserMaxNbrTddPCell		 OBJECT-TYPE
		SYNTAX					 Counter32
		MAX-ACCESS			 read-only
		STATUS					 current
		DESCRIPTION			 " -- "
		::=  { caPerformanceByRRCEntry  21 }


	handOverIntraCellTable		 OBJECT-TYPE
		SYNTAX					 SEQUENCE  OF	 HandOverIntraCellEntry
		MAX-ACCESS			 not-accessible
		STATUS					 current
		DESCRIPTION			 " -- "
		::=  { rrcrelatedOriginCounter  33 }


	handOverIntraCellEntry		 OBJECT-TYPE
		SYNTAX					 HandOverIntraCellEntry
		MAX-ACCESS			 not-accessible
		STATUS					 current
		DESCRIPTION			 " -- "
		INDEX						{ handOverIntraCellLcId }
		::=  { handOverIntraCellTable  1 }


	HandOverIntraCellEntry		 ::=  SEQUENCE {
		handOverIntraCellLcId					Integer32,
		handOverIntraCellRowStatus					RowStatus,
		hoAttOutIntraCell					Counter32,
		hoSuccIncIntraCell					Counter32,
		hoFailOutIntraCellNoRsp					Counter32
		}


	handOverIntraCellLcId		 OBJECT-TYPE
		SYNTAX					 Integer32( 0 .. 23 )
		MAX-ACCESS			 not-accessible
		STATUS					 current
		DESCRIPTION			 " -- "
		::=  { handOverIntraCellEntry  1 }


	handOverIntraCellRowStatus		 OBJECT-TYPE
		SYNTAX					 RowStatus
		MAX-ACCESS			 read-only
		STATUS					 current
		DESCRIPTION			 " -- "
		::=  { handOverIntraCellEntry  2 }


	hoAttOutIntraCell		 OBJECT-TYPE
		SYNTAX					 Counter32
		MAX-ACCESS			 read-only
		STATUS					 current
		DESCRIPTION			 " -- "
		::=  { handOverIntraCellEntry  3 }


	hoSuccIncIntraCell		 OBJECT-TYPE
		SYNTAX					 Counter32
		MAX-ACCESS			 read-only
		STATUS					 current
		DESCRIPTION			 " -- "
		::=  { handOverIntraCellEntry  4 }


	hoFailOutIntraCellNoRsp		 OBJECT-TYPE
		SYNTAX					 Counter32
		MAX-ACCESS			 read-only
		STATUS					 current
		DESCRIPTION			 " -- "
		::=  { handOverIntraCellEntry  5 }


	geranAdjCellMeasTable		 OBJECT-TYPE
		SYNTAX					 SEQUENCE  OF	 GeranAdjCellMeasEntry
		MAX-ACCESS			 not-accessible
		STATUS					 current
		DESCRIPTION			 " -- "
		::=  { rrcrelatedOriginCounter  34 }


	geranAdjCellMeasEntry		 OBJECT-TYPE
		SYNTAX					 GeranAdjCellMeasEntry
		MAX-ACCESS			 not-accessible
		STATUS					 current
		DESCRIPTION			 " -- "
		INDEX						{ geranAdjCellMeasCellAdjGeranCellIndex }
		::=  { geranAdjCellMeasTable  1 }


	GeranAdjCellMeasEntry		 ::=  SEQUENCE {
		geranAdjCellMeasCellAdjGeranCellIndex					Integer32,
		geranAdjCellMeasRowStatus					RowStatus,
		hoPenaltyGeran					Counter32
		}


	geranAdjCellMeasCellAdjGeranCellIndex		 OBJECT-TYPE
		SYNTAX					 Integer32( 0 .. 191 )
		MAX-ACCESS			 not-accessible
		STATUS					 current
		DESCRIPTION			 " -- "
		::=  { geranAdjCellMeasEntry  1 }


	geranAdjCellMeasRowStatus		 OBJECT-TYPE
		SYNTAX					 RowStatus
		MAX-ACCESS			 read-only
		STATUS					 current
		DESCRIPTION			 " -- "
		::=  { geranAdjCellMeasEntry  2 }


	hoPenaltyGeran		 OBJECT-TYPE
		SYNTAX					 Counter32
		MAX-ACCESS			 read-only
		STATUS					 current
		DESCRIPTION			 " -- "
		::=  { geranAdjCellMeasEntry  3 }


	rrcPresetPerformanceTable		 OBJECT-TYPE
		SYNTAX					 SEQUENCE  OF	 RrcPresetPerformanceEntry
		MAX-ACCESS			 not-accessible
		STATUS					 current
		DESCRIPTION			 " -- "
		::=  { rrcrelatedOriginCounter  35 }


	rrcPresetPerformanceEntry		 OBJECT-TYPE
		SYNTAX					 RrcPresetPerformanceEntry
		MAX-ACCESS			 not-accessible
		STATUS					 current
		DESCRIPTION			 " -- "
		INDEX						{ rrcPresetPerformanceLcId }
		::=  { rrcPresetPerformanceTable  1 }


	RrcPresetPerformanceEntry		 ::=  SEQUENCE {
		rrcPresetPerformanceLcId					Integer32,
		rrcPresetPerformanceRowStatus					RowStatus,
		rrcPreset1					Counter32,
		rrcPreset2					Counter32,
		rrcPreset3					Counter32,
		rrcPreset4					Counter32,
		rrcPreset5					Counter32,
		rrcPreset6					Counter32,
		rrcPreset7					Counter32,
		rrcPreset8					Counter32,
		rrcPreset9					Counter32,
		rrcPreset10					Counter32,
		rrcPreset11					Counter32,
		rrcPreset12					Counter32,
		rrcPreset13					Counter32,
		rrcPreset14					Counter32,
		rrcPreset15					Counter32,
		rrcPreset16					Counter32,
		rrcPreset17					Counter32,
		rrcPreset18					Counter32,
		rrcPreset19					Counter32,
		rrcPreset20					Counter32,
		rrcPreset21					Counter32,
		rrcPreset22					Counter32,
		rrcPreset23					Counter32,
		rrcPreset24					Counter32,
		rrcPreset25					Counter32,
		rrcPreset26					Counter32,
		rrcPreset27					Counter32,
		rrcPreset28					Counter32,
		rrcPreset29					Counter32,
		rrcPreset30					Counter32,
		rrcPreset31					Counter32,
		rrcPreset32					Counter32,
		rrcPreset33					Counter32,
		rrcPreset34					Counter32,
		rrcPreset35					Counter32,
		rrcPreset36					Counter32,
		rrcPreset37					Counter32,
		rrcPreset38					Counter32,
		rrcPreset39					Counter32,
		rrcPreset40					Counter32
		}


	rrcPresetPerformanceLcId		 OBJECT-TYPE
		SYNTAX					 Integer32( 0 .. 23 )
		MAX-ACCESS			 not-accessible
		STATUS					 current
		DESCRIPTION			 " -- "
		::=  { rrcPresetPerformanceEntry  1 }


	rrcPresetPerformanceRowStatus		 OBJECT-TYPE
		SYNTAX					 RowStatus
		MAX-ACCESS			 read-only
		STATUS					 current
		DESCRIPTION			 " -- "
		::=  { rrcPresetPerformanceEntry  2 }


	rrcPreset1		 OBJECT-TYPE
		SYNTAX					 Counter32
		MAX-ACCESS			 read-only
		STATUS					 current
		DESCRIPTION			 " -- "
		::=  { rrcPresetPerformanceEntry  3 }


	rrcPreset2		 OBJECT-TYPE
		SYNTAX					 Counter32
		MAX-ACCESS			 read-only
		STATUS					 current
		DESCRIPTION			 " -- "
		::=  { rrcPresetPerformanceEntry  4 }


	rrcPreset3		 OBJECT-TYPE
		SYNTAX					 Counter32
		MAX-ACCESS			 read-only
		STATUS					 current
		DESCRIPTION			 " -- "
		::=  { rrcPresetPerformanceEntry  5 }


	rrcPreset4		 OBJECT-TYPE
		SYNTAX					 Counter32
		MAX-ACCESS			 read-only
		STATUS					 current
		DESCRIPTION			 " -- "
		::=  { rrcPresetPerformanceEntry  6 }


	rrcPreset5		 OBJECT-TYPE
		SYNTAX					 Counter32
		MAX-ACCESS			 read-only
		STATUS					 current
		DESCRIPTION			 " -- "
		::=  { rrcPresetPerformanceEntry  7 }


	rrcPreset6		 OBJECT-TYPE
		SYNTAX					 Counter32
		MAX-ACCESS			 read-only
		STATUS					 current
		DESCRIPTION			 " -- "
		::=  { rrcPresetPerformanceEntry  8 }


	rrcPreset7		 OBJECT-TYPE
		SYNTAX					 Counter32
		MAX-ACCESS			 read-only
		STATUS					 current
		DESCRIPTION			 " -- "
		::=  { rrcPresetPerformanceEntry  9 }


	rrcPreset8		 OBJECT-TYPE
		SYNTAX					 Counter32
		MAX-ACCESS			 read-only
		STATUS					 current
		DESCRIPTION			 " -- "
		::=  { rrcPresetPerformanceEntry  10 }


	rrcPreset9		 OBJECT-TYPE
		SYNTAX					 Counter32
		MAX-ACCESS			 read-only
		STATUS					 current
		DESCRIPTION			 " -- "
		::=  { rrcPresetPerformanceEntry  11 }


	rrcPreset10		 OBJECT-TYPE
		SYNTAX					 Counter32
		MAX-ACCESS			 read-only
		STATUS					 current
		DESCRIPTION			 " -- "
		::=  { rrcPresetPerformanceEntry  12 }


	rrcPreset11		 OBJECT-TYPE
		SYNTAX					 Counter32
		MAX-ACCESS			 read-only
		STATUS					 current
		DESCRIPTION			 " -- "
		::=  { rrcPresetPerformanceEntry  13 }


	rrcPreset12		 OBJECT-TYPE
		SYNTAX					 Counter32
		MAX-ACCESS			 read-only
		STATUS					 current
		DESCRIPTION			 " -- "
		::=  { rrcPresetPerformanceEntry  14 }


	rrcPreset13		 OBJECT-TYPE
		SYNTAX					 Counter32
		MAX-ACCESS			 read-only
		STATUS					 current
		DESCRIPTION			 " -- "
		::=  { rrcPresetPerformanceEntry  15 }


	rrcPreset14		 OBJECT-TYPE
		SYNTAX					 Counter32
		MAX-ACCESS			 read-only
		STATUS					 current
		DESCRIPTION			 " -- "
		::=  { rrcPresetPerformanceEntry  16 }


	rrcPreset15		 OBJECT-TYPE
		SYNTAX					 Counter32
		MAX-ACCESS			 read-only
		STATUS					 current
		DESCRIPTION			 " -- "
		::=  { rrcPresetPerformanceEntry  17 }


	rrcPreset16		 OBJECT-TYPE
		SYNTAX					 Counter32
		MAX-ACCESS			 read-only
		STATUS					 current
		DESCRIPTION			 " -- "
		::=  { rrcPresetPerformanceEntry  18 }


	rrcPreset17		 OBJECT-TYPE
		SYNTAX					 Counter32
		MAX-ACCESS			 read-only
		STATUS					 current
		DESCRIPTION			 " -- "
		::=  { rrcPresetPerformanceEntry  19 }


	rrcPreset18		 OBJECT-TYPE
		SYNTAX					 Counter32
		MAX-ACCESS			 read-only
		STATUS					 current
		DESCRIPTION			 " -- "
		::=  { rrcPresetPerformanceEntry  20 }


	rrcPreset19		 OBJECT-TYPE
		SYNTAX					 Counter32
		MAX-ACCESS			 read-only
		STATUS					 current
		DESCRIPTION			 " -- "
		::=  { rrcPresetPerformanceEntry  21 }


	rrcPreset20		 OBJECT-TYPE
		SYNTAX					 Counter32
		MAX-ACCESS			 read-only
		STATUS					 current
		DESCRIPTION			 " -- "
		::=  { rrcPresetPerformanceEntry  22 }


	rrcPreset21		 OBJECT-TYPE
		SYNTAX					 Counter32
		MAX-ACCESS			 read-only
		STATUS					 current
		DESCRIPTION			 " -- "
		::=  { rrcPresetPerformanceEntry  23 }


	rrcPreset22		 OBJECT-TYPE
		SYNTAX					 Counter32
		MAX-ACCESS			 read-only
		STATUS					 current
		DESCRIPTION			 " -- "
		::=  { rrcPresetPerformanceEntry  24 }


	rrcPreset23		 OBJECT-TYPE
		SYNTAX					 Counter32
		MAX-ACCESS			 read-only
		STATUS					 current
		DESCRIPTION			 " -- "
		::=  { rrcPresetPerformanceEntry  25 }


	rrcPreset24		 OBJECT-TYPE
		SYNTAX					 Counter32
		MAX-ACCESS			 read-only
		STATUS					 current
		DESCRIPTION			 " -- "
		::=  { rrcPresetPerformanceEntry  26 }


	rrcPreset25		 OBJECT-TYPE
		SYNTAX					 Counter32
		MAX-ACCESS			 read-only
		STATUS					 current
		DESCRIPTION			 " -- "
		::=  { rrcPresetPerformanceEntry  27 }


	rrcPreset26		 OBJECT-TYPE
		SYNTAX					 Counter32
		MAX-ACCESS			 read-only
		STATUS					 current
		DESCRIPTION			 " -- "
		::=  { rrcPresetPerformanceEntry  28 }


	rrcPreset27		 OBJECT-TYPE
		SYNTAX					 Counter32
		MAX-ACCESS			 read-only
		STATUS					 current
		DESCRIPTION			 " -- "
		::=  { rrcPresetPerformanceEntry  29 }


	rrcPreset28		 OBJECT-TYPE
		SYNTAX					 Counter32
		MAX-ACCESS			 read-only
		STATUS					 current
		DESCRIPTION			 " -- "
		::=  { rrcPresetPerformanceEntry  30 }


	rrcPreset29		 OBJECT-TYPE
		SYNTAX					 Counter32
		MAX-ACCESS			 read-only
		STATUS					 current
		DESCRIPTION			 " -- "
		::=  { rrcPresetPerformanceEntry  31 }


	rrcPreset30		 OBJECT-TYPE
		SYNTAX					 Counter32
		MAX-ACCESS			 read-only
		STATUS					 current
		DESCRIPTION			 " -- "
		::=  { rrcPresetPerformanceEntry  32 }


	rrcPreset31		 OBJECT-TYPE
		SYNTAX					 Counter32
		MAX-ACCESS			 read-only
		STATUS					 current
		DESCRIPTION			 " -- "
		::=  { rrcPresetPerformanceEntry  33 }


	rrcPreset32		 OBJECT-TYPE
		SYNTAX					 Counter32
		MAX-ACCESS			 read-only
		STATUS					 current
		DESCRIPTION			 " -- "
		::=  { rrcPresetPerformanceEntry  34 }


	rrcPreset33		 OBJECT-TYPE
		SYNTAX					 Counter32
		MAX-ACCESS			 read-only
		STATUS					 current
		DESCRIPTION			 " -- "
		::=  { rrcPresetPerformanceEntry  35 }


	rrcPreset34		 OBJECT-TYPE
		SYNTAX					 Counter32
		MAX-ACCESS			 read-only
		STATUS					 current
		DESCRIPTION			 " -- "
		::=  { rrcPresetPerformanceEntry  36 }


	rrcPreset35		 OBJECT-TYPE
		SYNTAX					 Counter32
		MAX-ACCESS			 read-only
		STATUS					 current
		DESCRIPTION			 " -- "
		::=  { rrcPresetPerformanceEntry  37 }


	rrcPreset36		 OBJECT-TYPE
		SYNTAX					 Counter32
		MAX-ACCESS			 read-only
		STATUS					 current
		DESCRIPTION			 " -- "
		::=  { rrcPresetPerformanceEntry  38 }


	rrcPreset37		 OBJECT-TYPE
		SYNTAX					 Counter32
		MAX-ACCESS			 read-only
		STATUS					 current
		DESCRIPTION			 " -- "
		::=  { rrcPresetPerformanceEntry  39 }


	rrcPreset38		 OBJECT-TYPE
		SYNTAX					 Counter32
		MAX-ACCESS			 read-only
		STATUS					 current
		DESCRIPTION			 " -- "
		::=  { rrcPresetPerformanceEntry  40 }


	rrcPreset39		 OBJECT-TYPE
		SYNTAX					 Counter32
		MAX-ACCESS			 read-only
		STATUS					 current
		DESCRIPTION			 " -- "
		::=  { rrcPresetPerformanceEntry  41 }


	rrcPreset40		 OBJECT-TYPE
		SYNTAX					 Counter32
		MAX-ACCESS			 read-only
		STATUS					 current
		DESCRIPTION			 " -- "
		::=  { rrcPresetPerformanceEntry  42 }


	rrcCAndRCheckOfCellTable		 OBJECT-TYPE
		SYNTAX					 SEQUENCE  OF	 RrcCAndRCheckOfCellEntry
		MAX-ACCESS			 not-accessible
		STATUS					 current
		DESCRIPTION			 " -- "
		::=  { rrcrelatedOriginCounter  36 }


	rrcCAndRCheckOfCellEntry		 OBJECT-TYPE
		SYNTAX					 RrcCAndRCheckOfCellEntry
		MAX-ACCESS			 not-accessible
		STATUS					 current
		DESCRIPTION			 " -- "
		INDEX						{ rrcCAndRCheckOfCellLcId }
		::=  { rrcCAndRCheckOfCellTable  1 }


	RrcCAndRCheckOfCellEntry		 ::=  SEQUENCE {
		rrcCAndRCheckOfCellLcId					Integer32,
		rrcCAndRCheckOfCellRowStatus					RowStatus,
		rrcCellUeIndexRel					Counter32,
		rrcCellCrntiRel					Counter32,
		rrcCellPucch1BcsRel					Counter32,
		rrcCellPUCCH3Rel					Counter32,
		rrcCellSrsRel					Counter32,
		rrcCellCqiRel					Counter32,
		rrcCellSrRel					Counter32,
		rrcCellUeTimeOutRel					Counter32
		}


	rrcCAndRCheckOfCellLcId		 OBJECT-TYPE
		SYNTAX					 Integer32( 0 .. 23 )
		MAX-ACCESS			 not-accessible
		STATUS					 current
		DESCRIPTION			 " -- "
		::=  { rrcCAndRCheckOfCellEntry  1 }


	rrcCAndRCheckOfCellRowStatus		 OBJECT-TYPE
		SYNTAX					 RowStatus
		MAX-ACCESS			 read-only
		STATUS					 current
		DESCRIPTION			 " -- "
		::=  { rrcCAndRCheckOfCellEntry  2 }


	rrcCellUeIndexRel		 OBJECT-TYPE
		SYNTAX					 Counter32
		MAX-ACCESS			 read-only
		STATUS					 current
		DESCRIPTION			 " -- "
		::=  { rrcCAndRCheckOfCellEntry  3 }


	rrcCellCrntiRel		 OBJECT-TYPE
		SYNTAX					 Counter32
		MAX-ACCESS			 read-only
		STATUS					 current
		DESCRIPTION			 " -- "
		::=  { rrcCAndRCheckOfCellEntry  4 }


	rrcCellPucch1BcsRel		 OBJECT-TYPE
		SYNTAX					 Counter32
		MAX-ACCESS			 read-only
		STATUS					 current
		DESCRIPTION			 " -- "
		::=  { rrcCAndRCheckOfCellEntry  5 }


	rrcCellPUCCH3Rel		 OBJECT-TYPE
		SYNTAX					 Counter32
		MAX-ACCESS			 read-only
		STATUS					 current
		DESCRIPTION			 " -- "
		::=  { rrcCAndRCheckOfCellEntry  6 }


	rrcCellSrsRel		 OBJECT-TYPE
		SYNTAX					 Counter32
		MAX-ACCESS			 read-only
		STATUS					 current
		DESCRIPTION			 " -- "
		::=  { rrcCAndRCheckOfCellEntry  7 }


	rrcCellCqiRel		 OBJECT-TYPE
		SYNTAX					 Counter32
		MAX-ACCESS			 read-only
		STATUS					 current
		DESCRIPTION			 " -- "
		::=  { rrcCAndRCheckOfCellEntry  8 }


	rrcCellSrRel		 OBJECT-TYPE
		SYNTAX					 Counter32
		MAX-ACCESS			 read-only
		STATUS					 current
		DESCRIPTION			 " -- "
		::=  { rrcCAndRCheckOfCellEntry  9 }


	rrcCellUeTimeOutRel		 OBJECT-TYPE
		SYNTAX					 Counter32
		MAX-ACCESS			 read-only
		STATUS					 current
		DESCRIPTION			 " -- "
		::=  { rrcCAndRCheckOfCellEntry  10 }


	rrcCAndRCheckOfEnb		 OBJECT IDENTIFIER
		::=  { rrcrelatedOriginCounter  37 }


	rrcCpmCaseRelP0		 OBJECT-TYPE
		SYNTAX					 Counter32
		MAX-ACCESS			 read-only
		STATUS					 current
		DESCRIPTION			 " -- "
		::=  { rrcCAndRCheckOfEnb  1 }


	rrcCpmCaseRelP2		 OBJECT-TYPE
		SYNTAX					 Counter32
		MAX-ACCESS			 read-only
		STATUS					 current
		DESCRIPTION			 " -- "
		::=  { rrcCAndRCheckOfEnb  2 }


	rrcCpmCaseRelP3		 OBJECT-TYPE
		SYNTAX					 Counter32
		MAX-ACCESS			 read-only
		STATUS					 current
		DESCRIPTION			 " -- "
		::=  { rrcCAndRCheckOfEnb  3 }


	rrcCpmCaseRelP4		 OBJECT-TYPE
		SYNTAX					 Counter32
		MAX-ACCESS			 read-only
		STATUS					 current
		DESCRIPTION			 " -- "
		::=  { rrcCAndRCheckOfEnb  4 }


	rrcCpmCaseRelP5		 OBJECT-TYPE
		SYNTAX					 Counter32
		MAX-ACCESS			 read-only
		STATUS					 current
		DESCRIPTION			 " -- "
		::=  { rrcCAndRCheckOfEnb  5 }


	rrcCpmCaseRelP6		 OBJECT-TYPE
		SYNTAX					 Counter32
		MAX-ACCESS			 read-only
		STATUS					 current
		DESCRIPTION			 " -- "
		::=  { rrcCAndRCheckOfEnb  6 }


	rrcCpmCaseRelP7		 OBJECT-TYPE
		SYNTAX					 Counter32
		MAX-ACCESS			 read-only
		STATUS					 current
		DESCRIPTION			 " -- "
		::=  { rrcCAndRCheckOfEnb  7 }


	rrcCpmCaseRelP8		 OBJECT-TYPE
		SYNTAX					 Counter32
		MAX-ACCESS			 read-only
		STATUS					 current
		DESCRIPTION			 " -- "
		::=  { rrcCAndRCheckOfEnb  8 }


	rrcCpmCaseRelP9		 OBJECT-TYPE
		SYNTAX					 Counter32
		MAX-ACCESS			 read-only
		STATUS					 current
		DESCRIPTION			 " -- "
		::=  { rrcCAndRCheckOfEnb  9 }


	rrcCpmCaseRelP10		 OBJECT-TYPE
		SYNTAX					 Counter32
		MAX-ACCESS			 read-only
		STATUS					 current
		DESCRIPTION			 " -- "
		::=  { rrcCAndRCheckOfEnb  10 }


	rrcRbcCaseRelP0		 OBJECT-TYPE
		SYNTAX					 Counter32
		MAX-ACCESS			 read-only
		STATUS					 current
		DESCRIPTION			 " -- "
		::=  { rrcCAndRCheckOfEnb  11 }


	rrcRbcCaseRelP2		 OBJECT-TYPE
		SYNTAX					 Counter32
		MAX-ACCESS			 read-only
		STATUS					 current
		DESCRIPTION			 " -- "
		::=  { rrcCAndRCheckOfEnb  12 }


	rrcRbcCaseRelP3		 OBJECT-TYPE
		SYNTAX					 Counter32
		MAX-ACCESS			 read-only
		STATUS					 current
		DESCRIPTION			 " -- "
		::=  { rrcCAndRCheckOfEnb  13 }


	rrcRbcCaseRelP4		 OBJECT-TYPE
		SYNTAX					 Counter32
		MAX-ACCESS			 read-only
		STATUS					 current
		DESCRIPTION			 " -- "
		::=  { rrcCAndRCheckOfEnb  14 }


	rrcRbcCaseRelP5		 OBJECT-TYPE
		SYNTAX					 Counter32
		MAX-ACCESS			 read-only
		STATUS					 current
		DESCRIPTION			 " -- "
		::=  { rrcCAndRCheckOfEnb  15 }


	rrcRbcCaseRelP6		 OBJECT-TYPE
		SYNTAX					 Counter32
		MAX-ACCESS			 read-only
		STATUS					 current
		DESCRIPTION			 " -- "
		::=  { rrcCAndRCheckOfEnb  16 }


	rrcRbcCaseRelP7		 OBJECT-TYPE
		SYNTAX					 Counter32
		MAX-ACCESS			 read-only
		STATUS					 current
		DESCRIPTION			 " -- "
		::=  { rrcCAndRCheckOfEnb  17 }


	rrcRbcCaseRelP8		 OBJECT-TYPE
		SYNTAX					 Counter32
		MAX-ACCESS			 read-only
		STATUS					 current
		DESCRIPTION			 " -- "
		::=  { rrcCAndRCheckOfEnb  18 }


	rrcRbcCaseRelP9		 OBJECT-TYPE
		SYNTAX					 Counter32
		MAX-ACCESS			 read-only
		STATUS					 current
		DESCRIPTION			 " -- "
		::=  { rrcCAndRCheckOfEnb  19 }


	rrcRbcCaseRelP10		 OBJECT-TYPE
		SYNTAX					 Counter32
		MAX-ACCESS			 read-only
		STATUS					 current
		DESCRIPTION			 " -- "
		::=  { rrcCAndRCheckOfEnb  20 }


	rrcMchCaseRelP0		 OBJECT-TYPE
		SYNTAX					 Counter32
		MAX-ACCESS			 read-only
		STATUS					 current
		DESCRIPTION			 " -- "
		::=  { rrcCAndRCheckOfEnb  21 }


	rrcMchCaseRelP2		 OBJECT-TYPE
		SYNTAX					 Counter32
		MAX-ACCESS			 read-only
		STATUS					 current
		DESCRIPTION			 " -- "
		::=  { rrcCAndRCheckOfEnb  22 }


	rrcMchCaseRelP3		 OBJECT-TYPE
		SYNTAX					 Counter32
		MAX-ACCESS			 read-only
		STATUS					 current
		DESCRIPTION			 " -- "
		::=  { rrcCAndRCheckOfEnb  23 }


	rrcMchCaseRelP4		 OBJECT-TYPE
		SYNTAX					 Counter32
		MAX-ACCESS			 read-only
		STATUS					 current
		DESCRIPTION			 " -- "
		::=  { rrcCAndRCheckOfEnb  24 }


	rrcMchCaseRelP5		 OBJECT-TYPE
		SYNTAX					 Counter32
		MAX-ACCESS			 read-only
		STATUS					 current
		DESCRIPTION			 " -- "
		::=  { rrcCAndRCheckOfEnb  25 }


	rrcMchCaseRelP6		 OBJECT-TYPE
		SYNTAX					 Counter32
		MAX-ACCESS			 read-only
		STATUS					 current
		DESCRIPTION			 " -- "
		::=  { rrcCAndRCheckOfEnb  26 }


	rrcMchCaseRelP7		 OBJECT-TYPE
		SYNTAX					 Counter32
		MAX-ACCESS			 read-only
		STATUS					 current
		DESCRIPTION			 " -- "
		::=  { rrcCAndRCheckOfEnb  27 }


	rrcMchCaseRelP8		 OBJECT-TYPE
		SYNTAX					 Counter32
		MAX-ACCESS			 read-only
		STATUS					 current
		DESCRIPTION			 " -- "
		::=  { rrcCAndRCheckOfEnb  28 }


	rrcMchCaseRelP9		 OBJECT-TYPE
		SYNTAX					 Counter32
		MAX-ACCESS			 read-only
		STATUS					 current
		DESCRIPTION			 " -- "
		::=  { rrcCAndRCheckOfEnb  29 }


	rrcMchCaseRelP10		 OBJECT-TYPE
		SYNTAX					 Counter32
		MAX-ACCESS			 read-only
		STATUS					 current
		DESCRIPTION			 " -- "
		::=  { rrcCAndRCheckOfEnb  30 }


	rrcHcCaseRelP0		 OBJECT-TYPE
		SYNTAX					 Counter32
		MAX-ACCESS			 read-only
		STATUS					 current
		DESCRIPTION			 " -- "
		::=  { rrcCAndRCheckOfEnb  31 }


	rrcHcCaseRelP2		 OBJECT-TYPE
		SYNTAX					 Counter32
		MAX-ACCESS			 read-only
		STATUS					 current
		DESCRIPTION			 " -- "
		::=  { rrcCAndRCheckOfEnb  32 }


	rrcHcCaseRelP3		 OBJECT-TYPE
		SYNTAX					 Counter32
		MAX-ACCESS			 read-only
		STATUS					 current
		DESCRIPTION			 " -- "
		::=  { rrcCAndRCheckOfEnb  33 }


	rrcHcCaseRelP4		 OBJECT-TYPE
		SYNTAX					 Counter32
		MAX-ACCESS			 read-only
		STATUS					 current
		DESCRIPTION			 " -- "
		::=  { rrcCAndRCheckOfEnb  34 }


	rrcHcCaseRelP5		 OBJECT-TYPE
		SYNTAX					 Counter32
		MAX-ACCESS			 read-only
		STATUS					 current
		DESCRIPTION			 " -- "
		::=  { rrcCAndRCheckOfEnb  35 }


	rrcHcCaseRelP6		 OBJECT-TYPE
		SYNTAX					 Counter32
		MAX-ACCESS			 read-only
		STATUS					 current
		DESCRIPTION			 " -- "
		::=  { rrcCAndRCheckOfEnb  36 }


	rrcHcCaseRelP7		 OBJECT-TYPE
		SYNTAX					 Counter32
		MAX-ACCESS			 read-only
		STATUS					 current
		DESCRIPTION			 " -- "
		::=  { rrcCAndRCheckOfEnb  37 }


	rrcHcCaseRelP8		 OBJECT-TYPE
		SYNTAX					 Counter32
		MAX-ACCESS			 read-only
		STATUS					 current
		DESCRIPTION			 " -- "
		::=  { rrcCAndRCheckOfEnb  38 }


	rrcHcCaseRelP9		 OBJECT-TYPE
		SYNTAX					 Counter32
		MAX-ACCESS			 read-only
		STATUS					 current
		DESCRIPTION			 " -- "
		::=  { rrcCAndRCheckOfEnb  39 }


	rrcHcCaseRelP10		 OBJECT-TYPE
		SYNTAX					 Counter32
		MAX-ACCESS			 read-only
		STATUS					 current
		DESCRIPTION			 " -- "
		::=  { rrcCAndRCheckOfEnb  40 }


	rrcLpmCaseRelP0		 OBJECT-TYPE
		SYNTAX					 Counter32
		MAX-ACCESS			 read-only
		STATUS					 current
		DESCRIPTION			 " -- "
		::=  { rrcCAndRCheckOfEnb  41 }


	rrcLpmCaseRelP2		 OBJECT-TYPE
		SYNTAX					 Counter32
		MAX-ACCESS			 read-only
		STATUS					 current
		DESCRIPTION			 " -- "
		::=  { rrcCAndRCheckOfEnb  42 }


	rrcLpmCaseRelP3		 OBJECT-TYPE
		SYNTAX					 Counter32
		MAX-ACCESS			 read-only
		STATUS					 current
		DESCRIPTION			 " -- "
		::=  { rrcCAndRCheckOfEnb  43 }


	rrcLpmCaseRelP4		 OBJECT-TYPE
		SYNTAX					 Counter32
		MAX-ACCESS			 read-only
		STATUS					 current
		DESCRIPTION			 " -- "
		::=  { rrcCAndRCheckOfEnb  44 }


	rrcLpmCaseRelP5		 OBJECT-TYPE
		SYNTAX					 Counter32
		MAX-ACCESS			 read-only
		STATUS					 current
		DESCRIPTION			 " -- "
		::=  { rrcCAndRCheckOfEnb  45 }


	rrcLpmCaseRelP6		 OBJECT-TYPE
		SYNTAX					 Counter32
		MAX-ACCESS			 read-only
		STATUS					 current
		DESCRIPTION			 " -- "
		::=  { rrcCAndRCheckOfEnb  46 }


	rrcLpmCaseRelP7		 OBJECT-TYPE
		SYNTAX					 Counter32
		MAX-ACCESS			 read-only
		STATUS					 current
		DESCRIPTION			 " -- "
		::=  { rrcCAndRCheckOfEnb  47 }


	rrcLpmCaseRelP8		 OBJECT-TYPE
		SYNTAX					 Counter32
		MAX-ACCESS			 read-only
		STATUS					 current
		DESCRIPTION			 " -- "
		::=  { rrcCAndRCheckOfEnb  48 }


	rrcLpmCaseRelP9		 OBJECT-TYPE
		SYNTAX					 Counter32
		MAX-ACCESS			 read-only
		STATUS					 current
		DESCRIPTION			 " -- "
		::=  { rrcCAndRCheckOfEnb  49 }


	rrcLpmCaseRelP10		 OBJECT-TYPE
		SYNTAX					 Counter32
		MAX-ACCESS			 read-only
		STATUS					 current
		DESCRIPTION			 " -- "
		::=  { rrcCAndRCheckOfEnb  50 }


	rrcCpmMeasCaseRelP0		 OBJECT-TYPE
		SYNTAX					 Counter32
		MAX-ACCESS			 read-only
		STATUS					 current
		DESCRIPTION			 " -- "
		::=  { rrcCAndRCheckOfEnb  51 }


	rrcCpmMeasCaseRelP2		 OBJECT-TYPE
		SYNTAX					 Counter32
		MAX-ACCESS			 read-only
		STATUS					 current
		DESCRIPTION			 " -- "
		::=  { rrcCAndRCheckOfEnb  52 }


	rrcCpmMeasCaseRelP3		 OBJECT-TYPE
		SYNTAX					 Counter32
		MAX-ACCESS			 read-only
		STATUS					 current
		DESCRIPTION			 " -- "
		::=  { rrcCAndRCheckOfEnb  53 }


	rrcCpmMeasCaseRelP4		 OBJECT-TYPE
		SYNTAX					 Counter32
		MAX-ACCESS			 read-only
		STATUS					 current
		DESCRIPTION			 " -- "
		::=  { rrcCAndRCheckOfEnb  54 }


	rrcCpmMeasCaseRelP5		 OBJECT-TYPE
		SYNTAX					 Counter32
		MAX-ACCESS			 read-only
		STATUS					 current
		DESCRIPTION			 " -- "
		::=  { rrcCAndRCheckOfEnb  55 }


	rrcCpmMeasCaseRelP6		 OBJECT-TYPE
		SYNTAX					 Counter32
		MAX-ACCESS			 read-only
		STATUS					 current
		DESCRIPTION			 " -- "
		::=  { rrcCAndRCheckOfEnb  56 }


	rrcCpmMeasCaseRelP7		 OBJECT-TYPE
		SYNTAX					 Counter32
		MAX-ACCESS			 read-only
		STATUS					 current
		DESCRIPTION			 " -- "
		::=  { rrcCAndRCheckOfEnb  57 }


	rrcCpmMeasCaseRelP8		 OBJECT-TYPE
		SYNTAX					 Counter32
		MAX-ACCESS			 read-only
		STATUS					 current
		DESCRIPTION			 " -- "
		::=  { rrcCAndRCheckOfEnb  58 }


	rrcCpmMeasCaseRelP9		 OBJECT-TYPE
		SYNTAX					 Counter32
		MAX-ACCESS			 read-only
		STATUS					 current
		DESCRIPTION			 " -- "
		::=  { rrcCAndRCheckOfEnb  59 }


	rrcCpmMeasCaseRelP10		 OBJECT-TYPE
		SYNTAX					 Counter32
		MAX-ACCESS			 read-only
		STATUS					 current
		DESCRIPTION			 " -- "
		::=  { rrcCAndRCheckOfEnb  60 }


	aprelatedOriginCounter		 OBJECT IDENTIFIER
		::=  { pmOriginCounterGrpInfo  2 }


	initERABEstabProcTable		 OBJECT-TYPE
		SYNTAX					 SEQUENCE  OF	 InitERABEstabProcEntry
		MAX-ACCESS			 not-accessible
		STATUS					 current
		DESCRIPTION			 " -- "
		::=  { aprelatedOriginCounter  1 }


	initERABEstabProcEntry		 OBJECT-TYPE
		SYNTAX					 InitERABEstabProcEntry
		MAX-ACCESS			 not-accessible
		STATUS					 current
		DESCRIPTION			 " -- "
		INDEX						{ initERABEstabProcLcId }
		::=  { initERABEstabProcTable  1 }


	InitERABEstabProcEntry		 ::=  SEQUENCE {
		initERABEstabProcLcId					Integer32,
		initERABEstabProcRowStatus					RowStatus,
		erabEstabInitFailNbrEnbUeS1apIdError					Counter32,
		erabEstabInitFailNbrUeS1apIdPairError					Counter32,
		erabEstabInitFailNbrInvalidQosCombination					Counter32,
		erabEstabInitFailNbrRadioInterfaceFailure					Counter32,
		erabEstabInitFailNbrMultipleErabId					Counter32,
		erabEstabInitFailNbrAlgoNotSupported					Counter32,
		erabEstabInitFailNbrTransResNotAvailable					Counter32,
		erabEstabInitFailNbrTransferSyntaxError					Counter32,
		erabEstabInitFailNbrAbstractSyntaxError					Counter32,
		erabEstabInitFailNbrControlProcessingOverload					Counter32,
		erabEstabInitFailNbrUnspecifiedFailure					Counter32,
		erabEstabInitAttNbrQci1					Counter32,
		erabEstabInitSuccNbrQci1					Counter32,
		erabEstabInitAttNbrQci2					Counter32,
		erabEstabInitSuccNbrQci2					Counter32,
		erabEstabInitAttNbrQci3					Counter32,
		erabEstabInitSuccNbrQci3					Counter32,
		erabEstabInitAttNbrQci4					Counter32,
		erabEstabInitSuccNbrQci4					Counter32,
		erabEstabInitAttNbrQci5					Counter32,
		erabEstabInitSuccNbrQci5					Counter32,
		erabEstabInitAttNbrQci6					Counter32,
		erabEstabInitSuccNbrQci6					Counter32,
		erabEstabInitAttNbrQci7					Counter32,
		erabEstabInitSuccNbrQci7					Counter32,
		erabEstabInitAttNbrQci8					Counter32,
		erabEstabInitSuccNbrQci8					Counter32,
		erabEstabInitAttNbrQci9					Counter32,
		erabEstabInitSuccNbrQci9					Counter32,
		erabEstabInitFailNbrRadioResNotAvailable					Counter32,
		erabEstabInitFailNbrQci1RadioInterfaceFailure					Counter32,
		erabEstabInitFailNbrQci1RadioResNotAvailable					Counter32,
		erabEstabInitFailNbrQci1Mme					Counter32,
		erabEstabInitFailNbrQci1InterWithOtherProc					Counter32,
		erabEstabInitFailNbrQci1Transport					Counter32,
		erabEstabInitFailNbrQci1AlgoNotSupported					Counter32,
		erabEstabInitFailNbrQci1Other					Counter32,
		erabEstabInitFailNbrQci2RadioInterfaceFailure					Counter32,
		erabEstabInitFailNbrQci2RadioResNotAvailable					Counter32,
		erabEstabInitFailNbrQci2Mme					Counter32,
		erabEstabInitFailNbrQci2InterWithOtherProc					Counter32,
		erabEstabInitFailNbrQci2Transport					Counter32,
		erabEstabInitFailNbrQci2AlgoNotSupported					Counter32,
		erabEstabInitFailNbrQci2Other					Counter32
		}


	initERABEstabProcLcId		 OBJECT-TYPE
		SYNTAX					 Integer32( 0 .. 23 )
		MAX-ACCESS			 not-accessible
		STATUS					 current
		DESCRIPTION			 " -- "
		::=  { initERABEstabProcEntry  1 }


	initERABEstabProcRowStatus		 OBJECT-TYPE
		SYNTAX					 RowStatus
		MAX-ACCESS			 read-only
		STATUS					 current
		DESCRIPTION			 " -- "
		::=  { initERABEstabProcEntry  2 }


	erabEstabInitFailNbrEnbUeS1apIdError		 OBJECT-TYPE
		SYNTAX					 Counter32
		MAX-ACCESS			 read-only
		STATUS					 current
		DESCRIPTION			 " -- "
		::=  { initERABEstabProcEntry  3 }


	erabEstabInitFailNbrUeS1apIdPairError		 OBJECT-TYPE
		SYNTAX					 Counter32
		MAX-ACCESS			 read-only
		STATUS					 current
		DESCRIPTION			 " -- "
		::=  { initERABEstabProcEntry  4 }


	erabEstabInitFailNbrInvalidQosCombination		 OBJECT-TYPE
		SYNTAX					 Counter32
		MAX-ACCESS			 read-only
		STATUS					 current
		DESCRIPTION			 " -- "
		::=  { initERABEstabProcEntry  5 }


	erabEstabInitFailNbrRadioInterfaceFailure		 OBJECT-TYPE
		SYNTAX					 Counter32
		MAX-ACCESS			 read-only
		STATUS					 current
		DESCRIPTION			 " -- "
		::=  { initERABEstabProcEntry  6 }


	erabEstabInitFailNbrMultipleErabId		 OBJECT-TYPE
		SYNTAX					 Counter32
		MAX-ACCESS			 read-only
		STATUS					 current
		DESCRIPTION			 " -- "
		::=  { initERABEstabProcEntry  7 }


	erabEstabInitFailNbrAlgoNotSupported		 OBJECT-TYPE
		SYNTAX					 Counter32
		MAX-ACCESS			 read-only
		STATUS					 current
		DESCRIPTION			 " -- "
		::=  { initERABEstabProcEntry  8 }


	erabEstabInitFailNbrTransResNotAvailable		 OBJECT-TYPE
		SYNTAX					 Counter32
		MAX-ACCESS			 read-only
		STATUS					 current
		DESCRIPTION			 " -- "
		::=  { initERABEstabProcEntry  9 }


	erabEstabInitFailNbrTransferSyntaxError		 OBJECT-TYPE
		SYNTAX					 Counter32
		MAX-ACCESS			 read-only
		STATUS					 current
		DESCRIPTION			 " -- "
		::=  { initERABEstabProcEntry  10 }


	erabEstabInitFailNbrAbstractSyntaxError		 OBJECT-TYPE
		SYNTAX					 Counter32
		MAX-ACCESS			 read-only
		STATUS					 current
		DESCRIPTION			 " -- "
		::=  { initERABEstabProcEntry  11 }


	erabEstabInitFailNbrControlProcessingOverload		 OBJECT-TYPE
		SYNTAX					 Counter32
		MAX-ACCESS			 read-only
		STATUS					 current
		DESCRIPTION			 " -- "
		::=  { initERABEstabProcEntry  12 }


	erabEstabInitFailNbrUnspecifiedFailure		 OBJECT-TYPE
		SYNTAX					 Counter32
		MAX-ACCESS			 read-only
		STATUS					 current
		DESCRIPTION			 " -- "
		::=  { initERABEstabProcEntry  13 }


	erabEstabInitAttNbrQci1		 OBJECT-TYPE
		SYNTAX					 Counter32
		MAX-ACCESS			 read-only
		STATUS					 current
		DESCRIPTION			 " -- "
		::=  { initERABEstabProcEntry  14 }


	erabEstabInitSuccNbrQci1		 OBJECT-TYPE
		SYNTAX					 Counter32
		MAX-ACCESS			 read-only
		STATUS					 current
		DESCRIPTION			 " -- "
		::=  { initERABEstabProcEntry  15 }


	erabEstabInitAttNbrQci2		 OBJECT-TYPE
		SYNTAX					 Counter32
		MAX-ACCESS			 read-only
		STATUS					 current
		DESCRIPTION			 " -- "
		::=  { initERABEstabProcEntry  16 }


	erabEstabInitSuccNbrQci2		 OBJECT-TYPE
		SYNTAX					 Counter32
		MAX-ACCESS			 read-only
		STATUS					 current
		DESCRIPTION			 " -- "
		::=  { initERABEstabProcEntry  17 }


	erabEstabInitAttNbrQci3		 OBJECT-TYPE
		SYNTAX					 Counter32
		MAX-ACCESS			 read-only
		STATUS					 current
		DESCRIPTION			 " -- "
		::=  { initERABEstabProcEntry  18 }


	erabEstabInitSuccNbrQci3		 OBJECT-TYPE
		SYNTAX					 Counter32
		MAX-ACCESS			 read-only
		STATUS					 current
		DESCRIPTION			 " -- "
		::=  { initERABEstabProcEntry  19 }


	erabEstabInitAttNbrQci4		 OBJECT-TYPE
		SYNTAX					 Counter32
		MAX-ACCESS			 read-only
		STATUS					 current
		DESCRIPTION			 " -- "
		::=  { initERABEstabProcEntry  20 }


	erabEstabInitSuccNbrQci4		 OBJECT-TYPE
		SYNTAX					 Counter32
		MAX-ACCESS			 read-only
		STATUS					 current
		DESCRIPTION			 " -- "
		::=  { initERABEstabProcEntry  21 }


	erabEstabInitAttNbrQci5		 OBJECT-TYPE
		SYNTAX					 Counter32
		MAX-ACCESS			 read-only
		STATUS					 current
		DESCRIPTION			 " -- "
		::=  { initERABEstabProcEntry  22 }


	erabEstabInitSuccNbrQci5		 OBJECT-TYPE
		SYNTAX					 Counter32
		MAX-ACCESS			 read-only
		STATUS					 current
		DESCRIPTION			 " -- "
		::=  { initERABEstabProcEntry  23 }


	erabEstabInitAttNbrQci6		 OBJECT-TYPE
		SYNTAX					 Counter32
		MAX-ACCESS			 read-only
		STATUS					 current
		DESCRIPTION			 " -- "
		::=  { initERABEstabProcEntry  24 }


	erabEstabInitSuccNbrQci6		 OBJECT-TYPE
		SYNTAX					 Counter32
		MAX-ACCESS			 read-only
		STATUS					 current
		DESCRIPTION			 " -- "
		::=  { initERABEstabProcEntry  25 }


	erabEstabInitAttNbrQci7		 OBJECT-TYPE
		SYNTAX					 Counter32
		MAX-ACCESS			 read-only
		STATUS					 current
		DESCRIPTION			 " -- "
		::=  { initERABEstabProcEntry  26 }


	erabEstabInitSuccNbrQci7		 OBJECT-TYPE
		SYNTAX					 Counter32
		MAX-ACCESS			 read-only
		STATUS					 current
		DESCRIPTION			 " -- "
		::=  { initERABEstabProcEntry  27 }


	erabEstabInitAttNbrQci8		 OBJECT-TYPE
		SYNTAX					 Counter32
		MAX-ACCESS			 read-only
		STATUS					 current
		DESCRIPTION			 " -- "
		::=  { initERABEstabProcEntry  28 }


	erabEstabInitSuccNbrQci8		 OBJECT-TYPE
		SYNTAX					 Counter32
		MAX-ACCESS			 read-only
		STATUS					 current
		DESCRIPTION			 " -- "
		::=  { initERABEstabProcEntry  29 }


	erabEstabInitAttNbrQci9		 OBJECT-TYPE
		SYNTAX					 Counter32
		MAX-ACCESS			 read-only
		STATUS					 current
		DESCRIPTION			 " -- "
		::=  { initERABEstabProcEntry  30 }


	erabEstabInitSuccNbrQci9		 OBJECT-TYPE
		SYNTAX					 Counter32
		MAX-ACCESS			 read-only
		STATUS					 current
		DESCRIPTION			 " -- "
		::=  { initERABEstabProcEntry  31 }


	erabEstabInitFailNbrRadioResNotAvailable		 OBJECT-TYPE
		SYNTAX					 Counter32
		MAX-ACCESS			 read-only
		STATUS					 current
		DESCRIPTION			 " -- "
		::=  { initERABEstabProcEntry  32 }


	erabEstabInitFailNbrQci1RadioInterfaceFailure		 OBJECT-TYPE
		SYNTAX					 Counter32
		MAX-ACCESS			 read-only
		STATUS					 current
		DESCRIPTION			 " -- "
		::=  { initERABEstabProcEntry  33 }


	erabEstabInitFailNbrQci1RadioResNotAvailable		 OBJECT-TYPE
		SYNTAX					 Counter32
		MAX-ACCESS			 read-only
		STATUS					 current
		DESCRIPTION			 " -- "
		::=  { initERABEstabProcEntry  34 }


	erabEstabInitFailNbrQci1Mme		 OBJECT-TYPE
		SYNTAX					 Counter32
		MAX-ACCESS			 read-only
		STATUS					 current
		DESCRIPTION			 " -- "
		::=  { initERABEstabProcEntry  35 }


	erabEstabInitFailNbrQci1InterWithOtherProc		 OBJECT-TYPE
		SYNTAX					 Counter32
		MAX-ACCESS			 read-only
		STATUS					 current
		DESCRIPTION			 " -- "
		::=  { initERABEstabProcEntry  36 }


	erabEstabInitFailNbrQci1Transport		 OBJECT-TYPE
		SYNTAX					 Counter32
		MAX-ACCESS			 read-only
		STATUS					 current
		DESCRIPTION			 " -- "
		::=  { initERABEstabProcEntry  37 }


	erabEstabInitFailNbrQci1AlgoNotSupported		 OBJECT-TYPE
		SYNTAX					 Counter32
		MAX-ACCESS			 read-only
		STATUS					 current
		DESCRIPTION			 " -- "
		::=  { initERABEstabProcEntry  38 }


	erabEstabInitFailNbrQci1Other		 OBJECT-TYPE
		SYNTAX					 Counter32
		MAX-ACCESS			 read-only
		STATUS					 current
		DESCRIPTION			 " -- "
		::=  { initERABEstabProcEntry  39 }


	erabEstabInitFailNbrQci2RadioInterfaceFailure		 OBJECT-TYPE
		SYNTAX					 Counter32
		MAX-ACCESS			 read-only
		STATUS					 current
		DESCRIPTION			 " -- "
		::=  { initERABEstabProcEntry  40 }


	erabEstabInitFailNbrQci2RadioResNotAvailable		 OBJECT-TYPE
		SYNTAX					 Counter32
		MAX-ACCESS			 read-only
		STATUS					 current
		DESCRIPTION			 " -- "
		::=  { initERABEstabProcEntry  41 }


	erabEstabInitFailNbrQci2Mme		 OBJECT-TYPE
		SYNTAX					 Counter32
		MAX-ACCESS			 read-only
		STATUS					 current
		DESCRIPTION			 " -- "
		::=  { initERABEstabProcEntry  42 }


	erabEstabInitFailNbrQci2InterWithOtherProc		 OBJECT-TYPE
		SYNTAX					 Counter32
		MAX-ACCESS			 read-only
		STATUS					 current
		DESCRIPTION			 " -- "
		::=  { initERABEstabProcEntry  43 }


	erabEstabInitFailNbrQci2Transport		 OBJECT-TYPE
		SYNTAX					 Counter32
		MAX-ACCESS			 read-only
		STATUS					 current
		DESCRIPTION			 " -- "
		::=  { initERABEstabProcEntry  44 }


	erabEstabInitFailNbrQci2AlgoNotSupported		 OBJECT-TYPE
		SYNTAX					 Counter32
		MAX-ACCESS			 read-only
		STATUS					 current
		DESCRIPTION			 " -- "
		::=  { initERABEstabProcEntry  45 }


	erabEstabInitFailNbrQci2Other		 OBJECT-TYPE
		SYNTAX					 Counter32
		MAX-ACCESS			 read-only
		STATUS					 current
		DESCRIPTION			 " -- "
		::=  { initERABEstabProcEntry  46 }


	addERABEstabProcTable		 OBJECT-TYPE
		SYNTAX					 SEQUENCE  OF	 AddERABEstabProcEntry
		MAX-ACCESS			 not-accessible
		STATUS					 current
		DESCRIPTION			 " -- "
		::=  { aprelatedOriginCounter  2 }


	addERABEstabProcEntry		 OBJECT-TYPE
		SYNTAX					 AddERABEstabProcEntry
		MAX-ACCESS			 not-accessible
		STATUS					 current
		DESCRIPTION			 " -- "
		INDEX						{ addERABEstabProcLcId }
		::=  { addERABEstabProcTable  1 }


	AddERABEstabProcEntry		 ::=  SEQUENCE {
		addERABEstabProcLcId					Integer32,
		addERABEstabProcRowStatus					RowStatus,
		erabEstabAddFailNbrUeS1apIdPairError					Counter32,
		erabEstabAddFailNbrInteractionWithOtherProc					Counter32,
		erabEstabAddFailNbrInvalidQosCombination					Counter32,
		erabEstabAddFailNbrRadioInterfaceFailure					Counter32,
		erabEstabAddFailNbrMultipleErabId					Counter32,
		erabEstabAddFailNbrS1IntraSystemHoTrig					Counter32,
		erabEstabAddFailNbrS1InterSystemHoTrig					Counter32,
		erabEstabAddFailNbrX2HandoverTriggered					Counter32,
		erabEstabAddFailNbrTransportResNotAvailable					Counter32,
		erabEstabAddFailNbrTransferSyntaxError					Counter32,
		erabEstabAddFailNbrAbstractSyntaxError					Counter32,
		erabEstabAddFailNbrControlProcessingOverload					Counter32,
		erabEstabAddFailNbrUnspecifiedFailure					Counter32,
		erabEstabAddAttNbrQci1					Counter32,
		erabEstabAddSuccNbrQci1					Counter32,
		erabEstabAddAttNbrQci2					Counter32,
		erabEstabAddSuccNbrQci2					Counter32,
		erabEstabAddAttNbrQci3					Counter32,
		erabEstabAddSuccNbrQci3					Counter32,
		erabEstabAddAttNbrQci4					Counter32,
		erabEstabAddSuccNbrQci4					Counter32,
		erabEstabAddAttNbrQci5					Counter32,
		erabEstabAddSuccNbrQci5					Counter32,
		erabEstabAddAttNbrQci6					Counter32,
		erabEstabAddSuccNbrQci6					Counter32,
		erabEstabAddAttNbrQci7					Counter32,
		erabEstabAddSuccNbrQci7					Counter32,
		erabEstabAddAttNbrQci8					Counter32,
		erabEstabAddSuccNbrQci8					Counter32,
		erabEstabAddAttNbrQci9					Counter32,
		erabEstabAddSuccNbrQci9					Counter32,
		erabEstabAddFailNbrRadioResNotAvailable					Counter32,
		erabEstabAddFailNbrWeakCoverageQci1					Counter32,
		erabEstabAddFailNbrQci1RadioInterfaceFailure					Counter32,
		erabEstabAddFailNbrQci1RadioResNotAvailable					Counter32,
		erabEstabAddFailNbrQci1Mme					Counter32,
		erabEstabAddFailNbrQci1InterWithOtherProc					Counter32,
		erabEstabAddFailNbrQci1Transport					Counter32,
		erabEstabAddFailNbrQci1Other					Counter32,
		erabEstabAddFailNbrQci2RadioInterfaceFailure					Counter32,
		erabEstabAddFailNbrQci2RadioResNotAvailable					Counter32,
		erabEstabAddFailNbrQci2Mme					Counter32,
		erabEstabAddFailNbrQci2InterWithOtherProc					Counter32,
		erabEstabAddFailNbrQci2Transport					Counter32,
		erabEstabAddFailNbrQci2Other					Counter32
		}


	addERABEstabProcLcId		 OBJECT-TYPE
		SYNTAX					 Integer32( 0 .. 23 )
		MAX-ACCESS			 not-accessible
		STATUS					 current
		DESCRIPTION			 " -- "
		::=  { addERABEstabProcEntry  1 }


	addERABEstabProcRowStatus		 OBJECT-TYPE
		SYNTAX					 RowStatus
		MAX-ACCESS			 read-only
		STATUS					 current
		DESCRIPTION			 " -- "
		::=  { addERABEstabProcEntry  2 }


	erabEstabAddFailNbrUeS1apIdPairError		 OBJECT-TYPE
		SYNTAX					 Counter32
		MAX-ACCESS			 read-only
		STATUS					 current
		DESCRIPTION			 " -- "
		::=  { addERABEstabProcEntry  3 }


	erabEstabAddFailNbrInteractionWithOtherProc		 OBJECT-TYPE
		SYNTAX					 Counter32
		MAX-ACCESS			 read-only
		STATUS					 current
		DESCRIPTION			 " -- "
		::=  { addERABEstabProcEntry  4 }


	erabEstabAddFailNbrInvalidQosCombination		 OBJECT-TYPE
		SYNTAX					 Counter32
		MAX-ACCESS			 read-only
		STATUS					 current
		DESCRIPTION			 " -- "
		::=  { addERABEstabProcEntry  5 }


	erabEstabAddFailNbrRadioInterfaceFailure		 OBJECT-TYPE
		SYNTAX					 Counter32
		MAX-ACCESS			 read-only
		STATUS					 current
		DESCRIPTION			 " -- "
		::=  { addERABEstabProcEntry  6 }


	erabEstabAddFailNbrMultipleErabId		 OBJECT-TYPE
		SYNTAX					 Counter32
		MAX-ACCESS			 read-only
		STATUS					 current
		DESCRIPTION			 " -- "
		::=  { addERABEstabProcEntry  7 }


	erabEstabAddFailNbrS1IntraSystemHoTrig		 OBJECT-TYPE
		SYNTAX					 Counter32
		MAX-ACCESS			 read-only
		STATUS					 current
		DESCRIPTION			 " -- "
		::=  { addERABEstabProcEntry  8 }


	erabEstabAddFailNbrS1InterSystemHoTrig		 OBJECT-TYPE
		SYNTAX					 Counter32
		MAX-ACCESS			 read-only
		STATUS					 current
		DESCRIPTION			 " -- "
		::=  { addERABEstabProcEntry  9 }


	erabEstabAddFailNbrX2HandoverTriggered		 OBJECT-TYPE
		SYNTAX					 Counter32
		MAX-ACCESS			 read-only
		STATUS					 current
		DESCRIPTION			 " -- "
		::=  { addERABEstabProcEntry  10 }


	erabEstabAddFailNbrTransportResNotAvailable		 OBJECT-TYPE
		SYNTAX					 Counter32
		MAX-ACCESS			 read-only
		STATUS					 current
		DESCRIPTION			 " -- "
		::=  { addERABEstabProcEntry  11 }


	erabEstabAddFailNbrTransferSyntaxError		 OBJECT-TYPE
		SYNTAX					 Counter32
		MAX-ACCESS			 read-only
		STATUS					 current
		DESCRIPTION			 " -- "
		::=  { addERABEstabProcEntry  12 }


	erabEstabAddFailNbrAbstractSyntaxError		 OBJECT-TYPE
		SYNTAX					 Counter32
		MAX-ACCESS			 read-only
		STATUS					 current
		DESCRIPTION			 " -- "
		::=  { addERABEstabProcEntry  13 }


	erabEstabAddFailNbrControlProcessingOverload		 OBJECT-TYPE
		SYNTAX					 Counter32
		MAX-ACCESS			 read-only
		STATUS					 current
		DESCRIPTION			 " -- "
		::=  { addERABEstabProcEntry  14 }


	erabEstabAddFailNbrUnspecifiedFailure		 OBJECT-TYPE
		SYNTAX					 Counter32
		MAX-ACCESS			 read-only
		STATUS					 current
		DESCRIPTION			 " -- "
		::=  { addERABEstabProcEntry  15 }


	erabEstabAddAttNbrQci1		 OBJECT-TYPE
		SYNTAX					 Counter32
		MAX-ACCESS			 read-only
		STATUS					 current
		DESCRIPTION			 " -- "
		::=  { addERABEstabProcEntry  16 }


	erabEstabAddSuccNbrQci1		 OBJECT-TYPE
		SYNTAX					 Counter32
		MAX-ACCESS			 read-only
		STATUS					 current
		DESCRIPTION			 " -- "
		::=  { addERABEstabProcEntry  17 }


	erabEstabAddAttNbrQci2		 OBJECT-TYPE
		SYNTAX					 Counter32
		MAX-ACCESS			 read-only
		STATUS					 current
		DESCRIPTION			 " -- "
		::=  { addERABEstabProcEntry  18 }


	erabEstabAddSuccNbrQci2		 OBJECT-TYPE
		SYNTAX					 Counter32
		MAX-ACCESS			 read-only
		STATUS					 current
		DESCRIPTION			 " -- "
		::=  { addERABEstabProcEntry  19 }


	erabEstabAddAttNbrQci3		 OBJECT-TYPE
		SYNTAX					 Counter32
		MAX-ACCESS			 read-only
		STATUS					 current
		DESCRIPTION			 " -- "
		::=  { addERABEstabProcEntry  20 }


	erabEstabAddSuccNbrQci3		 OBJECT-TYPE
		SYNTAX					 Counter32
		MAX-ACCESS			 read-only
		STATUS					 current
		DESCRIPTION			 " -- "
		::=  { addERABEstabProcEntry  21 }


	erabEstabAddAttNbrQci4		 OBJECT-TYPE
		SYNTAX					 Counter32
		MAX-ACCESS			 read-only
		STATUS					 current
		DESCRIPTION			 " -- "
		::=  { addERABEstabProcEntry  22 }


	erabEstabAddSuccNbrQci4		 OBJECT-TYPE
		SYNTAX					 Counter32
		MAX-ACCESS			 read-only
		STATUS					 current
		DESCRIPTION			 " -- "
		::=  { addERABEstabProcEntry  23 }


	erabEstabAddAttNbrQci5		 OBJECT-TYPE
		SYNTAX					 Counter32
		MAX-ACCESS			 read-only
		STATUS					 current
		DESCRIPTION			 " -- "
		::=  { addERABEstabProcEntry  24 }


	erabEstabAddSuccNbrQci5		 OBJECT-TYPE
		SYNTAX					 Counter32
		MAX-ACCESS			 read-only
		STATUS					 current
		DESCRIPTION			 " -- "
		::=  { addERABEstabProcEntry  25 }


	erabEstabAddAttNbrQci6		 OBJECT-TYPE
		SYNTAX					 Counter32
		MAX-ACCESS			 read-only
		STATUS					 current
		DESCRIPTION			 " -- "
		::=  { addERABEstabProcEntry  26 }


	erabEstabAddSuccNbrQci6		 OBJECT-TYPE
		SYNTAX					 Counter32
		MAX-ACCESS			 read-only
		STATUS					 current
		DESCRIPTION			 " -- "
		::=  { addERABEstabProcEntry  27 }


	erabEstabAddAttNbrQci7		 OBJECT-TYPE
		SYNTAX					 Counter32
		MAX-ACCESS			 read-only
		STATUS					 current
		DESCRIPTION			 " -- "
		::=  { addERABEstabProcEntry  28 }


	erabEstabAddSuccNbrQci7		 OBJECT-TYPE
		SYNTAX					 Counter32
		MAX-ACCESS			 read-only
		STATUS					 current
		DESCRIPTION			 " -- "
		::=  { addERABEstabProcEntry  29 }


	erabEstabAddAttNbrQci8		 OBJECT-TYPE
		SYNTAX					 Counter32
		MAX-ACCESS			 read-only
		STATUS					 current
		DESCRIPTION			 " -- "
		::=  { addERABEstabProcEntry  30 }


	erabEstabAddSuccNbrQci8		 OBJECT-TYPE
		SYNTAX					 Counter32
		MAX-ACCESS			 read-only
		STATUS					 current
		DESCRIPTION			 " -- "
		::=  { addERABEstabProcEntry  31 }


	erabEstabAddAttNbrQci9		 OBJECT-TYPE
		SYNTAX					 Counter32
		MAX-ACCESS			 read-only
		STATUS					 current
		DESCRIPTION			 " -- "
		::=  { addERABEstabProcEntry  32 }


	erabEstabAddSuccNbrQci9		 OBJECT-TYPE
		SYNTAX					 Counter32
		MAX-ACCESS			 read-only
		STATUS					 current
		DESCRIPTION			 " -- "
		::=  { addERABEstabProcEntry  33 }


	erabEstabAddFailNbrRadioResNotAvailable		 OBJECT-TYPE
		SYNTAX					 Counter32
		MAX-ACCESS			 read-only
		STATUS					 current
		DESCRIPTION			 " -- "
		::=  { addERABEstabProcEntry  34 }


	erabEstabAddFailNbrWeakCoverageQci1		 OBJECT-TYPE
		SYNTAX					 Counter32
		MAX-ACCESS			 read-only
		STATUS					 current
		DESCRIPTION			 " -- "
		::=  { addERABEstabProcEntry  35 }


	erabEstabAddFailNbrQci1RadioInterfaceFailure		 OBJECT-TYPE
		SYNTAX					 Counter32
		MAX-ACCESS			 read-only
		STATUS					 current
		DESCRIPTION			 " -- "
		::=  { addERABEstabProcEntry  36 }


	erabEstabAddFailNbrQci1RadioResNotAvailable		 OBJECT-TYPE
		SYNTAX					 Counter32
		MAX-ACCESS			 read-only
		STATUS					 current
		DESCRIPTION			 " -- "
		::=  { addERABEstabProcEntry  37 }


	erabEstabAddFailNbrQci1Mme		 OBJECT-TYPE
		SYNTAX					 Counter32
		MAX-ACCESS			 read-only
		STATUS					 current
		DESCRIPTION			 " -- "
		::=  { addERABEstabProcEntry  38 }


	erabEstabAddFailNbrQci1InterWithOtherProc		 OBJECT-TYPE
		SYNTAX					 Counter32
		MAX-ACCESS			 read-only
		STATUS					 current
		DESCRIPTION			 " -- "
		::=  { addERABEstabProcEntry  39 }


	erabEstabAddFailNbrQci1Transport		 OBJECT-TYPE
		SYNTAX					 Counter32
		MAX-ACCESS			 read-only
		STATUS					 current
		DESCRIPTION			 " -- "
		::=  { addERABEstabProcEntry  40 }


	erabEstabAddFailNbrQci1Other		 OBJECT-TYPE
		SYNTAX					 Counter32
		MAX-ACCESS			 read-only
		STATUS					 current
		DESCRIPTION			 " -- "
		::=  { addERABEstabProcEntry  41 }


	erabEstabAddFailNbrQci2RadioInterfaceFailure		 OBJECT-TYPE
		SYNTAX					 Counter32
		MAX-ACCESS			 read-only
		STATUS					 current
		DESCRIPTION			 " -- "
		::=  { addERABEstabProcEntry  42 }


	erabEstabAddFailNbrQci2RadioResNotAvailable		 OBJECT-TYPE
		SYNTAX					 Counter32
		MAX-ACCESS			 read-only
		STATUS					 current
		DESCRIPTION			 " -- "
		::=  { addERABEstabProcEntry  43 }


	erabEstabAddFailNbrQci2Mme		 OBJECT-TYPE
		SYNTAX					 Counter32
		MAX-ACCESS			 read-only
		STATUS					 current
		DESCRIPTION			 " -- "
		::=  { addERABEstabProcEntry  44 }


	erabEstabAddFailNbrQci2InterWithOtherProc		 OBJECT-TYPE
		SYNTAX					 Counter32
		MAX-ACCESS			 read-only
		STATUS					 current
		DESCRIPTION			 " -- "
		::=  { addERABEstabProcEntry  45 }


	erabEstabAddFailNbrQci2Transport		 OBJECT-TYPE
		SYNTAX					 Counter32
		MAX-ACCESS			 read-only
		STATUS					 current
		DESCRIPTION			 " -- "
		::=  { addERABEstabProcEntry  46 }


	erabEstabAddFailNbrQci2Other		 OBJECT-TYPE
		SYNTAX					 Counter32
		MAX-ACCESS			 read-only
		STATUS					 current
		DESCRIPTION			 " -- "
		::=  { addERABEstabProcEntry  47 }


	erabRelProcTable		 OBJECT-TYPE
		SYNTAX					 SEQUENCE  OF	 ErabRelProcEntry
		MAX-ACCESS			 not-accessible
		STATUS					 current
		DESCRIPTION			 " -- "
		::=  { aprelatedOriginCounter  3 }


	erabRelProcEntry		 OBJECT-TYPE
		SYNTAX					 ErabRelProcEntry
		MAX-ACCESS			 not-accessible
		STATUS					 current
		DESCRIPTION			 " -- "
		INDEX						{ erabRelProcLcId }
		::=  { erabRelProcTable  1 }


	ErabRelProcEntry		 ::=  SEQUENCE {
		erabRelProcLcId					Integer32,
		erabRelProcRowStatus					RowStatus,
		erabRelEnbNbrQci1					Counter32,
		erabRelEnbNbrQci2					Counter32,
		erabRelEnbNbrQci3					Counter32,
		erabRelEnbNbrQci4					Counter32,
		erabRelEnbNbrQci5					Counter32,
		erabRelEnbNbrQci6					Counter32,
		erabRelEnbNbrQci7					Counter32,
		erabRelEnbNbrQci8					Counter32,
		erabRelEnbNbrQci9					Counter32,
		erabRelEnbNbrUserInactivity					Counter32,
		erabRelEnbNbrRadioInterfaceFailure					Counter32,
		erabRelEnbNbrUnspecified					Counter32,
		erabRelFailNbrInteractionWithOtherProcedure					Counter32,
		erabRelFailNbrTransferSyntaxError					Counter32,
		erabRelFailNbrAbstractSyntaxError					Counter32,
		erabRelFailNbrControlProcessingOverload					Counter32,
		erabRelFailNbrHardwareFailure					Counter32,
		erabRelFailNbrUeS1apIdPairError					Counter32,
		erabRelFailNbrRadioInterfaceFailure					Counter32,
		erabRelFailNbrUnspecifiedFailure					Counter32,
		erabRelAttNbrQci1					Counter32,
		erabRelSuccNbrQci1					Counter32,
		erabRelAttNbrQci2					Counter32,
		erabRelSuccNbrQci2					Counter32,
		erabRelAttNbrQci3					Counter32,
		erabRelSuccNbrQci3					Counter32,
		erabRelAttNbrQci4					Counter32,
		erabRelSuccNbrQci4					Counter32,
		erabRelAttNbrQci5					Counter32,
		erabRelSuccNbrQci5					Counter32,
		erabRelAttNbrQci6					Counter32,
		erabRelSuccNbrQci6					Counter32,
		erabRelAttNbrQci7					Counter32,
		erabRelSuccNbrQci7					Counter32,
		erabRelAttNbrQci8					Counter32,
		erabRelSuccNbrQci8					Counter32,
		erabRelAttNbrQci9					Counter32,
		erabRelSuccNbrQci9					Counter32,
		erabRelMmeNbrTransport					Counter32,
		erabRelMmeNbrNormalRelease					Counter32,
		erabRelMmeNbrDetach					Counter32,
		erabRelMmeNbrUnspecifiedNas					Counter32,
		erabRelMmeNbrProtocol					Counter32,
		erabRelMmeNbrMiscellaneous					Counter32,
		erabRelMmeNbrRadioNetworkLayer					Counter32,
		erabRelEnbNbrCSFallbackTriggered					Counter32,
		erabRelEnbNbrUENotAvailableforPS					Counter32,
		erabRelEnbNbrInterRATRedirection					Counter32,
		erabRelEnbNbrRedirectionto1xRTT					Counter32,
		erabRelEnbNbrOMIntervention					Counter32,
		erabRelEnbNbrUELostM1					Counter32,
		erabRelEnbNbrUELostN					Counter32,
		erabRelEnbNbrTransfer					Counter32,
		erabRelEnbNbrCongestion					Counter32,
		erabRelMmeNbrRadioNetworkLayerOther					Counter32,
		erabRelMmeNbrUserInactivity					Counter32,
		erabRelMmeNbrCSFallbackTriggered					Counter32,
		erabRelMmeNbrUENotAvailableforPS					Counter32,
		erabRelMmeNbrInterRATRedirection					Counter32,
		erabRelMmeNbrRedirectionTowards1xRTT					Counter32,
		erabRelMmeNbrRadioInterfaceFailure					Counter32,
		erabRelMmeNbrUELost					Counter32,
		erabRelMmeNbrCongestion					Counter32,
		erabRelMmeNbrSucHO					Counter32,
		erabRelEnbNbrUELostTa					Counter32,
		erabRelEnbNbrUELostRlc					Counter32,
		erabRelEnbNbrHoFail					Counter32,
		erabRelEnbNbrReConfigFail					Counter32,
		erabRelEnbNbrReEstabFail					Counter32
		}


	erabRelProcLcId		 OBJECT-TYPE
		SYNTAX					 Integer32( 0 .. 23 )
		MAX-ACCESS			 not-accessible
		STATUS					 current
		DESCRIPTION			 " -- "
		::=  { erabRelProcEntry  1 }


	erabRelProcRowStatus		 OBJECT-TYPE
		SYNTAX					 RowStatus
		MAX-ACCESS			 read-only
		STATUS					 current
		DESCRIPTION			 " -- "
		::=  { erabRelProcEntry  2 }


	erabRelEnbNbrQci1		 OBJECT-TYPE
		SYNTAX					 Counter32
		MAX-ACCESS			 read-only
		STATUS					 current
		DESCRIPTION			 " -- "
		::=  { erabRelProcEntry  3 }


	erabRelEnbNbrQci2		 OBJECT-TYPE
		SYNTAX					 Counter32
		MAX-ACCESS			 read-only
		STATUS					 current
		DESCRIPTION			 " -- "
		::=  { erabRelProcEntry  4 }


	erabRelEnbNbrQci3		 OBJECT-TYPE
		SYNTAX					 Counter32
		MAX-ACCESS			 read-only
		STATUS					 current
		DESCRIPTION			 " -- "
		::=  { erabRelProcEntry  5 }


	erabRelEnbNbrQci4		 OBJECT-TYPE
		SYNTAX					 Counter32
		MAX-ACCESS			 read-only
		STATUS					 current
		DESCRIPTION			 " -- "
		::=  { erabRelProcEntry  6 }


	erabRelEnbNbrQci5		 OBJECT-TYPE
		SYNTAX					 Counter32
		MAX-ACCESS			 read-only
		STATUS					 current
		DESCRIPTION			 " -- "
		::=  { erabRelProcEntry  7 }


	erabRelEnbNbrQci6		 OBJECT-TYPE
		SYNTAX					 Counter32
		MAX-ACCESS			 read-only
		STATUS					 current
		DESCRIPTION			 " -- "
		::=  { erabRelProcEntry  8 }


	erabRelEnbNbrQci7		 OBJECT-TYPE
		SYNTAX					 Counter32
		MAX-ACCESS			 read-only
		STATUS					 current
		DESCRIPTION			 " -- "
		::=  { erabRelProcEntry  9 }


	erabRelEnbNbrQci8		 OBJECT-TYPE
		SYNTAX					 Counter32
		MAX-ACCESS			 read-only
		STATUS					 current
		DESCRIPTION			 " -- "
		::=  { erabRelProcEntry  10 }


	erabRelEnbNbrQci9		 OBJECT-TYPE
		SYNTAX					 Counter32
		MAX-ACCESS			 read-only
		STATUS					 current
		DESCRIPTION			 " -- "
		::=  { erabRelProcEntry  11 }


	erabRelEnbNbrUserInactivity		 OBJECT-TYPE
		SYNTAX					 Counter32
		MAX-ACCESS			 read-only
		STATUS					 current
		DESCRIPTION			 " -- "
		::=  { erabRelProcEntry  12 }


	erabRelEnbNbrRadioInterfaceFailure		 OBJECT-TYPE
		SYNTAX					 Counter32
		MAX-ACCESS			 read-only
		STATUS					 current
		DESCRIPTION			 " -- "
		::=  { erabRelProcEntry  13 }


	erabRelEnbNbrUnspecified		 OBJECT-TYPE
		SYNTAX					 Counter32
		MAX-ACCESS			 read-only
		STATUS					 current
		DESCRIPTION			 " -- "
		::=  { erabRelProcEntry  14 }


	erabRelFailNbrInteractionWithOtherProcedure		 OBJECT-TYPE
		SYNTAX					 Counter32
		MAX-ACCESS			 read-only
		STATUS					 current
		DESCRIPTION			 " -- "
		::=  { erabRelProcEntry  15 }


	erabRelFailNbrTransferSyntaxError		 OBJECT-TYPE
		SYNTAX					 Counter32
		MAX-ACCESS			 read-only
		STATUS					 current
		DESCRIPTION			 " -- "
		::=  { erabRelProcEntry  16 }


	erabRelFailNbrAbstractSyntaxError		 OBJECT-TYPE
		SYNTAX					 Counter32
		MAX-ACCESS			 read-only
		STATUS					 current
		DESCRIPTION			 " -- "
		::=  { erabRelProcEntry  17 }


	erabRelFailNbrControlProcessingOverload		 OBJECT-TYPE
		SYNTAX					 Counter32
		MAX-ACCESS			 read-only
		STATUS					 current
		DESCRIPTION			 " -- "
		::=  { erabRelProcEntry  18 }


	erabRelFailNbrHardwareFailure		 OBJECT-TYPE
		SYNTAX					 Counter32
		MAX-ACCESS			 read-only
		STATUS					 current
		DESCRIPTION			 " -- "
		::=  { erabRelProcEntry  19 }


	erabRelFailNbrUeS1apIdPairError		 OBJECT-TYPE
		SYNTAX					 Counter32
		MAX-ACCESS			 read-only
		STATUS					 current
		DESCRIPTION			 " -- "
		::=  { erabRelProcEntry  20 }


	erabRelFailNbrRadioInterfaceFailure		 OBJECT-TYPE
		SYNTAX					 Counter32
		MAX-ACCESS			 read-only
		STATUS					 current
		DESCRIPTION			 " -- "
		::=  { erabRelProcEntry  21 }


	erabRelFailNbrUnspecifiedFailure		 OBJECT-TYPE
		SYNTAX					 Counter32
		MAX-ACCESS			 read-only
		STATUS					 current
		DESCRIPTION			 " -- "
		::=  { erabRelProcEntry  22 }


	erabRelAttNbrQci1		 OBJECT-TYPE
		SYNTAX					 Counter32
		MAX-ACCESS			 read-only
		STATUS					 current
		DESCRIPTION			 " -- "
		::=  { erabRelProcEntry  23 }


	erabRelSuccNbrQci1		 OBJECT-TYPE
		SYNTAX					 Counter32
		MAX-ACCESS			 read-only
		STATUS					 current
		DESCRIPTION			 " -- "
		::=  { erabRelProcEntry  24 }


	erabRelAttNbrQci2		 OBJECT-TYPE
		SYNTAX					 Counter32
		MAX-ACCESS			 read-only
		STATUS					 current
		DESCRIPTION			 " -- "
		::=  { erabRelProcEntry  25 }


	erabRelSuccNbrQci2		 OBJECT-TYPE
		SYNTAX					 Counter32
		MAX-ACCESS			 read-only
		STATUS					 current
		DESCRIPTION			 " -- "
		::=  { erabRelProcEntry  26 }


	erabRelAttNbrQci3		 OBJECT-TYPE
		SYNTAX					 Counter32
		MAX-ACCESS			 read-only
		STATUS					 current
		DESCRIPTION			 " -- "
		::=  { erabRelProcEntry  27 }


	erabRelSuccNbrQci3		 OBJECT-TYPE
		SYNTAX					 Counter32
		MAX-ACCESS			 read-only
		STATUS					 current
		DESCRIPTION			 " -- "
		::=  { erabRelProcEntry  28 }


	erabRelAttNbrQci4		 OBJECT-TYPE
		SYNTAX					 Counter32
		MAX-ACCESS			 read-only
		STATUS					 current
		DESCRIPTION			 " -- "
		::=  { erabRelProcEntry  29 }


	erabRelSuccNbrQci4		 OBJECT-TYPE
		SYNTAX					 Counter32
		MAX-ACCESS			 read-only
		STATUS					 current
		DESCRIPTION			 " -- "
		::=  { erabRelProcEntry  30 }


	erabRelAttNbrQci5		 OBJECT-TYPE
		SYNTAX					 Counter32
		MAX-ACCESS			 read-only
		STATUS					 current
		DESCRIPTION			 " -- "
		::=  { erabRelProcEntry  31 }


	erabRelSuccNbrQci5		 OBJECT-TYPE
		SYNTAX					 Counter32
		MAX-ACCESS			 read-only
		STATUS					 current
		DESCRIPTION			 " -- "
		::=  { erabRelProcEntry  32 }


	erabRelAttNbrQci6		 OBJECT-TYPE
		SYNTAX					 Counter32
		MAX-ACCESS			 read-only
		STATUS					 current
		DESCRIPTION			 " -- "
		::=  { erabRelProcEntry  33 }


	erabRelSuccNbrQci6		 OBJECT-TYPE
		SYNTAX					 Counter32
		MAX-ACCESS			 read-only
		STATUS					 current
		DESCRIPTION			 " -- "
		::=  { erabRelProcEntry  34 }


	erabRelAttNbrQci7		 OBJECT-TYPE
		SYNTAX					 Counter32
		MAX-ACCESS			 read-only
		STATUS					 current
		DESCRIPTION			 " -- "
		::=  { erabRelProcEntry  35 }


	erabRelSuccNbrQci7		 OBJECT-TYPE
		SYNTAX					 Counter32
		MAX-ACCESS			 read-only
		STATUS					 current
		DESCRIPTION			 " -- "
		::=  { erabRelProcEntry  36 }


	erabRelAttNbrQci8		 OBJECT-TYPE
		SYNTAX					 Counter32
		MAX-ACCESS			 read-only
		STATUS					 current
		DESCRIPTION			 " -- "
		::=  { erabRelProcEntry  37 }


	erabRelSuccNbrQci8		 OBJECT-TYPE
		SYNTAX					 Counter32
		MAX-ACCESS			 read-only
		STATUS					 current
		DESCRIPTION			 " -- "
		::=  { erabRelProcEntry  38 }


	erabRelAttNbrQci9		 OBJECT-TYPE
		SYNTAX					 Counter32
		MAX-ACCESS			 read-only
		STATUS					 current
		DESCRIPTION			 " -- "
		::=  { erabRelProcEntry  39 }


	erabRelSuccNbrQci9		 OBJECT-TYPE
		SYNTAX					 Counter32
		MAX-ACCESS			 read-only
		STATUS					 current
		DESCRIPTION			 " -- "
		::=  { erabRelProcEntry  40 }


	erabRelMmeNbrTransport		 OBJECT-TYPE
		SYNTAX					 Counter32
		MAX-ACCESS			 read-only
		STATUS					 current
		DESCRIPTION			 " -- "
		::=  { erabRelProcEntry  41 }


	erabRelMmeNbrNormalRelease		 OBJECT-TYPE
		SYNTAX					 Counter32
		MAX-ACCESS			 read-only
		STATUS					 current
		DESCRIPTION			 " -- "
		::=  { erabRelProcEntry  42 }


	erabRelMmeNbrDetach		 OBJECT-TYPE
		SYNTAX					 Counter32
		MAX-ACCESS			 read-only
		STATUS					 current
		DESCRIPTION			 " -- "
		::=  { erabRelProcEntry  43 }


	erabRelMmeNbrUnspecifiedNas		 OBJECT-TYPE
		SYNTAX					 Counter32
		MAX-ACCESS			 read-only
		STATUS					 current
		DESCRIPTION			 " -- "
		::=  { erabRelProcEntry  44 }


	erabRelMmeNbrProtocol		 OBJECT-TYPE
		SYNTAX					 Counter32
		MAX-ACCESS			 read-only
		STATUS					 current
		DESCRIPTION			 " -- "
		::=  { erabRelProcEntry  45 }


	erabRelMmeNbrMiscellaneous		 OBJECT-TYPE
		SYNTAX					 Counter32
		MAX-ACCESS			 read-only
		STATUS					 current
		DESCRIPTION			 " -- "
		::=  { erabRelProcEntry  46 }


	erabRelMmeNbrRadioNetworkLayer		 OBJECT-TYPE
		SYNTAX					 Counter32
		MAX-ACCESS			 read-only
		STATUS					 current
		DESCRIPTION			 " -- "
		::=  { erabRelProcEntry  47 }


	erabRelEnbNbrCSFallbackTriggered		 OBJECT-TYPE
		SYNTAX					 Counter32
		MAX-ACCESS			 read-only
		STATUS					 current
		DESCRIPTION			 " -- "
		::=  { erabRelProcEntry  48 }


	erabRelEnbNbrUENotAvailableforPS		 OBJECT-TYPE
		SYNTAX					 Counter32
		MAX-ACCESS			 read-only
		STATUS					 current
		DESCRIPTION			 " -- "
		::=  { erabRelProcEntry  49 }


	erabRelEnbNbrInterRATRedirection		 OBJECT-TYPE
		SYNTAX					 Counter32
		MAX-ACCESS			 read-only
		STATUS					 current
		DESCRIPTION			 " -- "
		::=  { erabRelProcEntry  50 }


	erabRelEnbNbrRedirectionto1xRTT		 OBJECT-TYPE
		SYNTAX					 Counter32
		MAX-ACCESS			 read-only
		STATUS					 current
		DESCRIPTION			 " -- "
		::=  { erabRelProcEntry  51 }


	erabRelEnbNbrOMIntervention		 OBJECT-TYPE
		SYNTAX					 Counter32
		MAX-ACCESS			 read-only
		STATUS					 current
		DESCRIPTION			 " -- "
		::=  { erabRelProcEntry  52 }


	erabRelEnbNbrUELostM1		 OBJECT-TYPE
		SYNTAX					 Counter32
		MAX-ACCESS			 read-only
		STATUS					 current
		DESCRIPTION			 " -- "
		::=  { erabRelProcEntry  53 }


	erabRelEnbNbrUELostN		 OBJECT-TYPE
		SYNTAX					 Counter32
		MAX-ACCESS			 read-only
		STATUS					 current
		DESCRIPTION			 " -- "
		::=  { erabRelProcEntry  54 }


	erabRelEnbNbrTransfer		 OBJECT-TYPE
		SYNTAX					 Counter32
		MAX-ACCESS			 read-only
		STATUS					 current
		DESCRIPTION			 " -- "
		::=  { erabRelProcEntry  55 }


	erabRelEnbNbrCongestion		 OBJECT-TYPE
		SYNTAX					 Counter32
		MAX-ACCESS			 read-only
		STATUS					 current
		DESCRIPTION			 " -- "
		::=  { erabRelProcEntry  56 }


	erabRelMmeNbrRadioNetworkLayerOther		 OBJECT-TYPE
		SYNTAX					 Counter32
		MAX-ACCESS			 read-only
		STATUS					 current
		DESCRIPTION			 " -- "
		::=  { erabRelProcEntry  57 }


	erabRelMmeNbrUserInactivity		 OBJECT-TYPE
		SYNTAX					 Counter32
		MAX-ACCESS			 read-only
		STATUS					 current
		DESCRIPTION			 " -- "
		::=  { erabRelProcEntry  58 }


	erabRelMmeNbrCSFallbackTriggered		 OBJECT-TYPE
		SYNTAX					 Counter32
		MAX-ACCESS			 read-only
		STATUS					 current
		DESCRIPTION			 " -- "
		::=  { erabRelProcEntry  59 }


	erabRelMmeNbrUENotAvailableforPS		 OBJECT-TYPE
		SYNTAX					 Counter32
		MAX-ACCESS			 read-only
		STATUS					 current
		DESCRIPTION			 " -- "
		::=  { erabRelProcEntry  60 }


	erabRelMmeNbrInterRATRedirection		 OBJECT-TYPE
		SYNTAX					 Counter32
		MAX-ACCESS			 read-only
		STATUS					 current
		DESCRIPTION			 " -- "
		::=  { erabRelProcEntry  61 }


	erabRelMmeNbrRedirectionTowards1xRTT		 OBJECT-TYPE
		SYNTAX					 Counter32
		MAX-ACCESS			 read-only
		STATUS					 current
		DESCRIPTION			 " -- "
		::=  { erabRelProcEntry  62 }


	erabRelMmeNbrRadioInterfaceFailure		 OBJECT-TYPE
		SYNTAX					 Counter32
		MAX-ACCESS			 read-only
		STATUS					 current
		DESCRIPTION			 " -- "
		::=  { erabRelProcEntry  63 }


	erabRelMmeNbrUELost		 OBJECT-TYPE
		SYNTAX					 Counter32
		MAX-ACCESS			 read-only
		STATUS					 current
		DESCRIPTION			 " -- "
		::=  { erabRelProcEntry  64 }


	erabRelMmeNbrCongestion		 OBJECT-TYPE
		SYNTAX					 Counter32
		MAX-ACCESS			 read-only
		STATUS					 current
		DESCRIPTION			 " -- "
		::=  { erabRelProcEntry  65 }


	erabRelMmeNbrSucHO		 OBJECT-TYPE
		SYNTAX					 Counter32
		MAX-ACCESS			 read-only
		STATUS					 current
		DESCRIPTION			 " -- "
		::=  { erabRelProcEntry  66 }


	erabRelEnbNbrUELostTa		 OBJECT-TYPE
		SYNTAX					 Counter32
		MAX-ACCESS			 read-only
		STATUS					 current
		DESCRIPTION			 " -- "
		::=  { erabRelProcEntry  67 }


	erabRelEnbNbrUELostRlc		 OBJECT-TYPE
		SYNTAX					 Counter32
		MAX-ACCESS			 read-only
		STATUS					 current
		DESCRIPTION			 " -- "
		::=  { erabRelProcEntry  68 }


	erabRelEnbNbrHoFail		 OBJECT-TYPE
		SYNTAX					 Counter32
		MAX-ACCESS			 read-only
		STATUS					 current
		DESCRIPTION			 " -- "
		::=  { erabRelProcEntry  69 }


	erabRelEnbNbrReConfigFail		 OBJECT-TYPE
		SYNTAX					 Counter32
		MAX-ACCESS			 read-only
		STATUS					 current
		DESCRIPTION			 " -- "
		::=  { erabRelProcEntry  70 }


	erabRelEnbNbrReEstabFail		 OBJECT-TYPE
		SYNTAX					 Counter32
		MAX-ACCESS			 read-only
		STATUS					 current
		DESCRIPTION			 " -- "
		::=  { erabRelProcEntry  71 }


	erabInitEstabTimeTable		 OBJECT-TYPE
		SYNTAX					 SEQUENCE  OF	 ErabInitEstabTimeEntry
		MAX-ACCESS			 not-accessible
		STATUS					 current
		DESCRIPTION			 " -- "
		::=  { aprelatedOriginCounter  4 }


	erabInitEstabTimeEntry		 OBJECT-TYPE
		SYNTAX					 ErabInitEstabTimeEntry
		MAX-ACCESS			 not-accessible
		STATUS					 current
		DESCRIPTION			 " -- "
		INDEX						{ erabInitEstabTimeLcId }
		::=  { erabInitEstabTimeTable  1 }


	ErabInitEstabTimeEntry		 ::=  SEQUENCE {
		erabInitEstabTimeLcId					Integer32,
		erabInitEstabTimeRowStatus					RowStatus,
		erabInitEstabTimeMean					Counter32,
		erabInitEstabTimeMax					Counter32,
		erabAddEstabTimeMean					Counter32,
		erabAddEstabTimeMax					Counter32,
		erabEstabTimeMean					Counter32,
		erabEstabTimeMax					Counter32
		}


	erabInitEstabTimeLcId		 OBJECT-TYPE
		SYNTAX					 Integer32( 0 .. 23 )
		MAX-ACCESS			 not-accessible
		STATUS					 current
		DESCRIPTION			 " -- "
		::=  { erabInitEstabTimeEntry  1 }


	erabInitEstabTimeRowStatus		 OBJECT-TYPE
		SYNTAX					 RowStatus
		MAX-ACCESS			 read-only
		STATUS					 current
		DESCRIPTION			 " -- "
		::=  { erabInitEstabTimeEntry  2 }


	erabInitEstabTimeMean		 OBJECT-TYPE
		SYNTAX					 Counter32
		MAX-ACCESS			 read-only
		STATUS					 current
		DESCRIPTION			 " -- "
		::=  { erabInitEstabTimeEntry  3 }


	erabInitEstabTimeMax		 OBJECT-TYPE
		SYNTAX					 Counter32
		MAX-ACCESS			 read-only
		STATUS					 current
		DESCRIPTION			 " -- "
		::=  { erabInitEstabTimeEntry  4 }


	erabAddEstabTimeMean		 OBJECT-TYPE
		SYNTAX					 Counter32
		MAX-ACCESS			 read-only
		STATUS					 current
		DESCRIPTION			 " -- "
		::=  { erabInitEstabTimeEntry  5 }


	erabAddEstabTimeMax		 OBJECT-TYPE
		SYNTAX					 Counter32
		MAX-ACCESS			 read-only
		STATUS					 current
		DESCRIPTION			 " -- "
		::=  { erabInitEstabTimeEntry  6 }


	erabEstabTimeMean		 OBJECT-TYPE
		SYNTAX					 Counter32
		MAX-ACCESS			 read-only
		STATUS					 current
		DESCRIPTION			 " -- "
		::=  { erabInitEstabTimeEntry  7 }


	erabEstabTimeMax		 OBJECT-TYPE
		SYNTAX					 Counter32
		MAX-ACCESS			 read-only
		STATUS					 current
		DESCRIPTION			 " -- "
		::=  { erabInitEstabTimeEntry  8 }


	erabModProcTable		 OBJECT-TYPE
		SYNTAX					 SEQUENCE  OF	 ErabModProcEntry
		MAX-ACCESS			 not-accessible
		STATUS					 current
		DESCRIPTION			 " -- "
		::=  { aprelatedOriginCounter  5 }


	erabModProcEntry		 OBJECT-TYPE
		SYNTAX					 ErabModProcEntry
		MAX-ACCESS			 not-accessible
		STATUS					 current
		DESCRIPTION			 " -- "
		INDEX						{ erabModProcLcId }
		::=  { erabModProcTable  1 }


	ErabModProcEntry		 ::=  SEQUENCE {
		erabModProcLcId					Integer32,
		erabModProcRowStatus					RowStatus,
		erabModQoSFailNbrUeS1apIdPairError					Counter32,
		erabModQoSFailNbrInteractionWithOtherProc					Counter32,
		erabModQoSFailNbrInvalidQosCombination					Counter32,
		erabModQoSFailNbrRadioInterfaceFailure					Counter32,
		erabModQoSFailNbrMultipleErabId					Counter32,
		erabModQoSFailNbrS1IntraSystemHoTrig					Counter32,
		erabModQoSFailNbrS1InterSystemHoTrig					Counter32,
		erabModQoSFailNbrX2HandoverTriggered					Counter32,
		erabModQoSFailNbrTransResNotAvailable					Counter32,
		erabModQoSFailNbrTransferSyntaxError					Counter32,
		erabModQoSFailNbrAbstractSyntaxError					Counter32,
		erabModQoSFailNbrControlProcessingOverload					Counter32,
		erabModQoSFailNbrUnspecifiedFailure					Counter32,
		erabModQoSAttNbrQci1					Counter32,
		erabModQoSSuccNbrQci1					Counter32,
		erabModQoSAttNbrQci2					Counter32,
		erabModQoSSuccNbrQci2					Counter32,
		erabModQoSAttNbrQci3					Counter32,
		erabModQoSSuccNbrQci3					Counter32,
		erabModQoSAttNbrQci4					Counter32,
		erabModQoSSuccNbrQci4					Counter32,
		erabModQoSAttNbrQci5					Counter32,
		erabModQoSSuccNbrQci5					Counter32,
		erabModQoSAttNbrQci6					Counter32,
		erabModQoSSuccNbrQci6					Counter32,
		erabModQoSAttNbrQci7					Counter32,
		erabModQoSSuccNbrQci7					Counter32,
		erabModQoSAttNbrQci8					Counter32,
		erabModQoSSuccNbrQci8					Counter32,
		erabModQoSAttNbrQci9					Counter32,
		erabModQoSSuccNbrQci9					Counter32
		}


	erabModProcLcId		 OBJECT-TYPE
		SYNTAX					 Integer32( 0 .. 23 )
		MAX-ACCESS			 not-accessible
		STATUS					 current
		DESCRIPTION			 " -- "
		::=  { erabModProcEntry  1 }


	erabModProcRowStatus		 OBJECT-TYPE
		SYNTAX					 RowStatus
		MAX-ACCESS			 read-only
		STATUS					 current
		DESCRIPTION			 " -- "
		::=  { erabModProcEntry  2 }


	erabModQoSFailNbrUeS1apIdPairError		 OBJECT-TYPE
		SYNTAX					 Counter32
		MAX-ACCESS			 read-only
		STATUS					 current
		DESCRIPTION			 " -- "
		::=  { erabModProcEntry  3 }


	erabModQoSFailNbrInteractionWithOtherProc		 OBJECT-TYPE
		SYNTAX					 Counter32
		MAX-ACCESS			 read-only
		STATUS					 current
		DESCRIPTION			 " -- "
		::=  { erabModProcEntry  4 }


	erabModQoSFailNbrInvalidQosCombination		 OBJECT-TYPE
		SYNTAX					 Counter32
		MAX-ACCESS			 read-only
		STATUS					 current
		DESCRIPTION			 " -- "
		::=  { erabModProcEntry  5 }


	erabModQoSFailNbrRadioInterfaceFailure		 OBJECT-TYPE
		SYNTAX					 Counter32
		MAX-ACCESS			 read-only
		STATUS					 current
		DESCRIPTION			 " -- "
		::=  { erabModProcEntry  6 }


	erabModQoSFailNbrMultipleErabId		 OBJECT-TYPE
		SYNTAX					 Counter32
		MAX-ACCESS			 read-only
		STATUS					 current
		DESCRIPTION			 " -- "
		::=  { erabModProcEntry  7 }


	erabModQoSFailNbrS1IntraSystemHoTrig		 OBJECT-TYPE
		SYNTAX					 Counter32
		MAX-ACCESS			 read-only
		STATUS					 current
		DESCRIPTION			 " -- "
		::=  { erabModProcEntry  8 }


	erabModQoSFailNbrS1InterSystemHoTrig		 OBJECT-TYPE
		SYNTAX					 Counter32
		MAX-ACCESS			 read-only
		STATUS					 current
		DESCRIPTION			 " -- "
		::=  { erabModProcEntry  9 }


	erabModQoSFailNbrX2HandoverTriggered		 OBJECT-TYPE
		SYNTAX					 Counter32
		MAX-ACCESS			 read-only
		STATUS					 current
		DESCRIPTION			 " -- "
		::=  { erabModProcEntry  10 }


	erabModQoSFailNbrTransResNotAvailable		 OBJECT-TYPE
		SYNTAX					 Counter32
		MAX-ACCESS			 read-only
		STATUS					 current
		DESCRIPTION			 " -- "
		::=  { erabModProcEntry  11 }


	erabModQoSFailNbrTransferSyntaxError		 OBJECT-TYPE
		SYNTAX					 Counter32
		MAX-ACCESS			 read-only
		STATUS					 current
		DESCRIPTION			 " -- "
		::=  { erabModProcEntry  12 }


	erabModQoSFailNbrAbstractSyntaxError		 OBJECT-TYPE
		SYNTAX					 Counter32
		MAX-ACCESS			 read-only
		STATUS					 current
		DESCRIPTION			 " -- "
		::=  { erabModProcEntry  13 }


	erabModQoSFailNbrControlProcessingOverload		 OBJECT-TYPE
		SYNTAX					 Counter32
		MAX-ACCESS			 read-only
		STATUS					 current
		DESCRIPTION			 " -- "
		::=  { erabModProcEntry  14 }


	erabModQoSFailNbrUnspecifiedFailure		 OBJECT-TYPE
		SYNTAX					 Counter32
		MAX-ACCESS			 read-only
		STATUS					 current
		DESCRIPTION			 " -- "
		::=  { erabModProcEntry  15 }


	erabModQoSAttNbrQci1		 OBJECT-TYPE
		SYNTAX					 Counter32
		MAX-ACCESS			 read-only
		STATUS					 current
		DESCRIPTION			 " -- "
		::=  { erabModProcEntry  16 }


	erabModQoSSuccNbrQci1		 OBJECT-TYPE
		SYNTAX					 Counter32
		MAX-ACCESS			 read-only
		STATUS					 current
		DESCRIPTION			 " -- "
		::=  { erabModProcEntry  17 }


	erabModQoSAttNbrQci2		 OBJECT-TYPE
		SYNTAX					 Counter32
		MAX-ACCESS			 read-only
		STATUS					 current
		DESCRIPTION			 " -- "
		::=  { erabModProcEntry  18 }


	erabModQoSSuccNbrQci2		 OBJECT-TYPE
		SYNTAX					 Counter32
		MAX-ACCESS			 read-only
		STATUS					 current
		DESCRIPTION			 " -- "
		::=  { erabModProcEntry  19 }


	erabModQoSAttNbrQci3		 OBJECT-TYPE
		SYNTAX					 Counter32
		MAX-ACCESS			 read-only
		STATUS					 current
		DESCRIPTION			 " -- "
		::=  { erabModProcEntry  20 }


	erabModQoSSuccNbrQci3		 OBJECT-TYPE
		SYNTAX					 Counter32
		MAX-ACCESS			 read-only
		STATUS					 current
		DESCRIPTION			 " -- "
		::=  { erabModProcEntry  21 }


	erabModQoSAttNbrQci4		 OBJECT-TYPE
		SYNTAX					 Counter32
		MAX-ACCESS			 read-only
		STATUS					 current
		DESCRIPTION			 " -- "
		::=  { erabModProcEntry  22 }


	erabModQoSSuccNbrQci4		 OBJECT-TYPE
		SYNTAX					 Counter32
		MAX-ACCESS			 read-only
		STATUS					 current
		DESCRIPTION			 " -- "
		::=  { erabModProcEntry  23 }


	erabModQoSAttNbrQci5		 OBJECT-TYPE
		SYNTAX					 Counter32
		MAX-ACCESS			 read-only
		STATUS					 current
		DESCRIPTION			 " -- "
		::=  { erabModProcEntry  24 }


	erabModQoSSuccNbrQci5		 OBJECT-TYPE
		SYNTAX					 Counter32
		MAX-ACCESS			 read-only
		STATUS					 current
		DESCRIPTION			 " -- "
		::=  { erabModProcEntry  25 }


	erabModQoSAttNbrQci6		 OBJECT-TYPE
		SYNTAX					 Counter32
		MAX-ACCESS			 read-only
		STATUS					 current
		DESCRIPTION			 " -- "
		::=  { erabModProcEntry  26 }


	erabModQoSSuccNbrQci6		 OBJECT-TYPE
		SYNTAX					 Counter32
		MAX-ACCESS			 read-only
		STATUS					 current
		DESCRIPTION			 " -- "
		::=  { erabModProcEntry  27 }


	erabModQoSAttNbrQci7		 OBJECT-TYPE
		SYNTAX					 Counter32
		MAX-ACCESS			 read-only
		STATUS					 current
		DESCRIPTION			 " -- "
		::=  { erabModProcEntry  28 }


	erabModQoSSuccNbrQci7		 OBJECT-TYPE
		SYNTAX					 Counter32
		MAX-ACCESS			 read-only
		STATUS					 current
		DESCRIPTION			 " -- "
		::=  { erabModProcEntry  29 }


	erabModQoSAttNbrQci8		 OBJECT-TYPE
		SYNTAX					 Counter32
		MAX-ACCESS			 read-only
		STATUS					 current
		DESCRIPTION			 " -- "
		::=  { erabModProcEntry  30 }


	erabModQoSSuccNbrQci8		 OBJECT-TYPE
		SYNTAX					 Counter32
		MAX-ACCESS			 read-only
		STATUS					 current
		DESCRIPTION			 " -- "
		::=  { erabModProcEntry  31 }


	erabModQoSAttNbrQci9		 OBJECT-TYPE
		SYNTAX					 Counter32
		MAX-ACCESS			 read-only
		STATUS					 current
		DESCRIPTION			 " -- "
		::=  { erabModProcEntry  32 }


	erabModQoSSuccNbrQci9		 OBJECT-TYPE
		SYNTAX					 Counter32
		MAX-ACCESS			 read-only
		STATUS					 current
		DESCRIPTION			 " -- "
		::=  { erabModProcEntry  33 }


	erabNbrTable		 OBJECT-TYPE
		SYNTAX					 SEQUENCE  OF	 ErabNbrEntry
		MAX-ACCESS			 not-accessible
		STATUS					 current
		DESCRIPTION			 " -- "
		::=  { aprelatedOriginCounter  6 }


	erabNbrEntry		 OBJECT-TYPE
		SYNTAX					 ErabNbrEntry
		MAX-ACCESS			 not-accessible
		STATUS					 current
		DESCRIPTION			 " -- "
		INDEX						{ erabNbrLcId }
		::=  { erabNbrTable  1 }


	ErabNbrEntry		 ::=  SEQUENCE {
		erabNbrLcId					Integer32,
		erabNbrRowStatus					RowStatus,
		erabNbrMeanEstabQci1					Counter32,
		erabNbrMeanEstabQci2					Counter32,
		erabNbrMeanEstabQci3					Counter32,
		erabNbrMeanEstabQci4					Counter32,
		erabNbrMeanEstabQci5					Counter32,
		erabNbrMeanEstabQci6					Counter32,
		erabNbrMeanEstabQci7					Counter32,
		erabNbrMeanEstabQci8					Counter32,
		erabNbrMeanEstabQci9					Counter32,
		erabNbrMaxEstabQci1					Counter32,
		erabNbrMaxEstabQci2					Counter32,
		erabNbrMaxEstabQci3					Counter32,
		erabNbrMaxEstabQci4					Counter32,
		erabNbrMaxEstabQci5					Counter32,
		erabNbrMaxEstabQci6					Counter32,
		erabNbrMaxEstabQci7					Counter32,
		erabNbrMaxEstabQci8					Counter32,
		erabNbrMaxEstabQci9					Counter32,
		erabNbrMaxEstab					Counter32,
		erabNbrEstabSumQci1					Counter32,
		erabNbrEstabSumQci2					Counter32,
		erabNbrEstabSumQci5					Counter32,
		erabNbrEstabSampNum					Counter32
		}


	erabNbrLcId		 OBJECT-TYPE
		SYNTAX					 Integer32( 0 .. 23 )
		MAX-ACCESS			 not-accessible
		STATUS					 current
		DESCRIPTION			 " -- "
		::=  { erabNbrEntry  1 }


	erabNbrRowStatus		 OBJECT-TYPE
		SYNTAX					 RowStatus
		MAX-ACCESS			 read-only
		STATUS					 current
		DESCRIPTION			 " -- "
		::=  { erabNbrEntry  2 }


	erabNbrMeanEstabQci1		 OBJECT-TYPE
		SYNTAX					 Counter32
		MAX-ACCESS			 read-only
		STATUS					 current
		DESCRIPTION			 " -- "
		::=  { erabNbrEntry  3 }


	erabNbrMeanEstabQci2		 OBJECT-TYPE
		SYNTAX					 Counter32
		MAX-ACCESS			 read-only
		STATUS					 current
		DESCRIPTION			 " -- "
		::=  { erabNbrEntry  4 }


	erabNbrMeanEstabQci3		 OBJECT-TYPE
		SYNTAX					 Counter32
		MAX-ACCESS			 read-only
		STATUS					 current
		DESCRIPTION			 " -- "
		::=  { erabNbrEntry  5 }


	erabNbrMeanEstabQci4		 OBJECT-TYPE
		SYNTAX					 Counter32
		MAX-ACCESS			 read-only
		STATUS					 current
		DESCRIPTION			 " -- "
		::=  { erabNbrEntry  6 }


	erabNbrMeanEstabQci5		 OBJECT-TYPE
		SYNTAX					 Counter32
		MAX-ACCESS			 read-only
		STATUS					 current
		DESCRIPTION			 " -- "
		::=  { erabNbrEntry  7 }


	erabNbrMeanEstabQci6		 OBJECT-TYPE
		SYNTAX					 Counter32
		MAX-ACCESS			 read-only
		STATUS					 current
		DESCRIPTION			 " -- "
		::=  { erabNbrEntry  8 }


	erabNbrMeanEstabQci7		 OBJECT-TYPE
		SYNTAX					 Counter32
		MAX-ACCESS			 read-only
		STATUS					 current
		DESCRIPTION			 " -- "
		::=  { erabNbrEntry  9 }


	erabNbrMeanEstabQci8		 OBJECT-TYPE
		SYNTAX					 Counter32
		MAX-ACCESS			 read-only
		STATUS					 current
		DESCRIPTION			 " -- "
		::=  { erabNbrEntry  10 }


	erabNbrMeanEstabQci9		 OBJECT-TYPE
		SYNTAX					 Counter32
		MAX-ACCESS			 read-only
		STATUS					 current
		DESCRIPTION			 " -- "
		::=  { erabNbrEntry  11 }


	erabNbrMaxEstabQci1		 OBJECT-TYPE
		SYNTAX					 Counter32
		MAX-ACCESS			 read-only
		STATUS					 current
		DESCRIPTION			 " -- "
		::=  { erabNbrEntry  12 }


	erabNbrMaxEstabQci2		 OBJECT-TYPE
		SYNTAX					 Counter32
		MAX-ACCESS			 read-only
		STATUS					 current
		DESCRIPTION			 " -- "
		::=  { erabNbrEntry  13 }


	erabNbrMaxEstabQci3		 OBJECT-TYPE
		SYNTAX					 Counter32
		MAX-ACCESS			 read-only
		STATUS					 current
		DESCRIPTION			 " -- "
		::=  { erabNbrEntry  14 }


	erabNbrMaxEstabQci4		 OBJECT-TYPE
		SYNTAX					 Counter32
		MAX-ACCESS			 read-only
		STATUS					 current
		DESCRIPTION			 " -- "
		::=  { erabNbrEntry  15 }


	erabNbrMaxEstabQci5		 OBJECT-TYPE
		SYNTAX					 Counter32
		MAX-ACCESS			 read-only
		STATUS					 current
		DESCRIPTION			 " -- "
		::=  { erabNbrEntry  16 }


	erabNbrMaxEstabQci6		 OBJECT-TYPE
		SYNTAX					 Counter32
		MAX-ACCESS			 read-only
		STATUS					 current
		DESCRIPTION			 " -- "
		::=  { erabNbrEntry  17 }


	erabNbrMaxEstabQci7		 OBJECT-TYPE
		SYNTAX					 Counter32
		MAX-ACCESS			 read-only
		STATUS					 current
		DESCRIPTION			 " -- "
		::=  { erabNbrEntry  18 }


	erabNbrMaxEstabQci8		 OBJECT-TYPE
		SYNTAX					 Counter32
		MAX-ACCESS			 read-only
		STATUS					 current
		DESCRIPTION			 " -- "
		::=  { erabNbrEntry  19 }


	erabNbrMaxEstabQci9		 OBJECT-TYPE
		SYNTAX					 Counter32
		MAX-ACCESS			 read-only
		STATUS					 current
		DESCRIPTION			 " -- "
		::=  { erabNbrEntry  20 }


	erabNbrMaxEstab		 OBJECT-TYPE
		SYNTAX					 Counter32
		MAX-ACCESS			 read-only
		STATUS					 current
		DESCRIPTION			 " -- "
		::=  { erabNbrEntry  21 }


	erabNbrEstabSumQci1		 OBJECT-TYPE
		SYNTAX					 Counter32
		MAX-ACCESS			 read-only
		STATUS					 current
		DESCRIPTION			 " -- "
		::=  { erabNbrEntry  22 }


	erabNbrEstabSumQci2		 OBJECT-TYPE
		SYNTAX					 Counter32
		MAX-ACCESS			 read-only
		STATUS					 current
		DESCRIPTION			 " -- "
		::=  { erabNbrEntry  23 }


	erabNbrEstabSumQci5		 OBJECT-TYPE
		SYNTAX					 Counter32
		MAX-ACCESS			 read-only
		STATUS					 current
		DESCRIPTION			 " -- "
		::=  { erabNbrEntry  24 }


	erabNbrEstabSampNum		 OBJECT-TYPE
		SYNTAX					 Counter32
		MAX-ACCESS			 read-only
		STATUS					 current
		DESCRIPTION			 " -- "
		::=  { erabNbrEntry  25 }


	handoverInERABNbrTable		 OBJECT-TYPE
		SYNTAX					 SEQUENCE  OF	 HandoverInERABNbrEntry
		MAX-ACCESS			 not-accessible
		STATUS					 current
		DESCRIPTION			 " -- "
		::=  { aprelatedOriginCounter  7 }


	handoverInERABNbrEntry		 OBJECT-TYPE
		SYNTAX					 HandoverInERABNbrEntry
		MAX-ACCESS			 not-accessible
		STATUS					 current
		DESCRIPTION			 " -- "
		INDEX						{ handoverInERABNbrLcId }
		::=  { handoverInERABNbrTable  1 }


	HandoverInERABNbrEntry		 ::=  SEQUENCE {
		handoverInERABNbrLcId					Integer32,
		handoverInERABNbrRowStatus					RowStatus,
		erabNbrHoIncQci1					Counter32,
		erabNbrHoIncQci2					Counter32,
		erabNbrHoIncQci3					Counter32,
		erabNbrHoIncQci4					Counter32,
		erabNbrHoIncQci5					Counter32,
		erabNbrHoIncQci6					Counter32,
		erabNbrHoIncQci7					Counter32,
		erabNbrHoIncQci8					Counter32,
		erabNbrHoIncQci9					Counter32
		}


	handoverInERABNbrLcId		 OBJECT-TYPE
		SYNTAX					 Integer32( 0 .. 23 )
		MAX-ACCESS			 not-accessible
		STATUS					 current
		DESCRIPTION			 " -- "
		::=  { handoverInERABNbrEntry  1 }


	handoverInERABNbrRowStatus		 OBJECT-TYPE
		SYNTAX					 RowStatus
		MAX-ACCESS			 read-only
		STATUS					 current
		DESCRIPTION			 " -- "
		::=  { handoverInERABNbrEntry  2 }


	erabNbrHoIncQci1		 OBJECT-TYPE
		SYNTAX					 Counter32
		MAX-ACCESS			 read-only
		STATUS					 current
		DESCRIPTION			 " -- "
		::=  { handoverInERABNbrEntry  3 }


	erabNbrHoIncQci2		 OBJECT-TYPE
		SYNTAX					 Counter32
		MAX-ACCESS			 read-only
		STATUS					 current
		DESCRIPTION			 " -- "
		::=  { handoverInERABNbrEntry  4 }


	erabNbrHoIncQci3		 OBJECT-TYPE
		SYNTAX					 Counter32
		MAX-ACCESS			 read-only
		STATUS					 current
		DESCRIPTION			 " -- "
		::=  { handoverInERABNbrEntry  5 }


	erabNbrHoIncQci4		 OBJECT-TYPE
		SYNTAX					 Counter32
		MAX-ACCESS			 read-only
		STATUS					 current
		DESCRIPTION			 " -- "
		::=  { handoverInERABNbrEntry  6 }


	erabNbrHoIncQci5		 OBJECT-TYPE
		SYNTAX					 Counter32
		MAX-ACCESS			 read-only
		STATUS					 current
		DESCRIPTION			 " -- "
		::=  { handoverInERABNbrEntry  7 }


	erabNbrHoIncQci6		 OBJECT-TYPE
		SYNTAX					 Counter32
		MAX-ACCESS			 read-only
		STATUS					 current
		DESCRIPTION			 " -- "
		::=  { handoverInERABNbrEntry  8 }


	erabNbrHoIncQci7		 OBJECT-TYPE
		SYNTAX					 Counter32
		MAX-ACCESS			 read-only
		STATUS					 current
		DESCRIPTION			 " -- "
		::=  { handoverInERABNbrEntry  9 }


	erabNbrHoIncQci8		 OBJECT-TYPE
		SYNTAX					 Counter32
		MAX-ACCESS			 read-only
		STATUS					 current
		DESCRIPTION			 " -- "
		::=  { handoverInERABNbrEntry  10 }


	erabNbrHoIncQci9		 OBJECT-TYPE
		SYNTAX					 Counter32
		MAX-ACCESS			 read-only
		STATUS					 current
		DESCRIPTION			 " -- "
		::=  { handoverInERABNbrEntry  11 }


	ueContextProcTable		 OBJECT-TYPE
		SYNTAX					 SEQUENCE  OF	 UeContextProcEntry
		MAX-ACCESS			 not-accessible
		STATUS					 current
		DESCRIPTION			 " -- "
		::=  { aprelatedOriginCounter  8 }


	ueContextProcEntry		 OBJECT-TYPE
		SYNTAX					 UeContextProcEntry
		MAX-ACCESS			 not-accessible
		STATUS					 current
		DESCRIPTION			 " -- "
		INDEX						{ ueContextProcLcId }
		::=  { ueContextProcTable  1 }


	UeContextProcEntry		 ::=  SEQUENCE {
		ueContextProcLcId					Integer32,
		ueContextProcRowStatus					RowStatus,
		contextFailInitalSetupNbrEnbUeS1apIdError					Counter32,
		contextFailInitalSetupNbrUeS1apIdPairError					Counter32,
		contextFailInitalSetupNbrInvalidQosComb					Counter32,
		contextFailInitalSetupNbrRadioInterfaceFail					Counter32,
		contextFailInitalSetupNbrMultipleErabId					Counter32,
		contextFailInitalSetupNbrAlgoNotSupported					Counter32,
		contextFailInitalSetupNbrTransResNotAvailable					Counter32,
		contextFailInitalSetupNbrTransferSyntaxError					Counter32,
		contextFailInitalSetupNbrAbstractSyntaxError					Counter32,
		contextFailInitalSetupNbrCPOverload					Counter32,
		contextFailInitalSetupNbrUnspecifiedFailure					Counter32,
		contextAttInitalSetupNbr					Counter32,
		contextSuccInitalSetupNbr					Counter32,
		contextFailModNbrUeS1apIdPairError					Counter32,
		contextFailModNbrRadioInterfaceFailure					Counter32,
		contextFailModNbrAlgoNotSupported					Counter32,
		contextFailModNbrTransferSyntaxError					Counter32,
		contextFailModNbrAbstractSyntaxError					Counter32,
		contextFailModNbrControlProcessingOverload					Counter32,
		contextFailModNbrUnspecifiedFailure					Counter32,
		contextAttModNbr					Counter32,
		contextSuccModNbr					Counter32,
		contextAttReleNBNbrUserInactivity					Counter32,
		contextAttReleNBNbrRadioInterfaceFailure					Counter32,
		contextAttReleNBNbrUnspecified					Counter32,
		contextAttRelMMENbrTransport					Counter32,
		contextAttRelMMENbrNormalRelease					Counter32,
		contextAttRelMMENbrDetach					Counter32,
		contextAttRelMMENbrUnspecifiedNas					Counter32,
		contextAttRelMMENbrProtocol					Counter32,
		contextAttRelMMENbrMiscellaneous					Counter32,
		contextAttRelMMENbrRadioNetworkLayer					Counter32,
		contextAttReleNBNbrCSFallbackTriggered					Counter32,
		contextAttReleNBNbrUENotAvailableforPS					Counter32,
		contextAttReleNBNbrInterRATRedirection					Counter32,
		contextAttReleNBNbrRedirectionto1xRTT					Counter32,
		contextAttReleNBNbrOMIntervention					Counter32,
		contextAttInitalSetupCsfb					Counter32,
		contextSuccInitalSetupCsfb					Counter32,
		contextAttModCsfb					Counter32,
		contextSuccModCsfb					Counter32,
		contextAttReleNBNbrUELostM1					Counter32,
		contextAttReleNBNbrUELostN					Counter32,
		contextAttReleNBNbrTransfer					Counter32,
		contextAttReleNBNbrCongestion					Counter32,
		contextAttRelMMENbrRadioNetworkLayerOther					Counter32,
		contextAttRelMMENbrUserInactivity					Counter32,
		contextAttRelMMENbrCSFallbackTriggered					Counter32,
		contextAttRelMMENbrUENotAvailableforPS					Counter32,
		contextAttRelMMENbrInterRATRedirection					Counter32,
		contextAttRelMMENbrRedirectionTowards1xRTT					Counter32,
		contextAttRelMMENbrRadioInterfaceFailure					Counter32,
		contextAttRelMMENbrUELost					Counter32,
		contextAttRelMMENbrCongestion					Counter32,
		contextAttRelMMENbrSucHO					Counter32,
		contextAttReleNBNbrUELostTa					Counter32,
		contextAttReleNBNbrUELostRlc					Counter32,
		contextAttReleNBNbrHoFail					Counter32,
		contextAttReleNBNbrReConfigFail					Counter32,
		contextAttReleNBNbrReEstabFail					Counter32
		}


	ueContextProcLcId		 OBJECT-TYPE
		SYNTAX					 Integer32( 0 .. 23 )
		MAX-ACCESS			 not-accessible
		STATUS					 current
		DESCRIPTION			 " -- "
		::=  { ueContextProcEntry  1 }


	ueContextProcRowStatus		 OBJECT-TYPE
		SYNTAX					 RowStatus
		MAX-ACCESS			 read-only
		STATUS					 current
		DESCRIPTION			 " -- "
		::=  { ueContextProcEntry  2 }


	contextFailInitalSetupNbrEnbUeS1apIdError		 OBJECT-TYPE
		SYNTAX					 Counter32
		MAX-ACCESS			 read-only
		STATUS					 current
		DESCRIPTION			 " -- "
		::=  { ueContextProcEntry  3 }


	contextFailInitalSetupNbrUeS1apIdPairError		 OBJECT-TYPE
		SYNTAX					 Counter32
		MAX-ACCESS			 read-only
		STATUS					 current
		DESCRIPTION			 " -- "
		::=  { ueContextProcEntry  4 }


	contextFailInitalSetupNbrInvalidQosComb		 OBJECT-TYPE
		SYNTAX					 Counter32
		MAX-ACCESS			 read-only
		STATUS					 current
		DESCRIPTION			 " -- "
		::=  { ueContextProcEntry  5 }


	contextFailInitalSetupNbrRadioInterfaceFail		 OBJECT-TYPE
		SYNTAX					 Counter32
		MAX-ACCESS			 read-only
		STATUS					 current
		DESCRIPTION			 " -- "
		::=  { ueContextProcEntry  6 }


	contextFailInitalSetupNbrMultipleErabId		 OBJECT-TYPE
		SYNTAX					 Counter32
		MAX-ACCESS			 read-only
		STATUS					 current
		DESCRIPTION			 " -- "
		::=  { ueContextProcEntry  7 }


	contextFailInitalSetupNbrAlgoNotSupported		 OBJECT-TYPE
		SYNTAX					 Counter32
		MAX-ACCESS			 read-only
		STATUS					 current
		DESCRIPTION			 " -- "
		::=  { ueContextProcEntry  8 }


	contextFailInitalSetupNbrTransResNotAvailable		 OBJECT-TYPE
		SYNTAX					 Counter32
		MAX-ACCESS			 read-only
		STATUS					 current
		DESCRIPTION			 " -- "
		::=  { ueContextProcEntry  9 }


	contextFailInitalSetupNbrTransferSyntaxError		 OBJECT-TYPE
		SYNTAX					 Counter32
		MAX-ACCESS			 read-only
		STATUS					 current
		DESCRIPTION			 " -- "
		::=  { ueContextProcEntry  10 }


	contextFailInitalSetupNbrAbstractSyntaxError		 OBJECT-TYPE
		SYNTAX					 Counter32
		MAX-ACCESS			 read-only
		STATUS					 current
		DESCRIPTION			 " -- "
		::=  { ueContextProcEntry  11 }


	contextFailInitalSetupNbrCPOverload		 OBJECT-TYPE
		SYNTAX					 Counter32
		MAX-ACCESS			 read-only
		STATUS					 current
		DESCRIPTION			 " -- "
		::=  { ueContextProcEntry  12 }


	contextFailInitalSetupNbrUnspecifiedFailure		 OBJECT-TYPE
		SYNTAX					 Counter32
		MAX-ACCESS			 read-only
		STATUS					 current
		DESCRIPTION			 " -- "
		::=  { ueContextProcEntry  13 }


	contextAttInitalSetupNbr		 OBJECT-TYPE
		SYNTAX					 Counter32
		MAX-ACCESS			 read-only
		STATUS					 current
		DESCRIPTION			 " -- "
		::=  { ueContextProcEntry  14 }


	contextSuccInitalSetupNbr		 OBJECT-TYPE
		SYNTAX					 Counter32
		MAX-ACCESS			 read-only
		STATUS					 current
		DESCRIPTION			 " -- "
		::=  { ueContextProcEntry  15 }


	contextFailModNbrUeS1apIdPairError		 OBJECT-TYPE
		SYNTAX					 Counter32
		MAX-ACCESS			 read-only
		STATUS					 current
		DESCRIPTION			 " -- "
		::=  { ueContextProcEntry  16 }


	contextFailModNbrRadioInterfaceFailure		 OBJECT-TYPE
		SYNTAX					 Counter32
		MAX-ACCESS			 read-only
		STATUS					 current
		DESCRIPTION			 " -- "
		::=  { ueContextProcEntry  17 }


	contextFailModNbrAlgoNotSupported		 OBJECT-TYPE
		SYNTAX					 Counter32
		MAX-ACCESS			 read-only
		STATUS					 current
		DESCRIPTION			 " -- "
		::=  { ueContextProcEntry  18 }


	contextFailModNbrTransferSyntaxError		 OBJECT-TYPE
		SYNTAX					 Counter32
		MAX-ACCESS			 read-only
		STATUS					 current
		DESCRIPTION			 " -- "
		::=  { ueContextProcEntry  19 }


	contextFailModNbrAbstractSyntaxError		 OBJECT-TYPE
		SYNTAX					 Counter32
		MAX-ACCESS			 read-only
		STATUS					 current
		DESCRIPTION			 " -- "
		::=  { ueContextProcEntry  20 }


	contextFailModNbrControlProcessingOverload		 OBJECT-TYPE
		SYNTAX					 Counter32
		MAX-ACCESS			 read-only
		STATUS					 current
		DESCRIPTION			 " -- "
		::=  { ueContextProcEntry  21 }


	contextFailModNbrUnspecifiedFailure		 OBJECT-TYPE
		SYNTAX					 Counter32
		MAX-ACCESS			 read-only
		STATUS					 current
		DESCRIPTION			 " -- "
		::=  { ueContextProcEntry  22 }


	contextAttModNbr		 OBJECT-TYPE
		SYNTAX					 Counter32
		MAX-ACCESS			 read-only
		STATUS					 current
		DESCRIPTION			 " -- "
		::=  { ueContextProcEntry  23 }


	contextSuccModNbr		 OBJECT-TYPE
		SYNTAX					 Counter32
		MAX-ACCESS			 read-only
		STATUS					 current
		DESCRIPTION			 " -- "
		::=  { ueContextProcEntry  24 }


	contextAttReleNBNbrUserInactivity		 OBJECT-TYPE
		SYNTAX					 Counter32
		MAX-ACCESS			 read-only
		STATUS					 current
		DESCRIPTION			 " -- "
		::=  { ueContextProcEntry  25 }


	contextAttReleNBNbrRadioInterfaceFailure		 OBJECT-TYPE
		SYNTAX					 Counter32
		MAX-ACCESS			 read-only
		STATUS					 current
		DESCRIPTION			 " -- "
		::=  { ueContextProcEntry  26 }


	contextAttReleNBNbrUnspecified		 OBJECT-TYPE
		SYNTAX					 Counter32
		MAX-ACCESS			 read-only
		STATUS					 current
		DESCRIPTION			 " -- "
		::=  { ueContextProcEntry  27 }


	contextAttRelMMENbrTransport		 OBJECT-TYPE
		SYNTAX					 Counter32
		MAX-ACCESS			 read-only
		STATUS					 current
		DESCRIPTION			 " -- "
		::=  { ueContextProcEntry  28 }


	contextAttRelMMENbrNormalRelease		 OBJECT-TYPE
		SYNTAX					 Counter32
		MAX-ACCESS			 read-only
		STATUS					 current
		DESCRIPTION			 " -- "
		::=  { ueContextProcEntry  29 }


	contextAttRelMMENbrDetach		 OBJECT-TYPE
		SYNTAX					 Counter32
		MAX-ACCESS			 read-only
		STATUS					 current
		DESCRIPTION			 " -- "
		::=  { ueContextProcEntry  30 }


	contextAttRelMMENbrUnspecifiedNas		 OBJECT-TYPE
		SYNTAX					 Counter32
		MAX-ACCESS			 read-only
		STATUS					 current
		DESCRIPTION			 " -- "
		::=  { ueContextProcEntry  31 }


	contextAttRelMMENbrProtocol		 OBJECT-TYPE
		SYNTAX					 Counter32
		MAX-ACCESS			 read-only
		STATUS					 current
		DESCRIPTION			 " -- "
		::=  { ueContextProcEntry  32 }


	contextAttRelMMENbrMiscellaneous		 OBJECT-TYPE
		SYNTAX					 Counter32
		MAX-ACCESS			 read-only
		STATUS					 current
		DESCRIPTION			 " -- "
		::=  { ueContextProcEntry  33 }


	contextAttRelMMENbrRadioNetworkLayer		 OBJECT-TYPE
		SYNTAX					 Counter32
		MAX-ACCESS			 read-only
		STATUS					 current
		DESCRIPTION			 " -- "
		::=  { ueContextProcEntry  34 }


	contextAttReleNBNbrCSFallbackTriggered		 OBJECT-TYPE
		SYNTAX					 Counter32
		MAX-ACCESS			 read-only
		STATUS					 current
		DESCRIPTION			 " -- "
		::=  { ueContextProcEntry  35 }


	contextAttReleNBNbrUENotAvailableforPS		 OBJECT-TYPE
		SYNTAX					 Counter32
		MAX-ACCESS			 read-only
		STATUS					 current
		DESCRIPTION			 " -- "
		::=  { ueContextProcEntry  36 }


	contextAttReleNBNbrInterRATRedirection		 OBJECT-TYPE
		SYNTAX					 Counter32
		MAX-ACCESS			 read-only
		STATUS					 current
		DESCRIPTION			 " -- "
		::=  { ueContextProcEntry  37 }


	contextAttReleNBNbrRedirectionto1xRTT		 OBJECT-TYPE
		SYNTAX					 Counter32
		MAX-ACCESS			 read-only
		STATUS					 current
		DESCRIPTION			 " -- "
		::=  { ueContextProcEntry  38 }


	contextAttReleNBNbrOMIntervention		 OBJECT-TYPE
		SYNTAX					 Counter32
		MAX-ACCESS			 read-only
		STATUS					 current
		DESCRIPTION			 " -- "
		::=  { ueContextProcEntry  39 }


	contextAttInitalSetupCsfb		 OBJECT-TYPE
		SYNTAX					 Counter32
		MAX-ACCESS			 read-only
		STATUS					 current
		DESCRIPTION			 " -- "
		::=  { ueContextProcEntry  40 }


	contextSuccInitalSetupCsfb		 OBJECT-TYPE
		SYNTAX					 Counter32
		MAX-ACCESS			 read-only
		STATUS					 current
		DESCRIPTION			 " -- "
		::=  { ueContextProcEntry  41 }


	contextAttModCsfb		 OBJECT-TYPE
		SYNTAX					 Counter32
		MAX-ACCESS			 read-only
		STATUS					 current
		DESCRIPTION			 " -- "
		::=  { ueContextProcEntry  42 }


	contextSuccModCsfb		 OBJECT-TYPE
		SYNTAX					 Counter32
		MAX-ACCESS			 read-only
		STATUS					 current
		DESCRIPTION			 " -- "
		::=  { ueContextProcEntry  43 }


	contextAttReleNBNbrUELostM1		 OBJECT-TYPE
		SYNTAX					 Counter32
		MAX-ACCESS			 read-only
		STATUS					 current
		DESCRIPTION			 " -- "
		::=  { ueContextProcEntry  44 }


	contextAttReleNBNbrUELostN		 OBJECT-TYPE
		SYNTAX					 Counter32
		MAX-ACCESS			 read-only
		STATUS					 current
		DESCRIPTION			 " -- "
		::=  { ueContextProcEntry  45 }


	contextAttReleNBNbrTransfer		 OBJECT-TYPE
		SYNTAX					 Counter32
		MAX-ACCESS			 read-only
		STATUS					 current
		DESCRIPTION			 " -- "
		::=  { ueContextProcEntry  46 }


	contextAttReleNBNbrCongestion		 OBJECT-TYPE
		SYNTAX					 Counter32
		MAX-ACCESS			 read-only
		STATUS					 current
		DESCRIPTION			 " -- "
		::=  { ueContextProcEntry  47 }


	contextAttRelMMENbrRadioNetworkLayerOther		 OBJECT-TYPE
		SYNTAX					 Counter32
		MAX-ACCESS			 read-only
		STATUS					 current
		DESCRIPTION			 " -- "
		::=  { ueContextProcEntry  48 }


	contextAttRelMMENbrUserInactivity		 OBJECT-TYPE
		SYNTAX					 Counter32
		MAX-ACCESS			 read-only
		STATUS					 current
		DESCRIPTION			 " -- "
		::=  { ueContextProcEntry  49 }


	contextAttRelMMENbrCSFallbackTriggered		 OBJECT-TYPE
		SYNTAX					 Counter32
		MAX-ACCESS			 read-only
		STATUS					 current
		DESCRIPTION			 " -- "
		::=  { ueContextProcEntry  50 }


	contextAttRelMMENbrUENotAvailableforPS		 OBJECT-TYPE
		SYNTAX					 Counter32
		MAX-ACCESS			 read-only
		STATUS					 current
		DESCRIPTION			 " -- "
		::=  { ueContextProcEntry  51 }


	contextAttRelMMENbrInterRATRedirection		 OBJECT-TYPE
		SYNTAX					 Counter32
		MAX-ACCESS			 read-only
		STATUS					 current
		DESCRIPTION			 " -- "
		::=  { ueContextProcEntry  52 }


	contextAttRelMMENbrRedirectionTowards1xRTT		 OBJECT-TYPE
		SYNTAX					 Counter32
		MAX-ACCESS			 read-only
		STATUS					 current
		DESCRIPTION			 " -- "
		::=  { ueContextProcEntry  53 }


	contextAttRelMMENbrRadioInterfaceFailure		 OBJECT-TYPE
		SYNTAX					 Counter32
		MAX-ACCESS			 read-only
		STATUS					 current
		DESCRIPTION			 " -- "
		::=  { ueContextProcEntry  54 }


	contextAttRelMMENbrUELost		 OBJECT-TYPE
		SYNTAX					 Counter32
		MAX-ACCESS			 read-only
		STATUS					 current
		DESCRIPTION			 " -- "
		::=  { ueContextProcEntry  55 }


	contextAttRelMMENbrCongestion		 OBJECT-TYPE
		SYNTAX					 Counter32
		MAX-ACCESS			 read-only
		STATUS					 current
		DESCRIPTION			 " -- "
		::=  { ueContextProcEntry  56 }


	contextAttRelMMENbrSucHO		 OBJECT-TYPE
		SYNTAX					 Counter32
		MAX-ACCESS			 read-only
		STATUS					 current
		DESCRIPTION			 " -- "
		::=  { ueContextProcEntry  57 }


	contextAttReleNBNbrUELostTa		 OBJECT-TYPE
		SYNTAX					 Counter32
		MAX-ACCESS			 read-only
		STATUS					 current
		DESCRIPTION			 " -- "
		::=  { ueContextProcEntry  58 }


	contextAttReleNBNbrUELostRlc		 OBJECT-TYPE
		SYNTAX					 Counter32
		MAX-ACCESS			 read-only
		STATUS					 current
		DESCRIPTION			 " -- "
		::=  { ueContextProcEntry  59 }


	contextAttReleNBNbrHoFail		 OBJECT-TYPE
		SYNTAX					 Counter32
		MAX-ACCESS			 read-only
		STATUS					 current
		DESCRIPTION			 " -- "
		::=  { ueContextProcEntry  60 }


	contextAttReleNBNbrReConfigFail		 OBJECT-TYPE
		SYNTAX					 Counter32
		MAX-ACCESS			 read-only
		STATUS					 current
		DESCRIPTION			 " -- "
		::=  { ueContextProcEntry  61 }


	contextAttReleNBNbrReEstabFail		 OBJECT-TYPE
		SYNTAX					 Counter32
		MAX-ACCESS			 read-only
		STATUS					 current
		DESCRIPTION			 " -- "
		::=  { ueContextProcEntry  62 }


	s1SigProcTable		 OBJECT-TYPE
		SYNTAX					 SEQUENCE  OF	 S1SigProcEntry
		MAX-ACCESS			 not-accessible
		STATUS					 current
		DESCRIPTION			 " -- "
		::=  { aprelatedOriginCounter  9 }


	s1SigProcEntry		 OBJECT-TYPE
		SYNTAX					 S1SigProcEntry
		MAX-ACCESS			 not-accessible
		STATUS					 current
		DESCRIPTION			 " -- "
		INDEX						{ s1SigProcLcId }
		::=  { s1SigProcTable  1 }


	S1SigProcEntry		 ::=  SEQUENCE {
		s1SigProcLcId					Integer32,
		s1SigProcRowStatus					RowStatus,
		s1sigConnEstabAtt					Counter32,
		s1sigConnEstabSucc					Counter32
		}


	s1SigProcLcId		 OBJECT-TYPE
		SYNTAX					 Integer32( 0 .. 23 )
		MAX-ACCESS			 not-accessible
		STATUS					 current
		DESCRIPTION			 " -- "
		::=  { s1SigProcEntry  1 }


	s1SigProcRowStatus		 OBJECT-TYPE
		SYNTAX					 RowStatus
		MAX-ACCESS			 read-only
		STATUS					 current
		DESCRIPTION			 " -- "
		::=  { s1SigProcEntry  2 }


	s1sigConnEstabAtt		 OBJECT-TYPE
		SYNTAX					 Counter32
		MAX-ACCESS			 read-only
		STATUS					 current
		DESCRIPTION			 " -- "
		::=  { s1SigProcEntry  3 }


	s1sigConnEstabSucc		 OBJECT-TYPE
		SYNTAX					 Counter32
		MAX-ACCESS			 read-only
		STATUS					 current
		DESCRIPTION			 " -- "
		::=  { s1SigProcEntry  4 }


	s1Conn		 OBJECT IDENTIFIER
		::=  { aprelatedOriginCounter  10 }


	s1FailSetupNbrTransferSyntaxError		 OBJECT-TYPE
		SYNTAX					 Counter32
		MAX-ACCESS			 read-only
		STATUS					 current
		DESCRIPTION			 " -- "
		::=  { s1Conn  1 }


	s1FailSetupNbrAbstractSyntaxError		 OBJECT-TYPE
		SYNTAX					 Counter32
		MAX-ACCESS			 read-only
		STATUS					 current
		DESCRIPTION			 " -- "
		::=  { s1Conn  2 }


	s1FailSetupNbrControlProcessingOverload		 OBJECT-TYPE
		SYNTAX					 Counter32
		MAX-ACCESS			 read-only
		STATUS					 current
		DESCRIPTION			 " -- "
		::=  { s1Conn  3 }


	s1FailSetupNbrUserPlaneResourcesNotEnough		 OBJECT-TYPE
		SYNTAX					 Counter32
		MAX-ACCESS			 read-only
		STATUS					 current
		DESCRIPTION			 " -- "
		::=  { s1Conn  4 }


	s1FailSetupNbrHardwareFailure		 OBJECT-TYPE
		SYNTAX					 Counter32
		MAX-ACCESS			 read-only
		STATUS					 current
		DESCRIPTION			 " -- "
		::=  { s1Conn  5 }


	s1FailSetupNbrUnspecifiedFailure		 OBJECT-TYPE
		SYNTAX					 Counter32
		MAX-ACCESS			 read-only
		STATUS					 current
		DESCRIPTION			 " -- "
		::=  { s1Conn  6 }


	s1AttSetupNbr		 OBJECT-TYPE
		SYNTAX					 Counter32
		MAX-ACCESS			 read-only
		STATUS					 current
		DESCRIPTION			 " -- "
		::=  { s1Conn  7 }


	s1SuccSetupNbr		 OBJECT-TYPE
		SYNTAX					 Counter32
		MAX-ACCESS			 read-only
		STATUS					 current
		DESCRIPTION			 " -- "
		::=  { s1Conn  8 }


	s1ErrorIndicatByeNBMmeUeS1apIdError		 OBJECT-TYPE
		SYNTAX					 Counter32
		MAX-ACCESS			 read-only
		STATUS					 current
		DESCRIPTION			 " -- "
		::=  { s1Conn  9 }


	s1ErrorIndicatByeNBEnbUeS1apIdError		 OBJECT-TYPE
		SYNTAX					 Counter32
		MAX-ACCESS			 read-only
		STATUS					 current
		DESCRIPTION			 " -- "
		::=  { s1Conn  10 }


	s1ErrorIndicatByeNBUeS1apIdPairError		 OBJECT-TYPE
		SYNTAX					 Counter32
		MAX-ACCESS			 read-only
		STATUS					 current
		DESCRIPTION			 " -- "
		::=  { s1Conn  11 }


	s1ErrorIndicatByeNBTransferSyntaxError		 OBJECT-TYPE
		SYNTAX					 Counter32
		MAX-ACCESS			 read-only
		STATUS					 current
		DESCRIPTION			 " -- "
		::=  { s1Conn  12 }


	s1ErrorIndicatByeNBAbstractSyntaxError		 OBJECT-TYPE
		SYNTAX					 Counter32
		MAX-ACCESS			 read-only
		STATUS					 current
		DESCRIPTION			 " -- "
		::=  { s1Conn  13 }


	s1ErrorIndicatByMMETransport		 OBJECT-TYPE
		SYNTAX					 Counter32
		MAX-ACCESS			 read-only
		STATUS					 current
		DESCRIPTION			 " -- "
		::=  { s1Conn  14 }


	s1ErrorIndicatByMMENas		 OBJECT-TYPE
		SYNTAX					 Counter32
		MAX-ACCESS			 read-only
		STATUS					 current
		DESCRIPTION			 " -- "
		::=  { s1Conn  15 }


	s1ErrorIndicatByMMEProtocol		 OBJECT-TYPE
		SYNTAX					 Counter32
		MAX-ACCESS			 read-only
		STATUS					 current
		DESCRIPTION			 " -- "
		::=  { s1Conn  16 }


	s1ErrorIndicatByMMEMiscellaneous		 OBJECT-TYPE
		SYNTAX					 Counter32
		MAX-ACCESS			 read-only
		STATUS					 current
		DESCRIPTION			 " -- "
		::=  { s1Conn  17 }


	s1ResetByeNBReleaseDueToEutran		 OBJECT-TYPE
		SYNTAX					 Counter32
		MAX-ACCESS			 read-only
		STATUS					 current
		DESCRIPTION			 " -- "
		::=  { s1Conn  18 }


	s1ResetByeNBOMIntervention		 OBJECT-TYPE
		SYNTAX					 Counter32
		MAX-ACCESS			 read-only
		STATUS					 current
		DESCRIPTION			 " -- "
		::=  { s1Conn  19 }


	s1ResetByeNBHardwareFailure		 OBJECT-TYPE
		SYNTAX					 Counter32
		MAX-ACCESS			 read-only
		STATUS					 current
		DESCRIPTION			 " -- "
		::=  { s1Conn  20 }


	s1ResetByeNBUnspecifiedFailure		 OBJECT-TYPE
		SYNTAX					 Counter32
		MAX-ACCESS			 read-only
		STATUS					 current
		DESCRIPTION			 " -- "
		::=  { s1Conn  21 }


	s1SuccResetByeNB		 OBJECT-TYPE
		SYNTAX					 Counter32
		MAX-ACCESS			 read-only
		STATUS					 current
		DESCRIPTION			 " -- "
		::=  { s1Conn  22 }


	s1ResetByMMETransport		 OBJECT-TYPE
		SYNTAX					 Counter32
		MAX-ACCESS			 read-only
		STATUS					 current
		DESCRIPTION			 " -- "
		::=  { s1Conn  23 }


	s1ResetByMMENas		 OBJECT-TYPE
		SYNTAX					 Counter32
		MAX-ACCESS			 read-only
		STATUS					 current
		DESCRIPTION			 " -- "
		::=  { s1Conn  24 }


	s1ResetByMMEProtocol		 OBJECT-TYPE
		SYNTAX					 Counter32
		MAX-ACCESS			 read-only
		STATUS					 current
		DESCRIPTION			 " -- "
		::=  { s1Conn  25 }


	s1ResetByMMEMiscellaneous		 OBJECT-TYPE
		SYNTAX					 Counter32
		MAX-ACCESS			 read-only
		STATUS					 current
		DESCRIPTION			 " -- "
		::=  { s1Conn  26 }


	s1SuccResetByMME		 OBJECT-TYPE
		SYNTAX					 Counter32
		MAX-ACCESS			 read-only
		STATUS					 current
		DESCRIPTION			 " -- "
		::=  { s1Conn  27 }


	s1OverLoadMme		 OBJECT-TYPE
		SYNTAX					 Counter32
		MAX-ACCESS			 read-only
		STATUS					 current
		DESCRIPTION			 " -- "
		::=  { s1Conn  28 }


	x2AbnormalProc		 OBJECT IDENTIFIER
		::=  { aprelatedOriginCounter  11 }


	x2ErrorInd		 OBJECT-TYPE
		SYNTAX					 Counter32
		MAX-ACCESS			 read-only
		STATUS					 current
		DESCRIPTION			 " -- "
		::=  { x2AbnormalProc  1 }


	x2Reset		 OBJECT-TYPE
		SYNTAX					 Counter32
		MAX-ACCESS			 read-only
		STATUS					 current
		DESCRIPTION			 " -- "
		::=  { x2AbnormalProc  2 }


	erabRelProcByHOTable		 OBJECT-TYPE
		SYNTAX					 SEQUENCE  OF	 ErabRelProcByHOEntry
		MAX-ACCESS			 not-accessible
		STATUS					 current
		DESCRIPTION			 " -- "
		::=  { aprelatedOriginCounter  12 }


	erabRelProcByHOEntry		 OBJECT-TYPE
		SYNTAX					 ErabRelProcByHOEntry
		MAX-ACCESS			 not-accessible
		STATUS					 current
		DESCRIPTION			 " -- "
		INDEX						{ erabRelProcByHOLcId }
		::=  { erabRelProcByHOTable  1 }


	ErabRelProcByHOEntry		 ::=  SEQUENCE {
		erabRelProcByHOLcId					Integer32,
		erabRelProcByHORowStatus					RowStatus,
		erabNbrReqRelEnbByHOQCI1					Counter32,
		erabNbrReqRelEnbByHOQCI2					Counter32,
		erabNbrReqRelEnbByHOQCI3					Counter32,
		erabNbrReqRelEnbByHOQCI4					Counter32,
		erabNbrReqRelEnbByHOQCI5					Counter32,
		erabNbrReqRelEnbByHOQCI6					Counter32,
		erabNbrReqRelEnbByHOQCI7					Counter32,
		erabNbrReqRelEnbByHOQCI8					Counter32,
		erabNbrReqRelEnbByHOQCI9					Counter32
		}


	erabRelProcByHOLcId		 OBJECT-TYPE
		SYNTAX					 Integer32( 0 .. 23 )
		MAX-ACCESS			 not-accessible
		STATUS					 current
		DESCRIPTION			 " -- "
		::=  { erabRelProcByHOEntry  1 }


	erabRelProcByHORowStatus		 OBJECT-TYPE
		SYNTAX					 RowStatus
		MAX-ACCESS			 read-only
		STATUS					 current
		DESCRIPTION			 " -- "
		::=  { erabRelProcByHOEntry  2 }


	erabNbrReqRelEnbByHOQCI1		 OBJECT-TYPE
		SYNTAX					 Counter32
		MAX-ACCESS			 read-only
		STATUS					 current
		DESCRIPTION			 " -- "
		::=  { erabRelProcByHOEntry  3 }


	erabNbrReqRelEnbByHOQCI2		 OBJECT-TYPE
		SYNTAX					 Counter32
		MAX-ACCESS			 read-only
		STATUS					 current
		DESCRIPTION			 " -- "
		::=  { erabRelProcByHOEntry  4 }


	erabNbrReqRelEnbByHOQCI3		 OBJECT-TYPE
		SYNTAX					 Counter32
		MAX-ACCESS			 read-only
		STATUS					 current
		DESCRIPTION			 " -- "
		::=  { erabRelProcByHOEntry  5 }


	erabNbrReqRelEnbByHOQCI4		 OBJECT-TYPE
		SYNTAX					 Counter32
		MAX-ACCESS			 read-only
		STATUS					 current
		DESCRIPTION			 " -- "
		::=  { erabRelProcByHOEntry  6 }


	erabNbrReqRelEnbByHOQCI5		 OBJECT-TYPE
		SYNTAX					 Counter32
		MAX-ACCESS			 read-only
		STATUS					 current
		DESCRIPTION			 " -- "
		::=  { erabRelProcByHOEntry  7 }


	erabNbrReqRelEnbByHOQCI6		 OBJECT-TYPE
		SYNTAX					 Counter32
		MAX-ACCESS			 read-only
		STATUS					 current
		DESCRIPTION			 " -- "
		::=  { erabRelProcByHOEntry  8 }


	erabNbrReqRelEnbByHOQCI7		 OBJECT-TYPE
		SYNTAX					 Counter32
		MAX-ACCESS			 read-only
		STATUS					 current
		DESCRIPTION			 " -- "
		::=  { erabRelProcByHOEntry  9 }


	erabNbrReqRelEnbByHOQCI8		 OBJECT-TYPE
		SYNTAX					 Counter32
		MAX-ACCESS			 read-only
		STATUS					 current
		DESCRIPTION			 " -- "
		::=  { erabRelProcByHOEntry  10 }


	erabNbrReqRelEnbByHOQCI9		 OBJECT-TYPE
		SYNTAX					 Counter32
		MAX-ACCESS			 read-only
		STATUS					 current
		DESCRIPTION			 " -- "
		::=  { erabRelProcByHOEntry  11 }


	erabExistNbrTable		 OBJECT-TYPE
		SYNTAX					 SEQUENCE  OF	 ErabExistNbrEntry
		MAX-ACCESS			 not-accessible
		STATUS					 current
		DESCRIPTION			 " -- "
		::=  { aprelatedOriginCounter  13 }


	erabExistNbrEntry		 OBJECT-TYPE
		SYNTAX					 ErabExistNbrEntry
		MAX-ACCESS			 not-accessible
		STATUS					 current
		DESCRIPTION			 " -- "
		INDEX						{ erabExistNbrLcId }
		::=  { erabExistNbrTable  1 }


	ErabExistNbrEntry		 ::=  SEQUENCE {
		erabExistNbrLcId					Integer32,
		erabExistNbrRowStatus					RowStatus,
		erabNbrExistQCI1					Counter32,
		erabNbrExistQCI2					Counter32,
		erabNbrExistQCI3					Counter32,
		erabNbrExistQCI4					Counter32,
		erabNbrExistQCI5					Counter32,
		erabNbrExistQCI6					Counter32,
		erabNbrExistQCI7					Counter32,
		erabNbrExistQCI8					Counter32,
		erabNbrExistQCI9					Counter32
		}


	erabExistNbrLcId		 OBJECT-TYPE
		SYNTAX					 Integer32( 0 .. 23 )
		MAX-ACCESS			 not-accessible
		STATUS					 current
		DESCRIPTION			 " -- "
		::=  { erabExistNbrEntry  1 }


	erabExistNbrRowStatus		 OBJECT-TYPE
		SYNTAX					 RowStatus
		MAX-ACCESS			 read-only
		STATUS					 current
		DESCRIPTION			 " -- "
		::=  { erabExistNbrEntry  2 }


	erabNbrExistQCI1		 OBJECT-TYPE
		SYNTAX					 Counter32
		MAX-ACCESS			 read-only
		STATUS					 current
		DESCRIPTION			 " -- "
		::=  { erabExistNbrEntry  3 }


	erabNbrExistQCI2		 OBJECT-TYPE
		SYNTAX					 Counter32
		MAX-ACCESS			 read-only
		STATUS					 current
		DESCRIPTION			 " -- "
		::=  { erabExistNbrEntry  4 }


	erabNbrExistQCI3		 OBJECT-TYPE
		SYNTAX					 Counter32
		MAX-ACCESS			 read-only
		STATUS					 current
		DESCRIPTION			 " -- "
		::=  { erabExistNbrEntry  5 }


	erabNbrExistQCI4		 OBJECT-TYPE
		SYNTAX					 Counter32
		MAX-ACCESS			 read-only
		STATUS					 current
		DESCRIPTION			 " -- "
		::=  { erabExistNbrEntry  6 }


	erabNbrExistQCI5		 OBJECT-TYPE
		SYNTAX					 Counter32
		MAX-ACCESS			 read-only
		STATUS					 current
		DESCRIPTION			 " -- "
		::=  { erabExistNbrEntry  7 }


	erabNbrExistQCI6		 OBJECT-TYPE
		SYNTAX					 Counter32
		MAX-ACCESS			 read-only
		STATUS					 current
		DESCRIPTION			 " -- "
		::=  { erabExistNbrEntry  8 }


	erabNbrExistQCI7		 OBJECT-TYPE
		SYNTAX					 Counter32
		MAX-ACCESS			 read-only
		STATUS					 current
		DESCRIPTION			 " -- "
		::=  { erabExistNbrEntry  9 }


	erabNbrExistQCI8		 OBJECT-TYPE
		SYNTAX					 Counter32
		MAX-ACCESS			 read-only
		STATUS					 current
		DESCRIPTION			 " -- "
		::=  { erabExistNbrEntry  10 }


	erabNbrExistQCI9		 OBJECT-TYPE
		SYNTAX					 Counter32
		MAX-ACCESS			 read-only
		STATUS					 current
		DESCRIPTION			 " -- "
		::=  { erabExistNbrEntry  11 }


	erabReleNBTable		 OBJECT-TYPE
		SYNTAX					 SEQUENCE  OF	 ErabReleNBEntry
		MAX-ACCESS			 not-accessible
		STATUS					 current
		DESCRIPTION			 " -- "
		::=  { aprelatedOriginCounter  14 }


	erabReleNBEntry		 OBJECT-TYPE
		SYNTAX					 ErabReleNBEntry
		MAX-ACCESS			 not-accessible
		STATUS					 current
		DESCRIPTION			 " -- "
		INDEX						{ erabReleNBLcId }
		::=  { erabReleNBTable  1 }


	ErabReleNBEntry		 ::=  SEQUENCE {
		erabReleNBLcId					Integer32,
		erabReleNBRowStatus					RowStatus,
		erabNormRelEnbNbrQci1					Counter32,
		erabNormRelEnbNbrQci2					Counter32,
		erabNormRelEnbNbrQci3					Counter32,
		erabNormRelEnbNbrQci4					Counter32,
		erabNormRelEnbNbrQci5					Counter32,
		erabNormRelEnbNbrQci6					Counter32,
		erabNormRelEnbNbrQci7					Counter32,
		erabNormRelEnbNbrQci8					Counter32,
		erabNormRelEnbNbrQci9					Counter32,
		erabNbrReqRelEnbQci1					Counter32,
		erabNbrReqRelEnbQci2					Counter32,
		erabNbrReqRelEnbQci3					Counter32,
		erabNbrReqRelEnbQci4					Counter32,
		erabNbrReqRelEnbQci5					Counter32,
		erabNbrReqRelEnbQci6					Counter32,
		erabNbrReqRelEnbQci7					Counter32,
		erabNbrReqRelEnbQci8					Counter32,
		erabNbrReqRelEnbQci9					Counter32,
		erabRelEnbNbrQci1UserInactivity					Counter32,
		erabRelEnbNbrQci1RadioInterfaceFailure					Counter32,
		erabRelEnbNbrQci1UELost					Counter32,
		erabRelEnbNbrQci1PdcpNotRcvSn					Counter32,
		erabRelEnbNbrQci1Other					Counter32,
		erabRelMmeNbrQci1NormalRelease					Counter32,
		erabRelMmeNbrQci1Other					Counter32,
		erabRelEnbNbrQci1Transfer					Counter32,
		erabRelEnbNbrQci1Congestion					Counter32,
		erabRelEnbNbrQci1HoFail					Counter32,
		erabRelEnbNbrQci1ReConfigFail					Counter32,
		erabRelEnbNbrQci1ReEstabFail					Counter32,
		erabRelMmeNbrQci1HoSuccess					Counter32,
		erabRelMmeNbrQci1Detech					Counter32,
		erabRelMmeNbrQci1Transfer					Counter32,
		erabRelMmeNbrQci1RadioNetwork					Counter32
		}


	erabReleNBLcId		 OBJECT-TYPE
		SYNTAX					 Integer32( 0 .. 23 )
		MAX-ACCESS			 not-accessible
		STATUS					 current
		DESCRIPTION			 " -- "
		::=  { erabReleNBEntry  1 }


	erabReleNBRowStatus		 OBJECT-TYPE
		SYNTAX					 RowStatus
		MAX-ACCESS			 read-only
		STATUS					 current
		DESCRIPTION			 " -- "
		::=  { erabReleNBEntry  2 }


	erabNormRelEnbNbrQci1		 OBJECT-TYPE
		SYNTAX					 Counter32
		MAX-ACCESS			 read-only
		STATUS					 current
		DESCRIPTION			 " -- "
		::=  { erabReleNBEntry  3 }


	erabNormRelEnbNbrQci2		 OBJECT-TYPE
		SYNTAX					 Counter32
		MAX-ACCESS			 read-only
		STATUS					 current
		DESCRIPTION			 " -- "
		::=  { erabReleNBEntry  4 }


	erabNormRelEnbNbrQci3		 OBJECT-TYPE
		SYNTAX					 Counter32
		MAX-ACCESS			 read-only
		STATUS					 current
		DESCRIPTION			 " -- "
		::=  { erabReleNBEntry  5 }


	erabNormRelEnbNbrQci4		 OBJECT-TYPE
		SYNTAX					 Counter32
		MAX-ACCESS			 read-only
		STATUS					 current
		DESCRIPTION			 " -- "
		::=  { erabReleNBEntry  6 }


	erabNormRelEnbNbrQci5		 OBJECT-TYPE
		SYNTAX					 Counter32
		MAX-ACCESS			 read-only
		STATUS					 current
		DESCRIPTION			 " -- "
		::=  { erabReleNBEntry  7 }


	erabNormRelEnbNbrQci6		 OBJECT-TYPE
		SYNTAX					 Counter32
		MAX-ACCESS			 read-only
		STATUS					 current
		DESCRIPTION			 " -- "
		::=  { erabReleNBEntry  8 }


	erabNormRelEnbNbrQci7		 OBJECT-TYPE
		SYNTAX					 Counter32
		MAX-ACCESS			 read-only
		STATUS					 current
		DESCRIPTION			 " -- "
		::=  { erabReleNBEntry  9 }


	erabNormRelEnbNbrQci8		 OBJECT-TYPE
		SYNTAX					 Counter32
		MAX-ACCESS			 read-only
		STATUS					 current
		DESCRIPTION			 " -- "
		::=  { erabReleNBEntry  10 }


	erabNormRelEnbNbrQci9		 OBJECT-TYPE
		SYNTAX					 Counter32
		MAX-ACCESS			 read-only
		STATUS					 current
		DESCRIPTION			 " -- "
		::=  { erabReleNBEntry  11 }


	erabNbrReqRelEnbQci1		 OBJECT-TYPE
		SYNTAX					 Counter32
		MAX-ACCESS			 read-only
		STATUS					 current
		DESCRIPTION			 " -- "
		::=  { erabReleNBEntry  12 }


	erabNbrReqRelEnbQci2		 OBJECT-TYPE
		SYNTAX					 Counter32
		MAX-ACCESS			 read-only
		STATUS					 current
		DESCRIPTION			 " -- "
		::=  { erabReleNBEntry  13 }


	erabNbrReqRelEnbQci3		 OBJECT-TYPE
		SYNTAX					 Counter32
		MAX-ACCESS			 read-only
		STATUS					 current
		DESCRIPTION			 " -- "
		::=  { erabReleNBEntry  14 }


	erabNbrReqRelEnbQci4		 OBJECT-TYPE
		SYNTAX					 Counter32
		MAX-ACCESS			 read-only
		STATUS					 current
		DESCRIPTION			 " -- "
		::=  { erabReleNBEntry  15 }


	erabNbrReqRelEnbQci5		 OBJECT-TYPE
		SYNTAX					 Counter32
		MAX-ACCESS			 read-only
		STATUS					 current
		DESCRIPTION			 " -- "
		::=  { erabReleNBEntry  16 }


	erabNbrReqRelEnbQci6		 OBJECT-TYPE
		SYNTAX					 Counter32
		MAX-ACCESS			 read-only
		STATUS					 current
		DESCRIPTION			 " -- "
		::=  { erabReleNBEntry  17 }


	erabNbrReqRelEnbQci7		 OBJECT-TYPE
		SYNTAX					 Counter32
		MAX-ACCESS			 read-only
		STATUS					 current
		DESCRIPTION			 " -- "
		::=  { erabReleNBEntry  18 }


	erabNbrReqRelEnbQci8		 OBJECT-TYPE
		SYNTAX					 Counter32
		MAX-ACCESS			 read-only
		STATUS					 current
		DESCRIPTION			 " -- "
		::=  { erabReleNBEntry  19 }


	erabNbrReqRelEnbQci9		 OBJECT-TYPE
		SYNTAX					 Counter32
		MAX-ACCESS			 read-only
		STATUS					 current
		DESCRIPTION			 " -- "
		::=  { erabReleNBEntry  20 }


	erabRelEnbNbrQci1UserInactivity		 OBJECT-TYPE
		SYNTAX					 Counter32
		MAX-ACCESS			 read-only
		STATUS					 current
		DESCRIPTION			 " -- "
		::=  { erabReleNBEntry  21 }


	erabRelEnbNbrQci1RadioInterfaceFailure		 OBJECT-TYPE
		SYNTAX					 Counter32
		MAX-ACCESS			 read-only
		STATUS					 current
		DESCRIPTION			 " -- "
		::=  { erabReleNBEntry  22 }


	erabRelEnbNbrQci1UELost		 OBJECT-TYPE
		SYNTAX					 Counter32
		MAX-ACCESS			 read-only
		STATUS					 current
		DESCRIPTION			 " -- "
		::=  { erabReleNBEntry  23 }


	erabRelEnbNbrQci1PdcpNotRcvSn		 OBJECT-TYPE
		SYNTAX					 Counter32
		MAX-ACCESS			 read-only
		STATUS					 current
		DESCRIPTION			 " -- "
		::=  { erabReleNBEntry  24 }


	erabRelEnbNbrQci1Other		 OBJECT-TYPE
		SYNTAX					 Counter32
		MAX-ACCESS			 read-only
		STATUS					 current
		DESCRIPTION			 " -- "
		::=  { erabReleNBEntry  25 }


	erabRelMmeNbrQci1NormalRelease		 OBJECT-TYPE
		SYNTAX					 Counter32
		MAX-ACCESS			 read-only
		STATUS					 current
		DESCRIPTION			 " -- "
		::=  { erabReleNBEntry  26 }


	erabRelMmeNbrQci1Other		 OBJECT-TYPE
		SYNTAX					 Counter32
		MAX-ACCESS			 read-only
		STATUS					 current
		DESCRIPTION			 " -- "
		::=  { erabReleNBEntry  27 }


	erabRelEnbNbrQci1Transfer		 OBJECT-TYPE
		SYNTAX					 Counter32
		MAX-ACCESS			 read-only
		STATUS					 current
		DESCRIPTION			 " -- "
		::=  { erabReleNBEntry  28 }


	erabRelEnbNbrQci1Congestion		 OBJECT-TYPE
		SYNTAX					 Counter32
		MAX-ACCESS			 read-only
		STATUS					 current
		DESCRIPTION			 " -- "
		::=  { erabReleNBEntry  29 }


	erabRelEnbNbrQci1HoFail		 OBJECT-TYPE
		SYNTAX					 Counter32
		MAX-ACCESS			 read-only
		STATUS					 current
		DESCRIPTION			 " -- "
		::=  { erabReleNBEntry  30 }


	erabRelEnbNbrQci1ReConfigFail		 OBJECT-TYPE
		SYNTAX					 Counter32
		MAX-ACCESS			 read-only
		STATUS					 current
		DESCRIPTION			 " -- "
		::=  { erabReleNBEntry  31 }


	erabRelEnbNbrQci1ReEstabFail		 OBJECT-TYPE
		SYNTAX					 Counter32
		MAX-ACCESS			 read-only
		STATUS					 current
		DESCRIPTION			 " -- "
		::=  { erabReleNBEntry  32 }


	erabRelMmeNbrQci1HoSuccess		 OBJECT-TYPE
		SYNTAX					 Counter32
		MAX-ACCESS			 read-only
		STATUS					 current
		DESCRIPTION			 " -- "
		::=  { erabReleNBEntry  33 }


	erabRelMmeNbrQci1Detech		 OBJECT-TYPE
		SYNTAX					 Counter32
		MAX-ACCESS			 read-only
		STATUS					 current
		DESCRIPTION			 " -- "
		::=  { erabReleNBEntry  34 }


	erabRelMmeNbrQci1Transfer		 OBJECT-TYPE
		SYNTAX					 Counter32
		MAX-ACCESS			 read-only
		STATUS					 current
		DESCRIPTION			 " -- "
		::=  { erabReleNBEntry  35 }


	erabRelMmeNbrQci1RadioNetwork		 OBJECT-TYPE
		SYNTAX					 Counter32
		MAX-ACCESS			 read-only
		STATUS					 current
		DESCRIPTION			 " -- "
		::=  { erabReleNBEntry  36 }


	contextExistNbrTable		 OBJECT-TYPE
		SYNTAX					 SEQUENCE  OF	 ContextExistNbrEntry
		MAX-ACCESS			 not-accessible
		STATUS					 current
		DESCRIPTION			 " -- "
		::=  { aprelatedOriginCounter  15 }


	contextExistNbrEntry		 OBJECT-TYPE
		SYNTAX					 ContextExistNbrEntry
		MAX-ACCESS			 not-accessible
		STATUS					 current
		DESCRIPTION			 " -- "
		INDEX						{ contextExistNbrLcId }
		::=  { contextExistNbrTable  1 }


	ContextExistNbrEntry		 ::=  SEQUENCE {
		contextExistNbrLcId					Integer32,
		contextExistNbrRowStatus					RowStatus,
		contextNbrExist					Counter32
		}


	contextExistNbrLcId		 OBJECT-TYPE
		SYNTAX					 Integer32( 0 .. 23 )
		MAX-ACCESS			 not-accessible
		STATUS					 current
		DESCRIPTION			 " -- "
		::=  { contextExistNbrEntry  1 }


	contextExistNbrRowStatus		 OBJECT-TYPE
		SYNTAX					 RowStatus
		MAX-ACCESS			 read-only
		STATUS					 current
		DESCRIPTION			 " -- "
		::=  { contextExistNbrEntry  2 }


	contextNbrExist		 OBJECT-TYPE
		SYNTAX					 Counter32
		MAX-ACCESS			 read-only
		STATUS					 current
		DESCRIPTION			 " -- "
		::=  { contextExistNbrEntry  3 }


	s1PathSwichTable		 OBJECT-TYPE
		SYNTAX					 SEQUENCE  OF	 S1PathSwichEntry
		MAX-ACCESS			 not-accessible
		STATUS					 current
		DESCRIPTION			 " -- "
		::=  { aprelatedOriginCounter  16 }


	s1PathSwichEntry		 OBJECT-TYPE
		SYNTAX					 S1PathSwichEntry
		MAX-ACCESS			 not-accessible
		STATUS					 current
		DESCRIPTION			 " -- "
		INDEX						{ s1PathSwichLcId }
		::=  { s1PathSwichTable  1 }


	S1PathSwichEntry		 ::=  SEQUENCE {
		s1PathSwichLcId					Integer32,
		s1PathSwichRowStatus					RowStatus,
		s1PathSwichReq					Counter32,
		s1PathSwichFail					Counter32,
		s1PathSwichNoResp					Counter32
		}


	s1PathSwichLcId		 OBJECT-TYPE
		SYNTAX					 Integer32( 0 .. 23 )
		MAX-ACCESS			 not-accessible
		STATUS					 current
		DESCRIPTION			 " -- "
		::=  { s1PathSwichEntry  1 }


	s1PathSwichRowStatus		 OBJECT-TYPE
		SYNTAX					 RowStatus
		MAX-ACCESS			 read-only
		STATUS					 current
		DESCRIPTION			 " -- "
		::=  { s1PathSwichEntry  2 }


	s1PathSwichReq		 OBJECT-TYPE
		SYNTAX					 Counter32
		MAX-ACCESS			 read-only
		STATUS					 current
		DESCRIPTION			 " -- "
		::=  { s1PathSwichEntry  3 }


	s1PathSwichFail		 OBJECT-TYPE
		SYNTAX					 Counter32
		MAX-ACCESS			 read-only
		STATUS					 current
		DESCRIPTION			 " -- "
		::=  { s1PathSwichEntry  4 }


	s1PathSwichNoResp		 OBJECT-TYPE
		SYNTAX					 Counter32
		MAX-ACCESS			 read-only
		STATUS					 current
		DESCRIPTION			 " -- "
		::=  { s1PathSwichEntry  5 }


	rrcConnNumberOfeNB		 OBJECT IDENTIFIER
		::=  { aprelatedOriginCounter  17 }


	rrcConnMaxeNB		 OBJECT-TYPE
		SYNTAX					 Counter32
		MAX-ACCESS			 read-only
		STATUS					 current
		DESCRIPTION			 " -- "
		::=  { rrcConnNumberOfeNB  1 }


	rrcConnMeaneNB		 OBJECT-TYPE
		SYNTAX					 Counter32
		MAX-ACCESS			 read-only
		STATUS					 current
		DESCRIPTION			 " -- "
		::=  { rrcConnNumberOfeNB  2 }


	erabEstabProcOfRUETable		 OBJECT-TYPE
		SYNTAX					 SEQUENCE  OF	 ErabEstabProcOfRUEEntry
		MAX-ACCESS			 not-accessible
		STATUS					 current
		DESCRIPTION			 " -- "
		::=  { aprelatedOriginCounter  18 }


	erabEstabProcOfRUEEntry		 OBJECT-TYPE
		SYNTAX					 ErabEstabProcOfRUEEntry
		MAX-ACCESS			 not-accessible
		STATUS					 current
		DESCRIPTION			 " -- "
		INDEX						{ erabEstabProcOfRUELcId }
		::=  { erabEstabProcOfRUETable  1 }


	ErabEstabProcOfRUEEntry		 ::=  SEQUENCE {
		erabEstabProcOfRUELcId					Integer32,
		erabEstabProcOfRUERowStatus					RowStatus,
		erabEstabAttNbrQci251					Counter32,
		erabEstabAttNbrQci252					Counter32,
		erabEstabAttNbrQci253					Counter32,
		erabEstabAttNbrQci254					Counter32,
		erabEstabSuccNbrQci251					Counter32,
		erabEstabSuccNbrQci252					Counter32,
		erabEstabSuccNbrQci253					Counter32,
		erabEstabSuccNbrQci254					Counter32
		}


	erabEstabProcOfRUELcId		 OBJECT-TYPE
		SYNTAX					 Integer32( 0 .. 23 )
		MAX-ACCESS			 not-accessible
		STATUS					 current
		DESCRIPTION			 " -- "
		::=  { erabEstabProcOfRUEEntry  1 }


	erabEstabProcOfRUERowStatus		 OBJECT-TYPE
		SYNTAX					 RowStatus
		MAX-ACCESS			 read-only
		STATUS					 current
		DESCRIPTION			 " -- "
		::=  { erabEstabProcOfRUEEntry  2 }


	erabEstabAttNbrQci251		 OBJECT-TYPE
		SYNTAX					 Counter32
		MAX-ACCESS			 read-only
		STATUS					 current
		DESCRIPTION			 " -- "
		::=  { erabEstabProcOfRUEEntry  3 }


	erabEstabAttNbrQci252		 OBJECT-TYPE
		SYNTAX					 Counter32
		MAX-ACCESS			 read-only
		STATUS					 current
		DESCRIPTION			 " -- "
		::=  { erabEstabProcOfRUEEntry  4 }


	erabEstabAttNbrQci253		 OBJECT-TYPE
		SYNTAX					 Counter32
		MAX-ACCESS			 read-only
		STATUS					 current
		DESCRIPTION			 " -- "
		::=  { erabEstabProcOfRUEEntry  5 }


	erabEstabAttNbrQci254		 OBJECT-TYPE
		SYNTAX					 Counter32
		MAX-ACCESS			 read-only
		STATUS					 current
		DESCRIPTION			 " -- "
		::=  { erabEstabProcOfRUEEntry  6 }


	erabEstabSuccNbrQci251		 OBJECT-TYPE
		SYNTAX					 Counter32
		MAX-ACCESS			 read-only
		STATUS					 current
		DESCRIPTION			 " -- "
		::=  { erabEstabProcOfRUEEntry  7 }


	erabEstabSuccNbrQci252		 OBJECT-TYPE
		SYNTAX					 Counter32
		MAX-ACCESS			 read-only
		STATUS					 current
		DESCRIPTION			 " -- "
		::=  { erabEstabProcOfRUEEntry  8 }


	erabEstabSuccNbrQci253		 OBJECT-TYPE
		SYNTAX					 Counter32
		MAX-ACCESS			 read-only
		STATUS					 current
		DESCRIPTION			 " -- "
		::=  { erabEstabProcOfRUEEntry  9 }


	erabEstabSuccNbrQci254		 OBJECT-TYPE
		SYNTAX					 Counter32
		MAX-ACCESS			 read-only
		STATUS					 current
		DESCRIPTION			 " -- "
		::=  { erabEstabProcOfRUEEntry  10 }


	handOverInterWithERABTable		 OBJECT-TYPE
		SYNTAX					 SEQUENCE  OF	 HandOverInterWithERABEntry
		MAX-ACCESS			 not-accessible
		STATUS					 current
		DESCRIPTION			 " -- "
		::=  { aprelatedOriginCounter  19 }


	handOverInterWithERABEntry		 OBJECT-TYPE
		SYNTAX					 HandOverInterWithERABEntry
		MAX-ACCESS			 not-accessible
		STATUS					 current
		DESCRIPTION			 " -- "
		INDEX						{ handOverInterWithERABLcId }
		::=  { handOverInterWithERABTable  1 }


	HandOverInterWithERABEntry		 ::=  SEQUENCE {
		handOverInterWithERABLcId					Integer32,
		handOverInterWithERABRowStatus					RowStatus,
		apHoInteractWithErabSetupInterNBFail					Counter32,
		apHoInteractWithEraSetupIntraNB					Counter32,
		apHoInteractWithErabModInterNBFail					Counter32,
		apHoInteractWithEraModIntraNB					Counter32,
		apHoInteractWithErabDelInterNBFail					Counter32,
		apHoInteractWithEraDelIntraNB					Counter32
		}


	handOverInterWithERABLcId		 OBJECT-TYPE
		SYNTAX					 Integer32( 0 .. 23 )
		MAX-ACCESS			 not-accessible
		STATUS					 current
		DESCRIPTION			 " -- "
		::=  { handOverInterWithERABEntry  1 }


	handOverInterWithERABRowStatus		 OBJECT-TYPE
		SYNTAX					 RowStatus
		MAX-ACCESS			 read-only
		STATUS					 current
		DESCRIPTION			 " -- "
		::=  { handOverInterWithERABEntry  2 }


	apHoInteractWithErabSetupInterNBFail		 OBJECT-TYPE
		SYNTAX					 Counter32
		MAX-ACCESS			 read-only
		STATUS					 current
		DESCRIPTION			 " -- "
		::=  { handOverInterWithERABEntry  3 }


	apHoInteractWithEraSetupIntraNB		 OBJECT-TYPE
		SYNTAX					 Counter32
		MAX-ACCESS			 read-only
		STATUS					 current
		DESCRIPTION			 " -- "
		::=  { handOverInterWithERABEntry  4 }


	apHoInteractWithErabModInterNBFail		 OBJECT-TYPE
		SYNTAX					 Counter32
		MAX-ACCESS			 read-only
		STATUS					 current
		DESCRIPTION			 " -- "
		::=  { handOverInterWithERABEntry  5 }


	apHoInteractWithEraModIntraNB		 OBJECT-TYPE
		SYNTAX					 Counter32
		MAX-ACCESS			 read-only
		STATUS					 current
		DESCRIPTION			 " -- "
		::=  { handOverInterWithERABEntry  6 }


	apHoInteractWithErabDelInterNBFail		 OBJECT-TYPE
		SYNTAX					 Counter32
		MAX-ACCESS			 read-only
		STATUS					 current
		DESCRIPTION			 " -- "
		::=  { handOverInterWithERABEntry  7 }


	apHoInteractWithEraDelIntraNB		 OBJECT-TYPE
		SYNTAX					 Counter32
		MAX-ACCESS			 read-only
		STATUS					 current
		DESCRIPTION			 " -- "
		::=  { handOverInterWithERABEntry  8 }


	apCAndRCheckOfCellTable		 OBJECT-TYPE
		SYNTAX					 SEQUENCE  OF	 ApCAndRCheckOfCellEntry
		MAX-ACCESS			 not-accessible
		STATUS					 current
		DESCRIPTION			 " -- "
		::=  { aprelatedOriginCounter  20 }


	apCAndRCheckOfCellEntry		 OBJECT-TYPE
		SYNTAX					 ApCAndRCheckOfCellEntry
		MAX-ACCESS			 not-accessible
		STATUS					 current
		DESCRIPTION			 " -- "
		INDEX						{ apCAndRCheckOfCellLcId }
		::=  { apCAndRCheckOfCellTable  1 }


	ApCAndRCheckOfCellEntry		 ::=  SEQUENCE {
		apCAndRCheckOfCellLcId					Integer32,
		apCAndRCheckOfCellRowStatus					RowStatus,
		apErabRel					Counter32,
		apSwitchErabResourceRel					Counter32,
		apTeidRel					Counter32,
		apX2apIdRel					Counter32
		}


	apCAndRCheckOfCellLcId		 OBJECT-TYPE
		SYNTAX					 Integer32( 0 .. 23 )
		MAX-ACCESS			 not-accessible
		STATUS					 current
		DESCRIPTION			 " -- "
		::=  { apCAndRCheckOfCellEntry  1 }


	apCAndRCheckOfCellRowStatus		 OBJECT-TYPE
		SYNTAX					 RowStatus
		MAX-ACCESS			 read-only
		STATUS					 current
		DESCRIPTION			 " -- "
		::=  { apCAndRCheckOfCellEntry  2 }


	apErabRel		 OBJECT-TYPE
		SYNTAX					 Counter32
		MAX-ACCESS			 read-only
		STATUS					 current
		DESCRIPTION			 " -- "
		::=  { apCAndRCheckOfCellEntry  3 }


	apSwitchErabResourceRel		 OBJECT-TYPE
		SYNTAX					 Counter32
		MAX-ACCESS			 read-only
		STATUS					 current
		DESCRIPTION			 " -- "
		::=  { apCAndRCheckOfCellEntry  4 }


	apTeidRel		 OBJECT-TYPE
		SYNTAX					 Counter32
		MAX-ACCESS			 read-only
		STATUS					 current
		DESCRIPTION			 " -- "
		::=  { apCAndRCheckOfCellEntry  5 }


	apX2apIdRel		 OBJECT-TYPE
		SYNTAX					 Counter32
		MAX-ACCESS			 read-only
		STATUS					 current
		DESCRIPTION			 " -- "
		::=  { apCAndRCheckOfCellEntry  6 }


	apCAndRCheckOfEnb		 OBJECT IDENTIFIER
		::=  { aprelatedOriginCounter  21 }


	apTeidMapRel		 OBJECT-TYPE
		SYNTAX					 Counter32
		MAX-ACCESS			 read-only
		STATUS					 current
		DESCRIPTION			 " -- "
		::=  { apCAndRCheckOfEnb  1 }


	apS1apRelP0		 OBJECT-TYPE
		SYNTAX					 Counter32
		MAX-ACCESS			 read-only
		STATUS					 current
		DESCRIPTION			 " -- "
		::=  { apCAndRCheckOfEnb  2 }


	apS1apRelP2		 OBJECT-TYPE
		SYNTAX					 Counter32
		MAX-ACCESS			 read-only
		STATUS					 current
		DESCRIPTION			 " -- "
		::=  { apCAndRCheckOfEnb  3 }


	apS1apRelP3		 OBJECT-TYPE
		SYNTAX					 Counter32
		MAX-ACCESS			 read-only
		STATUS					 current
		DESCRIPTION			 " -- "
		::=  { apCAndRCheckOfEnb  4 }


	apS1apRelP4		 OBJECT-TYPE
		SYNTAX					 Counter32
		MAX-ACCESS			 read-only
		STATUS					 current
		DESCRIPTION			 " -- "
		::=  { apCAndRCheckOfEnb  5 }


	apS1apRelP5		 OBJECT-TYPE
		SYNTAX					 Counter32
		MAX-ACCESS			 read-only
		STATUS					 current
		DESCRIPTION			 " -- "
		::=  { apCAndRCheckOfEnb  6 }


	apS1apRelP6		 OBJECT-TYPE
		SYNTAX					 Counter32
		MAX-ACCESS			 read-only
		STATUS					 current
		DESCRIPTION			 " -- "
		::=  { apCAndRCheckOfEnb  7 }


	apS1apRelP7		 OBJECT-TYPE
		SYNTAX					 Counter32
		MAX-ACCESS			 read-only
		STATUS					 current
		DESCRIPTION			 " -- "
		::=  { apCAndRCheckOfEnb  8 }


	apS1apRelP8		 OBJECT-TYPE
		SYNTAX					 Counter32
		MAX-ACCESS			 read-only
		STATUS					 current
		DESCRIPTION			 " -- "
		::=  { apCAndRCheckOfEnb  9 }


	apS1apRelP9		 OBJECT-TYPE
		SYNTAX					 Counter32
		MAX-ACCESS			 read-only
		STATUS					 current
		DESCRIPTION			 " -- "
		::=  { apCAndRCheckOfEnb  10 }


	apS1apRelP10		 OBJECT-TYPE
		SYNTAX					 Counter32
		MAX-ACCESS			 read-only
		STATUS					 current
		DESCRIPTION			 " -- "
		::=  { apCAndRCheckOfEnb  11 }


	apX2apRelP0		 OBJECT-TYPE
		SYNTAX					 Counter32
		MAX-ACCESS			 read-only
		STATUS					 current
		DESCRIPTION			 " -- "
		::=  { apCAndRCheckOfEnb  12 }


	apX2apRelP2		 OBJECT-TYPE
		SYNTAX					 Counter32
		MAX-ACCESS			 read-only
		STATUS					 current
		DESCRIPTION			 " -- "
		::=  { apCAndRCheckOfEnb  13 }


	apX2apRelP3		 OBJECT-TYPE
		SYNTAX					 Counter32
		MAX-ACCESS			 read-only
		STATUS					 current
		DESCRIPTION			 " -- "
		::=  { apCAndRCheckOfEnb  14 }


	apX2apRelP4		 OBJECT-TYPE
		SYNTAX					 Counter32
		MAX-ACCESS			 read-only
		STATUS					 current
		DESCRIPTION			 " -- "
		::=  { apCAndRCheckOfEnb  15 }


	apX2apRelP5		 OBJECT-TYPE
		SYNTAX					 Counter32
		MAX-ACCESS			 read-only
		STATUS					 current
		DESCRIPTION			 " -- "
		::=  { apCAndRCheckOfEnb  16 }


	apX2apRelP6		 OBJECT-TYPE
		SYNTAX					 Counter32
		MAX-ACCESS			 read-only
		STATUS					 current
		DESCRIPTION			 " -- "
		::=  { apCAndRCheckOfEnb  17 }


	apX2apRelP7		 OBJECT-TYPE
		SYNTAX					 Counter32
		MAX-ACCESS			 read-only
		STATUS					 current
		DESCRIPTION			 " -- "
		::=  { apCAndRCheckOfEnb  18 }


	apX2apRelP8		 OBJECT-TYPE
		SYNTAX					 Counter32
		MAX-ACCESS			 read-only
		STATUS					 current
		DESCRIPTION			 " -- "
		::=  { apCAndRCheckOfEnb  19 }


	apX2apRelP9		 OBJECT-TYPE
		SYNTAX					 Counter32
		MAX-ACCESS			 read-only
		STATUS					 current
		DESCRIPTION			 " -- "
		::=  { apCAndRCheckOfEnb  20 }


	apX2apRelP10		 OBJECT-TYPE
		SYNTAX					 Counter32
		MAX-ACCESS			 read-only
		STATUS					 current
		DESCRIPTION			 " -- "
		::=  { apCAndRCheckOfEnb  21 }


	apPmofeNB		 OBJECT IDENTIFIER
		::=  { aprelatedOriginCounter  22 }


	apConnReEstabInterEnbScRecRlf		 OBJECT-TYPE
		SYNTAX					 Counter32
		MAX-ACCESS			 read-only
		STATUS					 current
		DESCRIPTION			 " -- "
		::=  { apPmofeNB  1 }


	apConnReEstabInterEnbScfailClose		 OBJECT-TYPE
		SYNTAX					 Counter32
		MAX-ACCESS			 read-only
		STATUS					 current
		DESCRIPTION			 " -- "
		::=  { apPmofeNB  2 }


	macrelatedOriginCounter		 OBJECT IDENTIFIER
		::=  { pmOriginCounterGrpInfo  3 }


	macPrbUtilizationCCTable		 OBJECT-TYPE
		SYNTAX					 SEQUENCE  OF	 MacPrbUtilizationCCEntry
		MAX-ACCESS			 not-accessible
		STATUS					 current
		DESCRIPTION			 " -- "
		::=  { macrelatedOriginCounter  1 }


	macPrbUtilizationCCEntry		 OBJECT-TYPE
		SYNTAX					 MacPrbUtilizationCCEntry
		MAX-ACCESS			 not-accessible
		STATUS					 current
		DESCRIPTION			 " -- "
		INDEX						{ macPrbUtilizationCCLcId }
		::=  { macPrbUtilizationCCTable  1 }


	MacPrbUtilizationCCEntry		 ::=  SEQUENCE {
		macPrbUtilizationCCLcId					Integer32,
		macPrbUtilizationCCRowStatus					RowStatus,
		rruPrbUlTotalNum					Counter32,
		rruPrbUlUsedNum					Counter32,
		rruPrbUlQci1Num					Counter32,
		rruPrbUlQci2Num					Counter32,
		rruPrbUlQci3Num					Counter32,
		rruPrbUlQci4Num					Counter32,
		rruPrbUlQci5Num					Counter32,
		rruPrbUlQci6Num					Counter32,
		rruPrbUlQci7Num					Counter32,
		rruPrbUlQci8Num					Counter32,
		rruPrbUlQci9Num					Counter32,
		rruPrbDlTotalNum					Counter32,
		rruPrbDlUsedNum					Counter32,
		rruPrbDlQci1Num					Counter32,
		rruPrbDlQci2Num					Counter32,
		rruPrbDlQci3Num					Counter32,
		rruPrbDlQci4Num					Counter32,
		rruPrbDlQci5Num					Counter32,
		rruPrbDlQci6Num					Counter32,
		rruPrbDlQci7Num					Counter32,
		rruPrbDlQci8Num					Counter32,
		rruPrbDlQci9Num					Counter32,
		rruUlDcheTimes					Counter32,
		rruDlDcheTimes					Counter32,
		rruEffectiveScheTimesUl					Counter32,
		rruEffectiveScheTimesDl					Counter32,
		rruTheorScheTimesUl					Counter32,
		rruTheorScheTimesDl					Counter32,
		rruPrbDlRank2UsedNum					Counter32,
		rruPrbUlMumimoUsedNum					Counter32,
		macPreSchPrbNumUL					Counter32,
		macPreSchNumUL					Counter32,
		rruPrbPucchUsedNum					Counter32,
		rruFreqSelPrbPuschUsedNum					Counter32,
		rruFreqSelPrbPdschUsedNum					Counter32,
		macPrbUsedNumULHighSpeedUser					Counter32,
		macPrbUsedNumULLowSpeedUser					Counter32,
		macPrbUsedNumDLHighSpeedUser					Counter32,
		macPrbUsedNumDLLowSpeedUser					Counter32,
		macPreSchRealPrbNumUL					Counter32,
		macPreReSchNumUL					Counter32,
		macPreLowMCSSchNumUL					Counter32,
		rruFullRbTtiTotUl					Counter32,
		rruFullRbTtiTotDl					Counter32,
		rruDtchPrbAssnMeanUIEnb					Counter32,
		rruDtchPrbAssnMeanDlEnb					Counter32,
		rruPrbTotUlEnb					Counter32,
		rruPrbTotDlEnb					Counter32,
		rruPuschPrbMeanTotUl					Counter32,
		rruPdschPrbMeanTotDl					Counter32,
		rruEffectiveDataTransTimeUl					Counter32,
		rruEffectiveDataTransTimeDl					Counter32
		}


	macPrbUtilizationCCLcId		 OBJECT-TYPE
		SYNTAX					 Integer32( 0 .. 23 )
		MAX-ACCESS			 not-accessible
		STATUS					 current
		DESCRIPTION			 " -- "
		::=  { macPrbUtilizationCCEntry  1 }


	macPrbUtilizationCCRowStatus		 OBJECT-TYPE
		SYNTAX					 RowStatus
		MAX-ACCESS			 read-only
		STATUS					 current
		DESCRIPTION			 " -- "
		::=  { macPrbUtilizationCCEntry  2 }


	rruPrbUlTotalNum		 OBJECT-TYPE
		SYNTAX					 Counter32
		MAX-ACCESS			 read-only
		STATUS					 current
		DESCRIPTION			 " -- "
		::=  { macPrbUtilizationCCEntry  3 }


	rruPrbUlUsedNum		 OBJECT-TYPE
		SYNTAX					 Counter32
		MAX-ACCESS			 read-only
		STATUS					 current
		DESCRIPTION			 " -- "
		::=  { macPrbUtilizationCCEntry  4 }


	rruPrbUlQci1Num		 OBJECT-TYPE
		SYNTAX					 Counter32
		MAX-ACCESS			 read-only
		STATUS					 current
		DESCRIPTION			 " -- "
		::=  { macPrbUtilizationCCEntry  5 }


	rruPrbUlQci2Num		 OBJECT-TYPE
		SYNTAX					 Counter32
		MAX-ACCESS			 read-only
		STATUS					 current
		DESCRIPTION			 " -- "
		::=  { macPrbUtilizationCCEntry  6 }


	rruPrbUlQci3Num		 OBJECT-TYPE
		SYNTAX					 Counter32
		MAX-ACCESS			 read-only
		STATUS					 current
		DESCRIPTION			 " -- "
		::=  { macPrbUtilizationCCEntry  7 }


	rruPrbUlQci4Num		 OBJECT-TYPE
		SYNTAX					 Counter32
		MAX-ACCESS			 read-only
		STATUS					 current
		DESCRIPTION			 " -- "
		::=  { macPrbUtilizationCCEntry  8 }


	rruPrbUlQci5Num		 OBJECT-TYPE
		SYNTAX					 Counter32
		MAX-ACCESS			 read-only
		STATUS					 current
		DESCRIPTION			 " -- "
		::=  { macPrbUtilizationCCEntry  9 }


	rruPrbUlQci6Num		 OBJECT-TYPE
		SYNTAX					 Counter32
		MAX-ACCESS			 read-only
		STATUS					 current
		DESCRIPTION			 " -- "
		::=  { macPrbUtilizationCCEntry  10 }


	rruPrbUlQci7Num		 OBJECT-TYPE
		SYNTAX					 Counter32
		MAX-ACCESS			 read-only
		STATUS					 current
		DESCRIPTION			 " -- "
		::=  { macPrbUtilizationCCEntry  11 }


	rruPrbUlQci8Num		 OBJECT-TYPE
		SYNTAX					 Counter32
		MAX-ACCESS			 read-only
		STATUS					 current
		DESCRIPTION			 " -- "
		::=  { macPrbUtilizationCCEntry  12 }


	rruPrbUlQci9Num		 OBJECT-TYPE
		SYNTAX					 Counter32
		MAX-ACCESS			 read-only
		STATUS					 current
		DESCRIPTION			 " -- "
		::=  { macPrbUtilizationCCEntry  13 }


	rruPrbDlTotalNum		 OBJECT-TYPE
		SYNTAX					 Counter32
		MAX-ACCESS			 read-only
		STATUS					 current
		DESCRIPTION			 " -- "
		::=  { macPrbUtilizationCCEntry  14 }


	rruPrbDlUsedNum		 OBJECT-TYPE
		SYNTAX					 Counter32
		MAX-ACCESS			 read-only
		STATUS					 current
		DESCRIPTION			 " -- "
		::=  { macPrbUtilizationCCEntry  15 }


	rruPrbDlQci1Num		 OBJECT-TYPE
		SYNTAX					 Counter32
		MAX-ACCESS			 read-only
		STATUS					 current
		DESCRIPTION			 " -- "
		::=  { macPrbUtilizationCCEntry  16 }


	rruPrbDlQci2Num		 OBJECT-TYPE
		SYNTAX					 Counter32
		MAX-ACCESS			 read-only
		STATUS					 current
		DESCRIPTION			 " -- "
		::=  { macPrbUtilizationCCEntry  17 }


	rruPrbDlQci3Num		 OBJECT-TYPE
		SYNTAX					 Counter32
		MAX-ACCESS			 read-only
		STATUS					 current
		DESCRIPTION			 " -- "
		::=  { macPrbUtilizationCCEntry  18 }


	rruPrbDlQci4Num		 OBJECT-TYPE
		SYNTAX					 Counter32
		MAX-ACCESS			 read-only
		STATUS					 current
		DESCRIPTION			 " -- "
		::=  { macPrbUtilizationCCEntry  19 }


	rruPrbDlQci5Num		 OBJECT-TYPE
		SYNTAX					 Counter32
		MAX-ACCESS			 read-only
		STATUS					 current
		DESCRIPTION			 " -- "
		::=  { macPrbUtilizationCCEntry  20 }


	rruPrbDlQci6Num		 OBJECT-TYPE
		SYNTAX					 Counter32
		MAX-ACCESS			 read-only
		STATUS					 current
		DESCRIPTION			 " -- "
		::=  { macPrbUtilizationCCEntry  21 }


	rruPrbDlQci7Num		 OBJECT-TYPE
		SYNTAX					 Counter32
		MAX-ACCESS			 read-only
		STATUS					 current
		DESCRIPTION			 " -- "
		::=  { macPrbUtilizationCCEntry  22 }


	rruPrbDlQci8Num		 OBJECT-TYPE
		SYNTAX					 Counter32
		MAX-ACCESS			 read-only
		STATUS					 current
		DESCRIPTION			 " -- "
		::=  { macPrbUtilizationCCEntry  23 }


	rruPrbDlQci9Num		 OBJECT-TYPE
		SYNTAX					 Counter32
		MAX-ACCESS			 read-only
		STATUS					 current
		DESCRIPTION			 " -- "
		::=  { macPrbUtilizationCCEntry  24 }


	rruUlDcheTimes		 OBJECT-TYPE
		SYNTAX					 Counter32
		MAX-ACCESS			 read-only
		STATUS					 current
		DESCRIPTION			 " -- "
		::=  { macPrbUtilizationCCEntry  25 }


	rruDlDcheTimes		 OBJECT-TYPE
		SYNTAX					 Counter32
		MAX-ACCESS			 read-only
		STATUS					 current
		DESCRIPTION			 " -- "
		::=  { macPrbUtilizationCCEntry  26 }


	rruEffectiveScheTimesUl		 OBJECT-TYPE
		SYNTAX					 Counter32
		MAX-ACCESS			 read-only
		STATUS					 current
		DESCRIPTION			 " -- "
		::=  { macPrbUtilizationCCEntry  27 }


	rruEffectiveScheTimesDl		 OBJECT-TYPE
		SYNTAX					 Counter32
		MAX-ACCESS			 read-only
		STATUS					 current
		DESCRIPTION			 " -- "
		::=  { macPrbUtilizationCCEntry  28 }


	rruTheorScheTimesUl		 OBJECT-TYPE
		SYNTAX					 Counter32
		MAX-ACCESS			 read-only
		STATUS					 current
		DESCRIPTION			 " -- "
		::=  { macPrbUtilizationCCEntry  29 }


	rruTheorScheTimesDl		 OBJECT-TYPE
		SYNTAX					 Counter32
		MAX-ACCESS			 read-only
		STATUS					 current
		DESCRIPTION			 " -- "
		::=  { macPrbUtilizationCCEntry  30 }


	rruPrbDlRank2UsedNum		 OBJECT-TYPE
		SYNTAX					 Counter32
		MAX-ACCESS			 read-only
		STATUS					 current
		DESCRIPTION			 " -- "
		::=  { macPrbUtilizationCCEntry  31 }


	rruPrbUlMumimoUsedNum		 OBJECT-TYPE
		SYNTAX					 Counter32
		MAX-ACCESS			 read-only
		STATUS					 current
		DESCRIPTION			 " -- "
		::=  { macPrbUtilizationCCEntry  32 }


	macPreSchPrbNumUL		 OBJECT-TYPE
		SYNTAX					 Counter32
		MAX-ACCESS			 read-only
		STATUS					 current
		DESCRIPTION			 " -- "
		::=  { macPrbUtilizationCCEntry  33 }


	macPreSchNumUL		 OBJECT-TYPE
		SYNTAX					 Counter32
		MAX-ACCESS			 read-only
		STATUS					 current
		DESCRIPTION			 " -- "
		::=  { macPrbUtilizationCCEntry  34 }


	rruPrbPucchUsedNum		 OBJECT-TYPE
		SYNTAX					 Counter32
		MAX-ACCESS			 read-only
		STATUS					 current
		DESCRIPTION			 " -- "
		::=  { macPrbUtilizationCCEntry  35 }


	rruFreqSelPrbPuschUsedNum		 OBJECT-TYPE
		SYNTAX					 Counter32
		MAX-ACCESS			 read-only
		STATUS					 current
		DESCRIPTION			 " -- "
		::=  { macPrbUtilizationCCEntry  36 }


	rruFreqSelPrbPdschUsedNum		 OBJECT-TYPE
		SYNTAX					 Counter32
		MAX-ACCESS			 read-only
		STATUS					 current
		DESCRIPTION			 " -- "
		::=  { macPrbUtilizationCCEntry  37 }


	macPrbUsedNumULHighSpeedUser		 OBJECT-TYPE
		SYNTAX					 Counter32
		MAX-ACCESS			 read-only
		STATUS					 current
		DESCRIPTION			 " -- "
		::=  { macPrbUtilizationCCEntry  38 }


	macPrbUsedNumULLowSpeedUser		 OBJECT-TYPE
		SYNTAX					 Counter32
		MAX-ACCESS			 read-only
		STATUS					 current
		DESCRIPTION			 " -- "
		::=  { macPrbUtilizationCCEntry  39 }


	macPrbUsedNumDLHighSpeedUser		 OBJECT-TYPE
		SYNTAX					 Counter32
		MAX-ACCESS			 read-only
		STATUS					 current
		DESCRIPTION			 " -- "
		::=  { macPrbUtilizationCCEntry  40 }


	macPrbUsedNumDLLowSpeedUser		 OBJECT-TYPE
		SYNTAX					 Counter32
		MAX-ACCESS			 read-only
		STATUS					 current
		DESCRIPTION			 " -- "
		::=  { macPrbUtilizationCCEntry  41 }


	macPreSchRealPrbNumUL		 OBJECT-TYPE
		SYNTAX					 Counter32
		MAX-ACCESS			 read-only
		STATUS					 current
		DESCRIPTION			 " -- "
		::=  { macPrbUtilizationCCEntry  42 }


	macPreReSchNumUL		 OBJECT-TYPE
		SYNTAX					 Counter32
		MAX-ACCESS			 read-only
		STATUS					 current
		DESCRIPTION			 " -- "
		::=  { macPrbUtilizationCCEntry  43 }


	macPreLowMCSSchNumUL		 OBJECT-TYPE
		SYNTAX					 Counter32
		MAX-ACCESS			 read-only
		STATUS					 current
		DESCRIPTION			 " -- "
		::=  { macPrbUtilizationCCEntry  44 }


	rruFullRbTtiTotUl		 OBJECT-TYPE
		SYNTAX					 Counter32
		MAX-ACCESS			 read-only
		STATUS					 current
		DESCRIPTION			 " -- "
		::=  { macPrbUtilizationCCEntry  45 }


	rruFullRbTtiTotDl		 OBJECT-TYPE
		SYNTAX					 Counter32
		MAX-ACCESS			 read-only
		STATUS					 current
		DESCRIPTION			 " -- "
		::=  { macPrbUtilizationCCEntry  46 }


	rruDtchPrbAssnMeanUIEnb		 OBJECT-TYPE
		SYNTAX					 Counter32
		MAX-ACCESS			 read-only
		STATUS					 current
		DESCRIPTION			 " -- "
		::=  { macPrbUtilizationCCEntry  200 }


	rruDtchPrbAssnMeanDlEnb		 OBJECT-TYPE
		SYNTAX					 Counter32
		MAX-ACCESS			 read-only
		STATUS					 current
		DESCRIPTION			 " -- "
		::=  { macPrbUtilizationCCEntry  201 }


	rruPrbTotUlEnb		 OBJECT-TYPE
		SYNTAX					 Counter32
		MAX-ACCESS			 read-only
		STATUS					 current
		DESCRIPTION			 " -- "
		::=  { macPrbUtilizationCCEntry  202 }


	rruPrbTotDlEnb		 OBJECT-TYPE
		SYNTAX					 Counter32
		MAX-ACCESS			 read-only
		STATUS					 current
		DESCRIPTION			 " -- "
		::=  { macPrbUtilizationCCEntry  203 }


	rruPuschPrbMeanTotUl		 OBJECT-TYPE
		SYNTAX					 Counter32
		MAX-ACCESS			 read-only
		STATUS					 current
		DESCRIPTION			 " -- "
		::=  { macPrbUtilizationCCEntry  204 }


	rruPdschPrbMeanTotDl		 OBJECT-TYPE
		SYNTAX					 Counter32
		MAX-ACCESS			 read-only
		STATUS					 current
		DESCRIPTION			 " -- "
		::=  { macPrbUtilizationCCEntry  205 }


	rruEffectiveDataTransTimeUl		 OBJECT-TYPE
		SYNTAX					 Counter32
		MAX-ACCESS			 read-only
		STATUS					 current
		DESCRIPTION			 " -- "
		::=  { macPrbUtilizationCCEntry  206 }


	rruEffectiveDataTransTimeDl		 OBJECT-TYPE
		SYNTAX					 Counter32
		MAX-ACCESS			 read-only
		STATUS					 current
		DESCRIPTION			 " -- "
		::=  { macPrbUtilizationCCEntry  207 }


	macPrbUtilizationSITable		 OBJECT-TYPE
		SYNTAX					 SEQUENCE  OF	 MacPrbUtilizationSIEntry
		MAX-ACCESS			 not-accessible
		STATUS					 current
		DESCRIPTION			 " -- "
		::=  { macrelatedOriginCounter  2 }


	macPrbUtilizationSIEntry		 OBJECT-TYPE
		SYNTAX					 MacPrbUtilizationSIEntry
		MAX-ACCESS			 not-accessible
		STATUS					 current
		DESCRIPTION			 " -- "
		INDEX						{ macPrbUtilizationSILcId }
		::=  { macPrbUtilizationSITable  1 }


	MacPrbUtilizationSIEntry		 ::=  SEQUENCE {
		macPrbUtilizationSILcId					Integer32,
		macPrbUtilizationSIRowStatus					RowStatus,
		macPrbUtilizationUlMax					Counter32,
		macPrbUtilizationUlMin					Counter32,
		macPrbUtilizationUlAvaild					Counter32,
		macPrbUtilizationDlMax					Counter32,
		macPrbUtilizationDlMin					Counter32,
		macPrbUtilizationDlAvaild					Counter32
		}


	macPrbUtilizationSILcId		 OBJECT-TYPE
		SYNTAX					 Integer32( 0 .. 23 )
		MAX-ACCESS			 not-accessible
		STATUS					 current
		DESCRIPTION			 " -- "
		::=  { macPrbUtilizationSIEntry  1 }


	macPrbUtilizationSIRowStatus		 OBJECT-TYPE
		SYNTAX					 RowStatus
		MAX-ACCESS			 read-only
		STATUS					 current
		DESCRIPTION			 " -- "
		::=  { macPrbUtilizationSIEntry  2 }


	macPrbUtilizationUlMax		 OBJECT-TYPE
		SYNTAX					 Counter32
		MAX-ACCESS			 read-only
		STATUS					 current
		DESCRIPTION			 " -- "
		::=  { macPrbUtilizationSIEntry  3 }


	macPrbUtilizationUlMin		 OBJECT-TYPE
		SYNTAX					 Counter32
		MAX-ACCESS			 read-only
		STATUS					 current
		DESCRIPTION			 " -- "
		::=  { macPrbUtilizationSIEntry  4 }


	macPrbUtilizationUlAvaild		 OBJECT-TYPE
		SYNTAX					 Counter32
		MAX-ACCESS			 read-only
		STATUS					 current
		DESCRIPTION			 " -- "
		::=  { macPrbUtilizationSIEntry  5 }


	macPrbUtilizationDlMax		 OBJECT-TYPE
		SYNTAX					 Counter32
		MAX-ACCESS			 read-only
		STATUS					 current
		DESCRIPTION			 " -- "
		::=  { macPrbUtilizationSIEntry  6 }


	macPrbUtilizationDlMin		 OBJECT-TYPE
		SYNTAX					 Counter32
		MAX-ACCESS			 read-only
		STATUS					 current
		DESCRIPTION			 " -- "
		::=  { macPrbUtilizationSIEntry  7 }


	macPrbUtilizationDlAvaild		 OBJECT-TYPE
		SYNTAX					 Counter32
		MAX-ACCESS			 read-only
		STATUS					 current
		DESCRIPTION			 " -- "
		::=  { macPrbUtilizationSIEntry  8 }


	activeUETable		 OBJECT-TYPE
		SYNTAX					 SEQUENCE  OF	 ActiveUEEntry
		MAX-ACCESS			 not-accessible
		STATUS					 current
		DESCRIPTION			 " -- "
		::=  { macrelatedOriginCounter  3 }


	activeUEEntry		 OBJECT-TYPE
		SYNTAX					 ActiveUEEntry
		MAX-ACCESS			 not-accessible
		STATUS					 current
		DESCRIPTION			 " -- "
		INDEX						{ activeUELcId }
		::=  { activeUETable  1 }


	ActiveUEEntry		 ::=  SEQUENCE {
		activeUELcId					Integer32,
		activeUERowStatus					RowStatus,
		drbUEActiveDlQci1					Counter32,
		drbUEActiveDlQci2					Counter32,
		drbUEActiveDlQci3					Counter32,
		drbUEActiveDlQci4					Counter32,
		drbUEActiveDlQci5					Counter32,
		drbUEActiveDlQci6					Counter32,
		drbUEActiveDlQci7					Counter32,
		drbUEActiveDlQci8					Counter32,
		drbUEActiveDlQci9					Counter32,
		drbUEActiveUlQci1					Counter32,
		drbUEActiveUlQci2					Counter32,
		drbUEActiveUlQci3					Counter32,
		drbUEActiveUlQci4					Counter32,
		drbUEActiveUlQci5					Counter32,
		drbUEActiveUlQci6					Counter32,
		drbUEActiveUlQci7					Counter32,
		drbUEActiveUlQci8					Counter32,
		drbUEActiveUlQci9					Counter32,
		drbUEActiveDl					Counter32,
		drbUEActiveUl					Counter32,
		drbMaxUeActiveDl					Counter32,
		drbMaxUeActiveUl					Counter32
		}


	activeUELcId		 OBJECT-TYPE
		SYNTAX					 Integer32( 0 .. 23 )
		MAX-ACCESS			 not-accessible
		STATUS					 current
		DESCRIPTION			 " -- "
		::=  { activeUEEntry  1 }


	activeUERowStatus		 OBJECT-TYPE
		SYNTAX					 RowStatus
		MAX-ACCESS			 read-only
		STATUS					 current
		DESCRIPTION			 " -- "
		::=  { activeUEEntry  2 }


	drbUEActiveDlQci1		 OBJECT-TYPE
		SYNTAX					 Counter32
		MAX-ACCESS			 read-only
		STATUS					 current
		DESCRIPTION			 " -- "
		::=  { activeUEEntry  3 }


	drbUEActiveDlQci2		 OBJECT-TYPE
		SYNTAX					 Counter32
		MAX-ACCESS			 read-only
		STATUS					 current
		DESCRIPTION			 " -- "
		::=  { activeUEEntry  4 }


	drbUEActiveDlQci3		 OBJECT-TYPE
		SYNTAX					 Counter32
		MAX-ACCESS			 read-only
		STATUS					 current
		DESCRIPTION			 " -- "
		::=  { activeUEEntry  5 }


	drbUEActiveDlQci4		 OBJECT-TYPE
		SYNTAX					 Counter32
		MAX-ACCESS			 read-only
		STATUS					 current
		DESCRIPTION			 " -- "
		::=  { activeUEEntry  6 }


	drbUEActiveDlQci5		 OBJECT-TYPE
		SYNTAX					 Counter32
		MAX-ACCESS			 read-only
		STATUS					 current
		DESCRIPTION			 " -- "
		::=  { activeUEEntry  7 }


	drbUEActiveDlQci6		 OBJECT-TYPE
		SYNTAX					 Counter32
		MAX-ACCESS			 read-only
		STATUS					 current
		DESCRIPTION			 " -- "
		::=  { activeUEEntry  8 }


	drbUEActiveDlQci7		 OBJECT-TYPE
		SYNTAX					 Counter32
		MAX-ACCESS			 read-only
		STATUS					 current
		DESCRIPTION			 " -- "
		::=  { activeUEEntry  9 }


	drbUEActiveDlQci8		 OBJECT-TYPE
		SYNTAX					 Counter32
		MAX-ACCESS			 read-only
		STATUS					 current
		DESCRIPTION			 " -- "
		::=  { activeUEEntry  10 }


	drbUEActiveDlQci9		 OBJECT-TYPE
		SYNTAX					 Counter32
		MAX-ACCESS			 read-only
		STATUS					 current
		DESCRIPTION			 " -- "
		::=  { activeUEEntry  11 }


	drbUEActiveUlQci1		 OBJECT-TYPE
		SYNTAX					 Counter32
		MAX-ACCESS			 read-only
		STATUS					 current
		DESCRIPTION			 " -- "
		::=  { activeUEEntry  12 }


	drbUEActiveUlQci2		 OBJECT-TYPE
		SYNTAX					 Counter32
		MAX-ACCESS			 read-only
		STATUS					 current
		DESCRIPTION			 " -- "
		::=  { activeUEEntry  13 }


	drbUEActiveUlQci3		 OBJECT-TYPE
		SYNTAX					 Counter32
		MAX-ACCESS			 read-only
		STATUS					 current
		DESCRIPTION			 " -- "
		::=  { activeUEEntry  14 }


	drbUEActiveUlQci4		 OBJECT-TYPE
		SYNTAX					 Counter32
		MAX-ACCESS			 read-only
		STATUS					 current
		DESCRIPTION			 " -- "
		::=  { activeUEEntry  15 }


	drbUEActiveUlQci5		 OBJECT-TYPE
		SYNTAX					 Counter32
		MAX-ACCESS			 read-only
		STATUS					 current
		DESCRIPTION			 " -- "
		::=  { activeUEEntry  16 }


	drbUEActiveUlQci6		 OBJECT-TYPE
		SYNTAX					 Counter32
		MAX-ACCESS			 read-only
		STATUS					 current
		DESCRIPTION			 " -- "
		::=  { activeUEEntry  17 }


	drbUEActiveUlQci7		 OBJECT-TYPE
		SYNTAX					 Counter32
		MAX-ACCESS			 read-only
		STATUS					 current
		DESCRIPTION			 " -- "
		::=  { activeUEEntry  18 }


	drbUEActiveUlQci8		 OBJECT-TYPE
		SYNTAX					 Counter32
		MAX-ACCESS			 read-only
		STATUS					 current
		DESCRIPTION			 " -- "
		::=  { activeUEEntry  19 }


	drbUEActiveUlQci9		 OBJECT-TYPE
		SYNTAX					 Counter32
		MAX-ACCESS			 read-only
		STATUS					 current
		DESCRIPTION			 " -- "
		::=  { activeUEEntry  20 }


	drbUEActiveDl		 OBJECT-TYPE
		SYNTAX					 Counter32
		MAX-ACCESS			 read-only
		STATUS					 current
		DESCRIPTION			 " -- "
		::=  { activeUEEntry  21 }


	drbUEActiveUl		 OBJECT-TYPE
		SYNTAX					 Counter32
		MAX-ACCESS			 read-only
		STATUS					 current
		DESCRIPTION			 " -- "
		::=  { activeUEEntry  22 }


	drbMaxUeActiveDl		 OBJECT-TYPE
		SYNTAX					 Counter32
		MAX-ACCESS			 read-only
		STATUS					 current
		DESCRIPTION			 " -- "
		::=  { activeUEEntry  23 }


	drbMaxUeActiveUl		 OBJECT-TYPE
		SYNTAX					 Counter32
		MAX-ACCESS			 read-only
		STATUS					 current
		DESCRIPTION			 " -- "
		::=  { activeUEEntry  24 }


	releasedActiveERABTable		 OBJECT-TYPE
		SYNTAX					 SEQUENCE  OF	 ReleasedActiveERABEntry
		MAX-ACCESS			 not-accessible
		STATUS					 current
		DESCRIPTION			 " -- "
		::=  { macrelatedOriginCounter  4 }


	releasedActiveERABEntry		 OBJECT-TYPE
		SYNTAX					 ReleasedActiveERABEntry
		MAX-ACCESS			 not-accessible
		STATUS					 current
		DESCRIPTION			 " -- "
		INDEX						{ releasedActiveERABLcId }
		::=  { releasedActiveERABTable  1 }


	ReleasedActiveERABEntry		 ::=  SEQUENCE {
		releasedActiveERABLcId					Integer32,
		releasedActiveERABRowStatus					RowStatus,
		erabRelActNbrQci1					Counter32,
		erabRelActNbrQci2					Counter32,
		erabRelActNbrQci3					Counter32,
		erabRelActNbrQci4					Counter32,
		erabRelActNbrQci5					Counter32,
		erabRelActNbrQci6					Counter32,
		erabRelActNbrQci7					Counter32,
		erabRelActNbrQci8					Counter32,
		erabRelActNbrQci9					Counter32
		}


	releasedActiveERABLcId		 OBJECT-TYPE
		SYNTAX					 Integer32( 0 .. 23 )
		MAX-ACCESS			 not-accessible
		STATUS					 current
		DESCRIPTION			 " -- "
		::=  { releasedActiveERABEntry  1 }


	releasedActiveERABRowStatus		 OBJECT-TYPE
		SYNTAX					 RowStatus
		MAX-ACCESS			 read-only
		STATUS					 current
		DESCRIPTION			 " -- "
		::=  { releasedActiveERABEntry  2 }


	erabRelActNbrQci1		 OBJECT-TYPE
		SYNTAX					 Counter32
		MAX-ACCESS			 read-only
		STATUS					 current
		DESCRIPTION			 " -- "
		::=  { releasedActiveERABEntry  3 }


	erabRelActNbrQci2		 OBJECT-TYPE
		SYNTAX					 Counter32
		MAX-ACCESS			 read-only
		STATUS					 current
		DESCRIPTION			 " -- "
		::=  { releasedActiveERABEntry  4 }


	erabRelActNbrQci3		 OBJECT-TYPE
		SYNTAX					 Counter32
		MAX-ACCESS			 read-only
		STATUS					 current
		DESCRIPTION			 " -- "
		::=  { releasedActiveERABEntry  5 }


	erabRelActNbrQci4		 OBJECT-TYPE
		SYNTAX					 Counter32
		MAX-ACCESS			 read-only
		STATUS					 current
		DESCRIPTION			 " -- "
		::=  { releasedActiveERABEntry  6 }


	erabRelActNbrQci5		 OBJECT-TYPE
		SYNTAX					 Counter32
		MAX-ACCESS			 read-only
		STATUS					 current
		DESCRIPTION			 " -- "
		::=  { releasedActiveERABEntry  7 }


	erabRelActNbrQci6		 OBJECT-TYPE
		SYNTAX					 Counter32
		MAX-ACCESS			 read-only
		STATUS					 current
		DESCRIPTION			 " -- "
		::=  { releasedActiveERABEntry  8 }


	erabRelActNbrQci7		 OBJECT-TYPE
		SYNTAX					 Counter32
		MAX-ACCESS			 read-only
		STATUS					 current
		DESCRIPTION			 " -- "
		::=  { releasedActiveERABEntry  9 }


	erabRelActNbrQci8		 OBJECT-TYPE
		SYNTAX					 Counter32
		MAX-ACCESS			 read-only
		STATUS					 current
		DESCRIPTION			 " -- "
		::=  { releasedActiveERABEntry  10 }


	erabRelActNbrQci9		 OBJECT-TYPE
		SYNTAX					 Counter32
		MAX-ACCESS			 read-only
		STATUS					 current
		DESCRIPTION			 " -- "
		::=  { releasedActiveERABEntry  11 }


	macBlerTable		 OBJECT-TYPE
		SYNTAX					 SEQUENCE  OF	 MacBlerEntry
		MAX-ACCESS			 not-accessible
		STATUS					 current
		DESCRIPTION			 " -- "
		::=  { macrelatedOriginCounter  5 }


	macBlerEntry		 OBJECT-TYPE
		SYNTAX					 MacBlerEntry
		MAX-ACCESS			 not-accessible
		STATUS					 current
		DESCRIPTION			 " -- "
		INDEX						{ macBlerLcId }
		::=  { macBlerTable  1 }


	MacBlerEntry		 ::=  SEQUENCE {
		macBlerLcId					Integer32,
		macBlerRowStatus					RowStatus,
		tbNbrInitUl					Counter32,
		tbNbrUlErr					Counter32,
		tbNbrInitDl					Counter32,
		tbNbrDlErr					Counter32,
		tbNbrInitUlQpsk					Counter32,
		tbNbrInitUl16QAM					Counter32,
		tbNbrInitUl64QAM					Counter32,
		tbNbrSuccInitUlQpsk					Counter32,
		tbNbrSuccInitUl16QAM					Counter32,
		tbNbrSuccInitUl64QAM					Counter32,
		tbNbrInitDlQpsk					Counter32,
		tbNbrInitDl16QAM					Counter32,
		tbNbrInitDl64QAM					Counter32,
		tbNbrSuccInitDlQpsk					Counter32,
		tbNbrSuccInitDl16QAM					Counter32,
		tbNbrSuccInitDl64QAM					Counter32,
		tbSRBInitUl					Counter32,
		tbSRBUlErr					Counter32,
		tbSRBInitDl					Counter32,
		tbSRBDlErr					Counter32,
		tbSRBInitUlQpsk					Counter32,
		tbSRBInitUl16QAM					Counter32,
		tbSRBInitUl64QAM					Counter32,
		tbSRBSuccInitUlQpsk					Counter32,
		tbSRBSuccInitUl16QAM					Counter32,
		tbSRBSuccInitUl64QAM					Counter32,
		tbSRBInitDlQpsk					Counter32,
		tbSRBInitDl16QAM					Counter32,
		tbSRBInitDl64QAM					Counter32,
		tbSRBSuccInitDlQpsk					Counter32,
		tbSRBSuccInitDl16QAM					Counter32,
		tbSRBSuccInitDl64QAM					Counter32
		}


	macBlerLcId		 OBJECT-TYPE
		SYNTAX					 Integer32( 0 .. 23 )
		MAX-ACCESS			 not-accessible
		STATUS					 current
		DESCRIPTION			 " -- "
		::=  { macBlerEntry  1 }


	macBlerRowStatus		 OBJECT-TYPE
		SYNTAX					 RowStatus
		MAX-ACCESS			 read-only
		STATUS					 current
		DESCRIPTION			 " -- "
		::=  { macBlerEntry  2 }


	tbNbrInitUl		 OBJECT-TYPE
		SYNTAX					 Counter32
		MAX-ACCESS			 read-only
		STATUS					 current
		DESCRIPTION			 " -- "
		::=  { macBlerEntry  3 }


	tbNbrUlErr		 OBJECT-TYPE
		SYNTAX					 Counter32
		MAX-ACCESS			 read-only
		STATUS					 current
		DESCRIPTION			 " -- "
		::=  { macBlerEntry  4 }


	tbNbrInitDl		 OBJECT-TYPE
		SYNTAX					 Counter32
		MAX-ACCESS			 read-only
		STATUS					 current
		DESCRIPTION			 " -- "
		::=  { macBlerEntry  5 }


	tbNbrDlErr		 OBJECT-TYPE
		SYNTAX					 Counter32
		MAX-ACCESS			 read-only
		STATUS					 current
		DESCRIPTION			 " -- "
		::=  { macBlerEntry  6 }


	tbNbrInitUlQpsk		 OBJECT-TYPE
		SYNTAX					 Counter32
		MAX-ACCESS			 read-only
		STATUS					 current
		DESCRIPTION			 " -- "
		::=  { macBlerEntry  7 }


	tbNbrInitUl16QAM		 OBJECT-TYPE
		SYNTAX					 Counter32
		MAX-ACCESS			 read-only
		STATUS					 current
		DESCRIPTION			 " -- "
		::=  { macBlerEntry  8 }


	tbNbrInitUl64QAM		 OBJECT-TYPE
		SYNTAX					 Counter32
		MAX-ACCESS			 read-only
		STATUS					 current
		DESCRIPTION			 " -- "
		::=  { macBlerEntry  9 }


	tbNbrSuccInitUlQpsk		 OBJECT-TYPE
		SYNTAX					 Counter32
		MAX-ACCESS			 read-only
		STATUS					 current
		DESCRIPTION			 " -- "
		::=  { macBlerEntry  10 }


	tbNbrSuccInitUl16QAM		 OBJECT-TYPE
		SYNTAX					 Counter32
		MAX-ACCESS			 read-only
		STATUS					 current
		DESCRIPTION			 " -- "
		::=  { macBlerEntry  11 }


	tbNbrSuccInitUl64QAM		 OBJECT-TYPE
		SYNTAX					 Counter32
		MAX-ACCESS			 read-only
		STATUS					 current
		DESCRIPTION			 " -- "
		::=  { macBlerEntry  12 }


	tbNbrInitDlQpsk		 OBJECT-TYPE
		SYNTAX					 Counter32
		MAX-ACCESS			 read-only
		STATUS					 current
		DESCRIPTION			 " -- "
		::=  { macBlerEntry  13 }


	tbNbrInitDl16QAM		 OBJECT-TYPE
		SYNTAX					 Counter32
		MAX-ACCESS			 read-only
		STATUS					 current
		DESCRIPTION			 " -- "
		::=  { macBlerEntry  14 }


	tbNbrInitDl64QAM		 OBJECT-TYPE
		SYNTAX					 Counter32
		MAX-ACCESS			 read-only
		STATUS					 current
		DESCRIPTION			 " -- "
		::=  { macBlerEntry  15 }


	tbNbrSuccInitDlQpsk		 OBJECT-TYPE
		SYNTAX					 Counter32
		MAX-ACCESS			 read-only
		STATUS					 current
		DESCRIPTION			 " -- "
		::=  { macBlerEntry  16 }


	tbNbrSuccInitDl16QAM		 OBJECT-TYPE
		SYNTAX					 Counter32
		MAX-ACCESS			 read-only
		STATUS					 current
		DESCRIPTION			 " -- "
		::=  { macBlerEntry  17 }


	tbNbrSuccInitDl64QAM		 OBJECT-TYPE
		SYNTAX					 Counter32
		MAX-ACCESS			 read-only
		STATUS					 current
		DESCRIPTION			 " -- "
		::=  { macBlerEntry  18 }


	tbSRBInitUl		 OBJECT-TYPE
		SYNTAX					 Counter32
		MAX-ACCESS			 read-only
		STATUS					 current
		DESCRIPTION			 " -- "
		::=  { macBlerEntry  19 }


	tbSRBUlErr		 OBJECT-TYPE
		SYNTAX					 Counter32
		MAX-ACCESS			 read-only
		STATUS					 current
		DESCRIPTION			 " -- "
		::=  { macBlerEntry  20 }


	tbSRBInitDl		 OBJECT-TYPE
		SYNTAX					 Counter32
		MAX-ACCESS			 read-only
		STATUS					 current
		DESCRIPTION			 " -- "
		::=  { macBlerEntry  21 }


	tbSRBDlErr		 OBJECT-TYPE
		SYNTAX					 Counter32
		MAX-ACCESS			 read-only
		STATUS					 current
		DESCRIPTION			 " -- "
		::=  { macBlerEntry  22 }


	tbSRBInitUlQpsk		 OBJECT-TYPE
		SYNTAX					 Counter32
		MAX-ACCESS			 read-only
		STATUS					 current
		DESCRIPTION			 " -- "
		::=  { macBlerEntry  23 }


	tbSRBInitUl16QAM		 OBJECT-TYPE
		SYNTAX					 Counter32
		MAX-ACCESS			 read-only
		STATUS					 current
		DESCRIPTION			 " -- "
		::=  { macBlerEntry  24 }


	tbSRBInitUl64QAM		 OBJECT-TYPE
		SYNTAX					 Counter32
		MAX-ACCESS			 read-only
		STATUS					 current
		DESCRIPTION			 " -- "
		::=  { macBlerEntry  25 }


	tbSRBSuccInitUlQpsk		 OBJECT-TYPE
		SYNTAX					 Counter32
		MAX-ACCESS			 read-only
		STATUS					 current
		DESCRIPTION			 " -- "
		::=  { macBlerEntry  26 }


	tbSRBSuccInitUl16QAM		 OBJECT-TYPE
		SYNTAX					 Counter32
		MAX-ACCESS			 read-only
		STATUS					 current
		DESCRIPTION			 " -- "
		::=  { macBlerEntry  27 }


	tbSRBSuccInitUl64QAM		 OBJECT-TYPE
		SYNTAX					 Counter32
		MAX-ACCESS			 read-only
		STATUS					 current
		DESCRIPTION			 " -- "
		::=  { macBlerEntry  28 }


	tbSRBInitDlQpsk		 OBJECT-TYPE
		SYNTAX					 Counter32
		MAX-ACCESS			 read-only
		STATUS					 current
		DESCRIPTION			 " -- "
		::=  { macBlerEntry  29 }


	tbSRBInitDl16QAM		 OBJECT-TYPE
		SYNTAX					 Counter32
		MAX-ACCESS			 read-only
		STATUS					 current
		DESCRIPTION			 " -- "
		::=  { macBlerEntry  30 }


	tbSRBInitDl64QAM		 OBJECT-TYPE
		SYNTAX					 Counter32
		MAX-ACCESS			 read-only
		STATUS					 current
		DESCRIPTION			 " -- "
		::=  { macBlerEntry  31 }


	tbSRBSuccInitDlQpsk		 OBJECT-TYPE
		SYNTAX					 Counter32
		MAX-ACCESS			 read-only
		STATUS					 current
		DESCRIPTION			 " -- "
		::=  { macBlerEntry  32 }


	tbSRBSuccInitDl16QAM		 OBJECT-TYPE
		SYNTAX					 Counter32
		MAX-ACCESS			 read-only
		STATUS					 current
		DESCRIPTION			 " -- "
		::=  { macBlerEntry  33 }


	tbSRBSuccInitDl64QAM		 OBJECT-TYPE
		SYNTAX					 Counter32
		MAX-ACCESS			 read-only
		STATUS					 current
		DESCRIPTION			 " -- "
		::=  { macBlerEntry  34 }


	macHarqRetxRatioTable		 OBJECT-TYPE
		SYNTAX					 SEQUENCE  OF	 MacHarqRetxRatioEntry
		MAX-ACCESS			 not-accessible
		STATUS					 current
		DESCRIPTION			 " -- "
		::=  { macrelatedOriginCounter  6 }


	macHarqRetxRatioEntry		 OBJECT-TYPE
		SYNTAX					 MacHarqRetxRatioEntry
		MAX-ACCESS			 not-accessible
		STATUS					 current
		DESCRIPTION			 " -- "
		INDEX						{ macHarqRetxRatioLcId }
		::=  { macHarqRetxRatioTable  1 }


	MacHarqRetxRatioEntry		 ::=  SEQUENCE {
		macHarqRetxRatioLcId					Integer32,
		macHarqRetxRatioRowStatus					RowStatus,
		macNbrTbUl					Counter32,
		macNbrAckdTbUl					Counter32,
		macNbrTbDl					Counter32,
		macNbrSuccTbDl					Counter32,
		macNbrTbDLRank1					Counter32,
		macNbrTbDLRank2					Counter32,
		macNbrTbDLRank3					Counter32,
		macNbrTbDLRank4					Counter32,
		macNbrTbDLRank5					Counter32,
		macNbrTbDLRank6					Counter32,
		macNbrTbDLRank7					Counter32,
		macNbrTbDLRank8					Counter32,
		macNbrTbDlTm1					Counter32,
		macNbrTbDlTm2					Counter32,
		macNbrTbDlTm3					Counter32,
		macNbrTbDlTm4					Counter32,
		macNbrTbDlTm5					Counter32,
		macNbrTbDlTm6					Counter32,
		macNbrTbDlTm7					Counter32,
		macNbrTbDlTm8					Counter32,
		macSRBTbUl					Counter32,
		macSRBAckdTbUl					Counter32,
		macSRBTbDl					Counter32,
		macSRBSuccTbDl					Counter32,
		macSRBTbDLRank1					Counter32,
		macSRBTbDLRank2					Counter32,
		macSRBTbDLRank3					Counter32,
		macSRBTbDLRank4					Counter32,
		macSRBTbDLRank5					Counter32,
		macSRBTbDLRank6					Counter32,
		macSRBTbDLRank7					Counter32,
		macSRBTbDLRank8					Counter32,
		macSRBTbDlTm1					Counter32,
		macSRBTbDlTm2					Counter32,
		macSRBTbDlTm3					Counter32,
		macSRBTbDlTm4					Counter32,
		macSRBTbDlTm5					Counter32,
		macSRBTbDlTm6					Counter32,
		macSRBTbDlTm7					Counter32,
		macSRBTbDlTm8					Counter32,
		macNbrTbDlTm9					Counter32
		}


	macHarqRetxRatioLcId		 OBJECT-TYPE
		SYNTAX					 Integer32( 0 .. 23 )
		MAX-ACCESS			 not-accessible
		STATUS					 current
		DESCRIPTION			 " -- "
		::=  { macHarqRetxRatioEntry  1 }


	macHarqRetxRatioRowStatus		 OBJECT-TYPE
		SYNTAX					 RowStatus
		MAX-ACCESS			 read-only
		STATUS					 current
		DESCRIPTION			 " -- "
		::=  { macHarqRetxRatioEntry  2 }


	macNbrTbUl		 OBJECT-TYPE
		SYNTAX					 Counter32
		MAX-ACCESS			 read-only
		STATUS					 current
		DESCRIPTION			 " -- "
		::=  { macHarqRetxRatioEntry  3 }


	macNbrAckdTbUl		 OBJECT-TYPE
		SYNTAX					 Counter32
		MAX-ACCESS			 read-only
		STATUS					 current
		DESCRIPTION			 " -- "
		::=  { macHarqRetxRatioEntry  4 }


	macNbrTbDl		 OBJECT-TYPE
		SYNTAX					 Counter32
		MAX-ACCESS			 read-only
		STATUS					 current
		DESCRIPTION			 " -- "
		::=  { macHarqRetxRatioEntry  5 }


	macNbrSuccTbDl		 OBJECT-TYPE
		SYNTAX					 Counter32
		MAX-ACCESS			 read-only
		STATUS					 current
		DESCRIPTION			 " -- "
		::=  { macHarqRetxRatioEntry  6 }


	macNbrTbDLRank1		 OBJECT-TYPE
		SYNTAX					 Counter32
		MAX-ACCESS			 read-only
		STATUS					 current
		DESCRIPTION			 " -- "
		::=  { macHarqRetxRatioEntry  7 }


	macNbrTbDLRank2		 OBJECT-TYPE
		SYNTAX					 Counter32
		MAX-ACCESS			 read-only
		STATUS					 current
		DESCRIPTION			 " -- "
		::=  { macHarqRetxRatioEntry  8 }


	macNbrTbDLRank3		 OBJECT-TYPE
		SYNTAX					 Counter32
		MAX-ACCESS			 read-only
		STATUS					 current
		DESCRIPTION			 " -- "
		::=  { macHarqRetxRatioEntry  9 }


	macNbrTbDLRank4		 OBJECT-TYPE
		SYNTAX					 Counter32
		MAX-ACCESS			 read-only
		STATUS					 current
		DESCRIPTION			 " -- "
		::=  { macHarqRetxRatioEntry  10 }


	macNbrTbDLRank5		 OBJECT-TYPE
		SYNTAX					 Counter32
		MAX-ACCESS			 read-only
		STATUS					 current
		DESCRIPTION			 " -- "
		::=  { macHarqRetxRatioEntry  11 }


	macNbrTbDLRank6		 OBJECT-TYPE
		SYNTAX					 Counter32
		MAX-ACCESS			 read-only
		STATUS					 current
		DESCRIPTION			 " -- "
		::=  { macHarqRetxRatioEntry  12 }


	macNbrTbDLRank7		 OBJECT-TYPE
		SYNTAX					 Counter32
		MAX-ACCESS			 read-only
		STATUS					 current
		DESCRIPTION			 " -- "
		::=  { macHarqRetxRatioEntry  13 }


	macNbrTbDLRank8		 OBJECT-TYPE
		SYNTAX					 Counter32
		MAX-ACCESS			 read-only
		STATUS					 current
		DESCRIPTION			 " -- "
		::=  { macHarqRetxRatioEntry  14 }


	macNbrTbDlTm1		 OBJECT-TYPE
		SYNTAX					 Counter32
		MAX-ACCESS			 read-only
		STATUS					 current
		DESCRIPTION			 " -- "
		::=  { macHarqRetxRatioEntry  15 }


	macNbrTbDlTm2		 OBJECT-TYPE
		SYNTAX					 Counter32
		MAX-ACCESS			 read-only
		STATUS					 current
		DESCRIPTION			 " -- "
		::=  { macHarqRetxRatioEntry  16 }


	macNbrTbDlTm3		 OBJECT-TYPE
		SYNTAX					 Counter32
		MAX-ACCESS			 read-only
		STATUS					 current
		DESCRIPTION			 " -- "
		::=  { macHarqRetxRatioEntry  17 }


	macNbrTbDlTm4		 OBJECT-TYPE
		SYNTAX					 Counter32
		MAX-ACCESS			 read-only
		STATUS					 current
		DESCRIPTION			 " -- "
		::=  { macHarqRetxRatioEntry  18 }


	macNbrTbDlTm5		 OBJECT-TYPE
		SYNTAX					 Counter32
		MAX-ACCESS			 read-only
		STATUS					 current
		DESCRIPTION			 " -- "
		::=  { macHarqRetxRatioEntry  19 }


	macNbrTbDlTm6		 OBJECT-TYPE
		SYNTAX					 Counter32
		MAX-ACCESS			 read-only
		STATUS					 current
		DESCRIPTION			 " -- "
		::=  { macHarqRetxRatioEntry  20 }


	macNbrTbDlTm7		 OBJECT-TYPE
		SYNTAX					 Counter32
		MAX-ACCESS			 read-only
		STATUS					 current
		DESCRIPTION			 " -- "
		::=  { macHarqRetxRatioEntry  21 }


	macNbrTbDlTm8		 OBJECT-TYPE
		SYNTAX					 Counter32
		MAX-ACCESS			 read-only
		STATUS					 current
		DESCRIPTION			 " -- "
		::=  { macHarqRetxRatioEntry  22 }


	macSRBTbUl		 OBJECT-TYPE
		SYNTAX					 Counter32
		MAX-ACCESS			 read-only
		STATUS					 current
		DESCRIPTION			 " -- "
		::=  { macHarqRetxRatioEntry  23 }


	macSRBAckdTbUl		 OBJECT-TYPE
		SYNTAX					 Counter32
		MAX-ACCESS			 read-only
		STATUS					 current
		DESCRIPTION			 " -- "
		::=  { macHarqRetxRatioEntry  24 }


	macSRBTbDl		 OBJECT-TYPE
		SYNTAX					 Counter32
		MAX-ACCESS			 read-only
		STATUS					 current
		DESCRIPTION			 " -- "
		::=  { macHarqRetxRatioEntry  25 }


	macSRBSuccTbDl		 OBJECT-TYPE
		SYNTAX					 Counter32
		MAX-ACCESS			 read-only
		STATUS					 current
		DESCRIPTION			 " -- "
		::=  { macHarqRetxRatioEntry  26 }


	macSRBTbDLRank1		 OBJECT-TYPE
		SYNTAX					 Counter32
		MAX-ACCESS			 read-only
		STATUS					 current
		DESCRIPTION			 " -- "
		::=  { macHarqRetxRatioEntry  27 }


	macSRBTbDLRank2		 OBJECT-TYPE
		SYNTAX					 Counter32
		MAX-ACCESS			 read-only
		STATUS					 current
		DESCRIPTION			 " -- "
		::=  { macHarqRetxRatioEntry  28 }


	macSRBTbDLRank3		 OBJECT-TYPE
		SYNTAX					 Counter32
		MAX-ACCESS			 read-only
		STATUS					 current
		DESCRIPTION			 " -- "
		::=  { macHarqRetxRatioEntry  29 }


	macSRBTbDLRank4		 OBJECT-TYPE
		SYNTAX					 Counter32
		MAX-ACCESS			 read-only
		STATUS					 current
		DESCRIPTION			 " -- "
		::=  { macHarqRetxRatioEntry  30 }


	macSRBTbDLRank5		 OBJECT-TYPE
		SYNTAX					 Counter32
		MAX-ACCESS			 read-only
		STATUS					 current
		DESCRIPTION			 " -- "
		::=  { macHarqRetxRatioEntry  31 }


	macSRBTbDLRank6		 OBJECT-TYPE
		SYNTAX					 Counter32
		MAX-ACCESS			 read-only
		STATUS					 current
		DESCRIPTION			 " -- "
		::=  { macHarqRetxRatioEntry  32 }


	macSRBTbDLRank7		 OBJECT-TYPE
		SYNTAX					 Counter32
		MAX-ACCESS			 read-only
		STATUS					 current
		DESCRIPTION			 " -- "
		::=  { macHarqRetxRatioEntry  33 }


	macSRBTbDLRank8		 OBJECT-TYPE
		SYNTAX					 Counter32
		MAX-ACCESS			 read-only
		STATUS					 current
		DESCRIPTION			 " -- "
		::=  { macHarqRetxRatioEntry  34 }


	macSRBTbDlTm1		 OBJECT-TYPE
		SYNTAX					 Counter32
		MAX-ACCESS			 read-only
		STATUS					 current
		DESCRIPTION			 " -- "
		::=  { macHarqRetxRatioEntry  35 }


	macSRBTbDlTm2		 OBJECT-TYPE
		SYNTAX					 Counter32
		MAX-ACCESS			 read-only
		STATUS					 current
		DESCRIPTION			 " -- "
		::=  { macHarqRetxRatioEntry  36 }


	macSRBTbDlTm3		 OBJECT-TYPE
		SYNTAX					 Counter32
		MAX-ACCESS			 read-only
		STATUS					 current
		DESCRIPTION			 " -- "
		::=  { macHarqRetxRatioEntry  37 }


	macSRBTbDlTm4		 OBJECT-TYPE
		SYNTAX					 Counter32
		MAX-ACCESS			 read-only
		STATUS					 current
		DESCRIPTION			 " -- "
		::=  { macHarqRetxRatioEntry  38 }


	macSRBTbDlTm5		 OBJECT-TYPE
		SYNTAX					 Counter32
		MAX-ACCESS			 read-only
		STATUS					 current
		DESCRIPTION			 " -- "
		::=  { macHarqRetxRatioEntry  39 }


	macSRBTbDlTm6		 OBJECT-TYPE
		SYNTAX					 Counter32
		MAX-ACCESS			 read-only
		STATUS					 current
		DESCRIPTION			 " -- "
		::=  { macHarqRetxRatioEntry  40 }


	macSRBTbDlTm7		 OBJECT-TYPE
		SYNTAX					 Counter32
		MAX-ACCESS			 read-only
		STATUS					 current
		DESCRIPTION			 " -- "
		::=  { macHarqRetxRatioEntry  41 }


	macSRBTbDlTm8		 OBJECT-TYPE
		SYNTAX					 Counter32
		MAX-ACCESS			 read-only
		STATUS					 current
		DESCRIPTION			 " -- "
		::=  { macHarqRetxRatioEntry  42 }


	macNbrTbDlTm9		 OBJECT-TYPE
		SYNTAX					 Counter32
		MAX-ACCESS			 read-only
		STATUS					 current
		DESCRIPTION			 " -- "
		::=  { macHarqRetxRatioEntry  43 }


	pdcchCceDlMeanTable		 OBJECT-TYPE
		SYNTAX					 SEQUENCE  OF	 PdcchCceDlMeanEntry
		MAX-ACCESS			 not-accessible
		STATUS					 current
		DESCRIPTION			 " -- "
		::=  { macrelatedOriginCounter  7 }


	pdcchCceDlMeanEntry		 OBJECT-TYPE
		SYNTAX					 PdcchCceDlMeanEntry
		MAX-ACCESS			 not-accessible
		STATUS					 current
		DESCRIPTION			 " -- "
		INDEX						{ pdcchCceDlMeanLcId }
		::=  { pdcchCceDlMeanTable  1 }


	PdcchCceDlMeanEntry		 ::=  SEQUENCE {
		pdcchCceDlMeanLcId					Integer32,
		pdcchCceDlMeanRowStatus					RowStatus,
		rruPdcchCceDlAssnMean					Counter32
		}


	pdcchCceDlMeanLcId		 OBJECT-TYPE
		SYNTAX					 Integer32( 0 .. 23 )
		MAX-ACCESS			 not-accessible
		STATUS					 current
		DESCRIPTION			 " -- "
		::=  { pdcchCceDlMeanEntry  1 }


	pdcchCceDlMeanRowStatus		 OBJECT-TYPE
		SYNTAX					 RowStatus
		MAX-ACCESS			 read-only
		STATUS					 current
		DESCRIPTION			 " -- "
		::=  { pdcchCceDlMeanEntry  2 }


	rruPdcchCceDlAssnMean		 OBJECT-TYPE
		SYNTAX					 Counter32
		MAX-ACCESS			 read-only
		STATUS					 current
		DESCRIPTION			 " -- "
		::=  { pdcchCceDlMeanEntry  3 }


	cqiNumberStatisticTable		 OBJECT-TYPE
		SYNTAX					 SEQUENCE  OF	 CqiNumberStatisticEntry
		MAX-ACCESS			 not-accessible
		STATUS					 current
		DESCRIPTION			 " -- "
		::=  { macrelatedOriginCounter  8 }


	cqiNumberStatisticEntry		 OBJECT-TYPE
		SYNTAX					 CqiNumberStatisticEntry
		MAX-ACCESS			 not-accessible
		STATUS					 current
		DESCRIPTION			 " -- "
		INDEX						{ cqiNumberStatisticLcId }
		::=  { cqiNumberStatisticTable  1 }


	CqiNumberStatisticEntry		 ::=  SEQUENCE {
		cqiNumberStatisticLcId					Integer32,
		cqiNumberStatisticRowStatus					RowStatus,
		phyNbrCqi0					Counter32,
		phyNbrCqi1					Counter32,
		phyNbrCqi2					Counter32,
		phyNbrCqi3					Counter32,
		phyNbrCqi4					Counter32,
		phyNbrCqi5					Counter32,
		phyNbrCqi6					Counter32,
		phyNbrCqi7					Counter32,
		phyNbrCqi8					Counter32,
		phyNbrCqi9					Counter32,
		phyNbrCqi10					Counter32,
		phyNbrCqi11					Counter32,
		phyNbrCqi12					Counter32,
		phyNbrCqi13					Counter32,
		phyNbrCqi14					Counter32,
		phyNbrCqi15					Counter32,
		rrcReduceIotUPNum					Counter32,
		rrcRecoverIotUPNum					Counter32,
		rrcReduceIotUPNumVip					Counter32
		}


	cqiNumberStatisticLcId		 OBJECT-TYPE
		SYNTAX					 Integer32( 0 .. 23 )
		MAX-ACCESS			 not-accessible
		STATUS					 current
		DESCRIPTION			 " -- "
		::=  { cqiNumberStatisticEntry  1 }


	cqiNumberStatisticRowStatus		 OBJECT-TYPE
		SYNTAX					 RowStatus
		MAX-ACCESS			 read-only
		STATUS					 current
		DESCRIPTION			 " -- "
		::=  { cqiNumberStatisticEntry  2 }


	phyNbrCqi0		 OBJECT-TYPE
		SYNTAX					 Counter32
		MAX-ACCESS			 read-only
		STATUS					 current
		DESCRIPTION			 " -- "
		::=  { cqiNumberStatisticEntry  3 }


	phyNbrCqi1		 OBJECT-TYPE
		SYNTAX					 Counter32
		MAX-ACCESS			 read-only
		STATUS					 current
		DESCRIPTION			 " -- "
		::=  { cqiNumberStatisticEntry  4 }


	phyNbrCqi2		 OBJECT-TYPE
		SYNTAX					 Counter32
		MAX-ACCESS			 read-only
		STATUS					 current
		DESCRIPTION			 " -- "
		::=  { cqiNumberStatisticEntry  5 }


	phyNbrCqi3		 OBJECT-TYPE
		SYNTAX					 Counter32
		MAX-ACCESS			 read-only
		STATUS					 current
		DESCRIPTION			 " -- "
		::=  { cqiNumberStatisticEntry  6 }


	phyNbrCqi4		 OBJECT-TYPE
		SYNTAX					 Counter32
		MAX-ACCESS			 read-only
		STATUS					 current
		DESCRIPTION			 " -- "
		::=  { cqiNumberStatisticEntry  7 }


	phyNbrCqi5		 OBJECT-TYPE
		SYNTAX					 Counter32
		MAX-ACCESS			 read-only
		STATUS					 current
		DESCRIPTION			 " -- "
		::=  { cqiNumberStatisticEntry  8 }


	phyNbrCqi6		 OBJECT-TYPE
		SYNTAX					 Counter32
		MAX-ACCESS			 read-only
		STATUS					 current
		DESCRIPTION			 " -- "
		::=  { cqiNumberStatisticEntry  9 }


	phyNbrCqi7		 OBJECT-TYPE
		SYNTAX					 Counter32
		MAX-ACCESS			 read-only
		STATUS					 current
		DESCRIPTION			 " -- "
		::=  { cqiNumberStatisticEntry  10 }


	phyNbrCqi8		 OBJECT-TYPE
		SYNTAX					 Counter32
		MAX-ACCESS			 read-only
		STATUS					 current
		DESCRIPTION			 " -- "
		::=  { cqiNumberStatisticEntry  11 }


	phyNbrCqi9		 OBJECT-TYPE
		SYNTAX					 Counter32
		MAX-ACCESS			 read-only
		STATUS					 current
		DESCRIPTION			 " -- "
		::=  { cqiNumberStatisticEntry  12 }


	phyNbrCqi10		 OBJECT-TYPE
		SYNTAX					 Counter32
		MAX-ACCESS			 read-only
		STATUS					 current
		DESCRIPTION			 " -- "
		::=  { cqiNumberStatisticEntry  13 }


	phyNbrCqi11		 OBJECT-TYPE
		SYNTAX					 Counter32
		MAX-ACCESS			 read-only
		STATUS					 current
		DESCRIPTION			 " -- "
		::=  { cqiNumberStatisticEntry  14 }


	phyNbrCqi12		 OBJECT-TYPE
		SYNTAX					 Counter32
		MAX-ACCESS			 read-only
		STATUS					 current
		DESCRIPTION			 " -- "
		::=  { cqiNumberStatisticEntry  15 }


	phyNbrCqi13		 OBJECT-TYPE
		SYNTAX					 Counter32
		MAX-ACCESS			 read-only
		STATUS					 current
		DESCRIPTION			 " -- "
		::=  { cqiNumberStatisticEntry  16 }


	phyNbrCqi14		 OBJECT-TYPE
		SYNTAX					 Counter32
		MAX-ACCESS			 read-only
		STATUS					 current
		DESCRIPTION			 " -- "
		::=  { cqiNumberStatisticEntry  17 }


	phyNbrCqi15		 OBJECT-TYPE
		SYNTAX					 Counter32
		MAX-ACCESS			 read-only
		STATUS					 current
		DESCRIPTION			 " -- "
		::=  { cqiNumberStatisticEntry  18 }


	rrcReduceIotUPNum		 OBJECT-TYPE
		SYNTAX					 Counter32
		MAX-ACCESS			 read-only
		STATUS					 current
		DESCRIPTION			 " -- "
		::=  { cqiNumberStatisticEntry  19 }


	rrcRecoverIotUPNum		 OBJECT-TYPE
		SYNTAX					 Counter32
		MAX-ACCESS			 read-only
		STATUS					 current
		DESCRIPTION			 " -- "
		::=  { cqiNumberStatisticEntry  20 }


	rrcReduceIotUPNumVip		 OBJECT-TYPE
		SYNTAX					 Counter32
		MAX-ACCESS			 read-only
		STATUS					 current
		DESCRIPTION			 " -- "
		::=  { cqiNumberStatisticEntry  21 }


	cceCclrTable		 OBJECT-TYPE
		SYNTAX					 SEQUENCE  OF	 CceCclrEntry
		MAX-ACCESS			 not-accessible
		STATUS					 current
		DESCRIPTION			 " -- "
		::=  { macrelatedOriginCounter  9 }


	cceCclrEntry		 OBJECT-TYPE
		SYNTAX					 CceCclrEntry
		MAX-ACCESS			 not-accessible
		STATUS					 current
		DESCRIPTION			 " -- "
		INDEX						{ cceCclrLcId }
		::=  { cceCclrTable  1 }


	CceCclrEntry		 ::=  SEQUENCE {
		cceCclrLcId					Integer32,
		cceCclrRowStatus					RowStatus,
		macsche1cce					Counter32,
		macsche2cce					Counter32,
		macsche3cce					Counter32,
		macsche4cce					Counter32,
		macschecceusedsfn0					Counter32,
		macschecceusedsfn1					Counter32,
		macschecceusedsfn3					Counter32,
		macschecceusedsfn4					Counter32,
		macschecceusedsfn5					Counter32,
		macschecceusedsfn6					Counter32,
		macschecceusedsfn7					Counter32,
		macschecceusedsfn8					Counter32,
		macschecceusedsfn9					Counter32,
		macschecceallsfn0					Counter32,
		macschecceallsfn1					Counter32,
		macschecceallsfn3					Counter32,
		macschecceallsfn4					Counter32,
		macschecceallsfn5					Counter32,
		macschecceallsfn6					Counter32,
		macschecceallsfn7					Counter32,
		macschecceallsfn8					Counter32,
		macschecceallsfn9					Counter32,
		macschefailtimescclr					Counter32,
		macschetimestotal					Counter32,
		macschecfi1					Counter32,
		macschecfi2					Counter32,
		macschecfi3					Counter32,
		macschecceusedUl					Counter32,
		macschecceallUl					Counter32,
		macscheCceUsed					Counter32,
		macscheCceAll					Counter32,
		rruPdcchCceAvailUlDciSf					Counter32,
		rruPdcchCceUtilUlDciSf					Counter32,
		macsche1cceratio					Counter32,
		macsche2cceratio					Counter32,
		macsche4cceratio					Counter32,
		macsche8cceratio					Counter32,
		macschecceusedratiosfn0					Counter32,
		macschecceusedratiosfn1					Counter32,
		macschecceusedratiosfn3					Counter32,
		macschecceusedratiosfn4					Counter32,
		macschecceusedratiosfn5					Counter32,
		macschecceusedratiosfn6					Counter32,
		macschecceusedratiosfn7					Counter32,
		macschecceusedratiosfn8					Counter32,
		macschecceusedratiosfn9					Counter32,
		macschefailtimescclrratio					Counter32,
		macschecfi1ratio					Counter32,
		macschecfi2ratio					Counter32,
		macschecfi3ratio					Counter32
		}


	cceCclrLcId		 OBJECT-TYPE
		SYNTAX					 Integer32( 0 .. 23 )
		MAX-ACCESS			 not-accessible
		STATUS					 current
		DESCRIPTION			 " -- "
		::=  { cceCclrEntry  1 }


	cceCclrRowStatus		 OBJECT-TYPE
		SYNTAX					 RowStatus
		MAX-ACCESS			 read-only
		STATUS					 current
		DESCRIPTION			 " -- "
		::=  { cceCclrEntry  2 }


	macsche1cce		 OBJECT-TYPE
		SYNTAX					 Counter32
		MAX-ACCESS			 read-only
		STATUS					 current
		DESCRIPTION			 " -- "
		::=  { cceCclrEntry  3 }


	macsche2cce		 OBJECT-TYPE
		SYNTAX					 Counter32
		MAX-ACCESS			 read-only
		STATUS					 current
		DESCRIPTION			 " -- "
		::=  { cceCclrEntry  4 }


	macsche3cce		 OBJECT-TYPE
		SYNTAX					 Counter32
		MAX-ACCESS			 read-only
		STATUS					 current
		DESCRIPTION			 " -- "
		::=  { cceCclrEntry  5 }


	macsche4cce		 OBJECT-TYPE
		SYNTAX					 Counter32
		MAX-ACCESS			 read-only
		STATUS					 current
		DESCRIPTION			 " -- "
		::=  { cceCclrEntry  6 }


	macschecceusedsfn0		 OBJECT-TYPE
		SYNTAX					 Counter32
		MAX-ACCESS			 read-only
		STATUS					 current
		DESCRIPTION			 " -- "
		::=  { cceCclrEntry  7 }


	macschecceusedsfn1		 OBJECT-TYPE
		SYNTAX					 Counter32
		MAX-ACCESS			 read-only
		STATUS					 current
		DESCRIPTION			 " -- "
		::=  { cceCclrEntry  8 }


	macschecceusedsfn3		 OBJECT-TYPE
		SYNTAX					 Counter32
		MAX-ACCESS			 read-only
		STATUS					 current
		DESCRIPTION			 " -- "
		::=  { cceCclrEntry  9 }


	macschecceusedsfn4		 OBJECT-TYPE
		SYNTAX					 Counter32
		MAX-ACCESS			 read-only
		STATUS					 current
		DESCRIPTION			 " -- "
		::=  { cceCclrEntry  10 }


	macschecceusedsfn5		 OBJECT-TYPE
		SYNTAX					 Counter32
		MAX-ACCESS			 read-only
		STATUS					 current
		DESCRIPTION			 " -- "
		::=  { cceCclrEntry  11 }


	macschecceusedsfn6		 OBJECT-TYPE
		SYNTAX					 Counter32
		MAX-ACCESS			 read-only
		STATUS					 current
		DESCRIPTION			 " -- "
		::=  { cceCclrEntry  12 }


	macschecceusedsfn7		 OBJECT-TYPE
		SYNTAX					 Counter32
		MAX-ACCESS			 read-only
		STATUS					 current
		DESCRIPTION			 " -- "
		::=  { cceCclrEntry  13 }


	macschecceusedsfn8		 OBJECT-TYPE
		SYNTAX					 Counter32
		MAX-ACCESS			 read-only
		STATUS					 current
		DESCRIPTION			 " -- "
		::=  { cceCclrEntry  14 }


	macschecceusedsfn9		 OBJECT-TYPE
		SYNTAX					 Counter32
		MAX-ACCESS			 read-only
		STATUS					 current
		DESCRIPTION			 " -- "
		::=  { cceCclrEntry  15 }


	macschecceallsfn0		 OBJECT-TYPE
		SYNTAX					 Counter32
		MAX-ACCESS			 read-only
		STATUS					 current
		DESCRIPTION			 " -- "
		::=  { cceCclrEntry  16 }


	macschecceallsfn1		 OBJECT-TYPE
		SYNTAX					 Counter32
		MAX-ACCESS			 read-only
		STATUS					 current
		DESCRIPTION			 " -- "
		::=  { cceCclrEntry  17 }


	macschecceallsfn3		 OBJECT-TYPE
		SYNTAX					 Counter32
		MAX-ACCESS			 read-only
		STATUS					 current
		DESCRIPTION			 " -- "
		::=  { cceCclrEntry  18 }


	macschecceallsfn4		 OBJECT-TYPE
		SYNTAX					 Counter32
		MAX-ACCESS			 read-only
		STATUS					 current
		DESCRIPTION			 " -- "
		::=  { cceCclrEntry  19 }


	macschecceallsfn5		 OBJECT-TYPE
		SYNTAX					 Counter32
		MAX-ACCESS			 read-only
		STATUS					 current
		DESCRIPTION			 " -- "
		::=  { cceCclrEntry  20 }


	macschecceallsfn6		 OBJECT-TYPE
		SYNTAX					 Counter32
		MAX-ACCESS			 read-only
		STATUS					 current
		DESCRIPTION			 " -- "
		::=  { cceCclrEntry  21 }


	macschecceallsfn7		 OBJECT-TYPE
		SYNTAX					 Counter32
		MAX-ACCESS			 read-only
		STATUS					 current
		DESCRIPTION			 " -- "
		::=  { cceCclrEntry  22 }


	macschecceallsfn8		 OBJECT-TYPE
		SYNTAX					 Counter32
		MAX-ACCESS			 read-only
		STATUS					 current
		DESCRIPTION			 " -- "
		::=  { cceCclrEntry  23 }


	macschecceallsfn9		 OBJECT-TYPE
		SYNTAX					 Counter32
		MAX-ACCESS			 read-only
		STATUS					 current
		DESCRIPTION			 " -- "
		::=  { cceCclrEntry  24 }


	macschefailtimescclr		 OBJECT-TYPE
		SYNTAX					 Counter32
		MAX-ACCESS			 read-only
		STATUS					 current
		DESCRIPTION			 " -- "
		::=  { cceCclrEntry  25 }


	macschetimestotal		 OBJECT-TYPE
		SYNTAX					 Counter32
		MAX-ACCESS			 read-only
		STATUS					 current
		DESCRIPTION			 " -- "
		::=  { cceCclrEntry  26 }


	macschecfi1		 OBJECT-TYPE
		SYNTAX					 Counter32
		MAX-ACCESS			 read-only
		STATUS					 current
		DESCRIPTION			 " -- "
		::=  { cceCclrEntry  27 }


	macschecfi2		 OBJECT-TYPE
		SYNTAX					 Counter32
		MAX-ACCESS			 read-only
		STATUS					 current
		DESCRIPTION			 " -- "
		::=  { cceCclrEntry  28 }


	macschecfi3		 OBJECT-TYPE
		SYNTAX					 Counter32
		MAX-ACCESS			 read-only
		STATUS					 current
		DESCRIPTION			 " -- "
		::=  { cceCclrEntry  29 }


	macschecceusedUl		 OBJECT-TYPE
		SYNTAX					 Counter32
		MAX-ACCESS			 read-only
		STATUS					 current
		DESCRIPTION			 " -- "
		::=  { cceCclrEntry  30 }


	macschecceallUl		 OBJECT-TYPE
		SYNTAX					 Counter32
		MAX-ACCESS			 read-only
		STATUS					 current
		DESCRIPTION			 " -- "
		::=  { cceCclrEntry  31 }


	macscheCceUsed		 OBJECT-TYPE
		SYNTAX					 Counter32
		MAX-ACCESS			 read-only
		STATUS					 current
		DESCRIPTION			 " -- "
		::=  { cceCclrEntry  32 }


	macscheCceAll		 OBJECT-TYPE
		SYNTAX					 Counter32
		MAX-ACCESS			 read-only
		STATUS					 current
		DESCRIPTION			 " -- "
		::=  { cceCclrEntry  33 }


	rruPdcchCceAvailUlDciSf		 OBJECT-TYPE
		SYNTAX					 Counter32
		MAX-ACCESS			 read-only
		STATUS					 current
		DESCRIPTION			 " -- "
		::=  { cceCclrEntry  34 }


	rruPdcchCceUtilUlDciSf		 OBJECT-TYPE
		SYNTAX					 Counter32
		MAX-ACCESS			 read-only
		STATUS					 current
		DESCRIPTION			 " -- "
		::=  { cceCclrEntry  35 }


	macsche1cceratio		 OBJECT-TYPE
		SYNTAX					 Counter32
		MAX-ACCESS			 read-only
		STATUS					 current
		DESCRIPTION			 " -- "
		::=  { cceCclrEntry  200 }


	macsche2cceratio		 OBJECT-TYPE
		SYNTAX					 Counter32
		MAX-ACCESS			 read-only
		STATUS					 current
		DESCRIPTION			 " -- "
		::=  { cceCclrEntry  201 }


	macsche4cceratio		 OBJECT-TYPE
		SYNTAX					 Counter32
		MAX-ACCESS			 read-only
		STATUS					 current
		DESCRIPTION			 " -- "
		::=  { cceCclrEntry  202 }


	macsche8cceratio		 OBJECT-TYPE
		SYNTAX					 Counter32
		MAX-ACCESS			 read-only
		STATUS					 current
		DESCRIPTION			 " -- "
		::=  { cceCclrEntry  203 }


	macschecceusedratiosfn0		 OBJECT-TYPE
		SYNTAX					 Counter32
		MAX-ACCESS			 read-only
		STATUS					 current
		DESCRIPTION			 " -- "
		::=  { cceCclrEntry  204 }


	macschecceusedratiosfn1		 OBJECT-TYPE
		SYNTAX					 Counter32
		MAX-ACCESS			 read-only
		STATUS					 current
		DESCRIPTION			 " -- "
		::=  { cceCclrEntry  205 }


	macschecceusedratiosfn3		 OBJECT-TYPE
		SYNTAX					 Counter32
		MAX-ACCESS			 read-only
		STATUS					 current
		DESCRIPTION			 " -- "
		::=  { cceCclrEntry  206 }


	macschecceusedratiosfn4		 OBJECT-TYPE
		SYNTAX					 Counter32
		MAX-ACCESS			 read-only
		STATUS					 current
		DESCRIPTION			 " -- "
		::=  { cceCclrEntry  207 }


	macschecceusedratiosfn5		 OBJECT-TYPE
		SYNTAX					 Counter32
		MAX-ACCESS			 read-only
		STATUS					 current
		DESCRIPTION			 " -- "
		::=  { cceCclrEntry  208 }


	macschecceusedratiosfn6		 OBJECT-TYPE
		SYNTAX					 Counter32
		MAX-ACCESS			 read-only
		STATUS					 current
		DESCRIPTION			 " -- "
		::=  { cceCclrEntry  209 }


	macschecceusedratiosfn7		 OBJECT-TYPE
		SYNTAX					 Counter32
		MAX-ACCESS			 read-only
		STATUS					 current
		DESCRIPTION			 " -- "
		::=  { cceCclrEntry  210 }


	macschecceusedratiosfn8		 OBJECT-TYPE
		SYNTAX					 Counter32
		MAX-ACCESS			 read-only
		STATUS					 current
		DESCRIPTION			 " -- "
		::=  { cceCclrEntry  211 }


	macschecceusedratiosfn9		 OBJECT-TYPE
		SYNTAX					 Counter32
		MAX-ACCESS			 read-only
		STATUS					 current
		DESCRIPTION			 " -- "
		::=  { cceCclrEntry  212 }


	macschefailtimescclrratio		 OBJECT-TYPE
		SYNTAX					 Counter32
		MAX-ACCESS			 read-only
		STATUS					 current
		DESCRIPTION			 " -- "
		::=  { cceCclrEntry  213 }


	macschecfi1ratio		 OBJECT-TYPE
		SYNTAX					 Counter32
		MAX-ACCESS			 read-only
		STATUS					 current
		DESCRIPTION			 " -- "
		::=  { cceCclrEntry  214 }


	macschecfi2ratio		 OBJECT-TYPE
		SYNTAX					 Counter32
		MAX-ACCESS			 read-only
		STATUS					 current
		DESCRIPTION			 " -- "
		::=  { cceCclrEntry  215 }


	macschecfi3ratio		 OBJECT-TYPE
		SYNTAX					 Counter32
		MAX-ACCESS			 read-only
		STATUS					 current
		DESCRIPTION			 " -- "
		::=  { cceCclrEntry  216 }


	pdcpThroughputTimeTable		 OBJECT-TYPE
		SYNTAX					 SEQUENCE  OF	 PdcpThroughputTimeEntry
		MAX-ACCESS			 not-accessible
		STATUS					 current
		DESCRIPTION			 " -- "
		::=  { macrelatedOriginCounter  10 }


	pdcpThroughputTimeEntry		 OBJECT-TYPE
		SYNTAX					 PdcpThroughputTimeEntry
		MAX-ACCESS			 not-accessible
		STATUS					 current
		DESCRIPTION			 " -- "
		INDEX						{ pdcpThroughputTimeLcId }
		::=  { pdcpThroughputTimeTable  1 }


	PdcpThroughputTimeEntry		 ::=  SEQUENCE {
		pdcpThroughputTimeLcId					Integer32,
		pdcpThroughputTimeRowStatus					RowStatus,
		pdcpThrpTimeUL					Counter32,
		pdcpThrpTimeULQci1					Counter32,
		pdcpThrpTimeULQci2					Counter32,
		pdcpThrpTimeULQci3					Counter32,
		pdcpThrpTimeULQci4					Counter32,
		pdcpThrpTimeULQci5					Counter32,
		pdcpThrpTimeULQci6					Counter32,
		pdcpThrpTimeULQci7					Counter32,
		pdcpThrpTimeULQci8					Counter32,
		pdcpThrpTimeULQci9					Counter32,
		pdcpThrpTimeDL					Counter32,
		pdcpThrpTimeDLQci1					Counter32,
		pdcpThrpTimeDLQci2					Counter32,
		pdcpThrpTimeDLQci3					Counter32,
		pdcpThrpTimeDLQci4					Counter32,
		pdcpThrpTimeDLQci5					Counter32,
		pdcpThrpTimeDLQci6					Counter32,
		pdcpThrpTimeDLQci7					Counter32,
		pdcpThrpTimeDLQci8					Counter32,
		pdcpThrpTimeDLQci9					Counter32
		}


	pdcpThroughputTimeLcId		 OBJECT-TYPE
		SYNTAX					 Integer32( 0 .. 23 )
		MAX-ACCESS			 not-accessible
		STATUS					 current
		DESCRIPTION			 " -- "
		::=  { pdcpThroughputTimeEntry  1 }


	pdcpThroughputTimeRowStatus		 OBJECT-TYPE
		SYNTAX					 RowStatus
		MAX-ACCESS			 read-only
		STATUS					 current
		DESCRIPTION			 " -- "
		::=  { pdcpThroughputTimeEntry  2 }


	pdcpThrpTimeUL		 OBJECT-TYPE
		SYNTAX					 Counter32
		MAX-ACCESS			 read-only
		STATUS					 current
		DESCRIPTION			 " -- "
		::=  { pdcpThroughputTimeEntry  3 }


	pdcpThrpTimeULQci1		 OBJECT-TYPE
		SYNTAX					 Counter32
		MAX-ACCESS			 read-only
		STATUS					 current
		DESCRIPTION			 " -- "
		::=  { pdcpThroughputTimeEntry  4 }


	pdcpThrpTimeULQci2		 OBJECT-TYPE
		SYNTAX					 Counter32
		MAX-ACCESS			 read-only
		STATUS					 current
		DESCRIPTION			 " -- "
		::=  { pdcpThroughputTimeEntry  5 }


	pdcpThrpTimeULQci3		 OBJECT-TYPE
		SYNTAX					 Counter32
		MAX-ACCESS			 read-only
		STATUS					 current
		DESCRIPTION			 " -- "
		::=  { pdcpThroughputTimeEntry  6 }


	pdcpThrpTimeULQci4		 OBJECT-TYPE
		SYNTAX					 Counter32
		MAX-ACCESS			 read-only
		STATUS					 current
		DESCRIPTION			 " -- "
		::=  { pdcpThroughputTimeEntry  7 }


	pdcpThrpTimeULQci5		 OBJECT-TYPE
		SYNTAX					 Counter32
		MAX-ACCESS			 read-only
		STATUS					 current
		DESCRIPTION			 " -- "
		::=  { pdcpThroughputTimeEntry  8 }


	pdcpThrpTimeULQci6		 OBJECT-TYPE
		SYNTAX					 Counter32
		MAX-ACCESS			 read-only
		STATUS					 current
		DESCRIPTION			 " -- "
		::=  { pdcpThroughputTimeEntry  9 }


	pdcpThrpTimeULQci7		 OBJECT-TYPE
		SYNTAX					 Counter32
		MAX-ACCESS			 read-only
		STATUS					 current
		DESCRIPTION			 " -- "
		::=  { pdcpThroughputTimeEntry  10 }


	pdcpThrpTimeULQci8		 OBJECT-TYPE
		SYNTAX					 Counter32
		MAX-ACCESS			 read-only
		STATUS					 current
		DESCRIPTION			 " -- "
		::=  { pdcpThroughputTimeEntry  11 }


	pdcpThrpTimeULQci9		 OBJECT-TYPE
		SYNTAX					 Counter32
		MAX-ACCESS			 read-only
		STATUS					 current
		DESCRIPTION			 " -- "
		::=  { pdcpThroughputTimeEntry  12 }


	pdcpThrpTimeDL		 OBJECT-TYPE
		SYNTAX					 Counter32
		MAX-ACCESS			 read-only
		STATUS					 current
		DESCRIPTION			 " -- "
		::=  { pdcpThroughputTimeEntry  13 }


	pdcpThrpTimeDLQci1		 OBJECT-TYPE
		SYNTAX					 Counter32
		MAX-ACCESS			 read-only
		STATUS					 current
		DESCRIPTION			 " -- "
		::=  { pdcpThroughputTimeEntry  14 }


	pdcpThrpTimeDLQci2		 OBJECT-TYPE
		SYNTAX					 Counter32
		MAX-ACCESS			 read-only
		STATUS					 current
		DESCRIPTION			 " -- "
		::=  { pdcpThroughputTimeEntry  15 }


	pdcpThrpTimeDLQci3		 OBJECT-TYPE
		SYNTAX					 Counter32
		MAX-ACCESS			 read-only
		STATUS					 current
		DESCRIPTION			 " -- "
		::=  { pdcpThroughputTimeEntry  16 }


	pdcpThrpTimeDLQci4		 OBJECT-TYPE
		SYNTAX					 Counter32
		MAX-ACCESS			 read-only
		STATUS					 current
		DESCRIPTION			 " -- "
		::=  { pdcpThroughputTimeEntry  17 }


	pdcpThrpTimeDLQci5		 OBJECT-TYPE
		SYNTAX					 Counter32
		MAX-ACCESS			 read-only
		STATUS					 current
		DESCRIPTION			 " -- "
		::=  { pdcpThroughputTimeEntry  18 }


	pdcpThrpTimeDLQci6		 OBJECT-TYPE
		SYNTAX					 Counter32
		MAX-ACCESS			 read-only
		STATUS					 current
		DESCRIPTION			 " -- "
		::=  { pdcpThroughputTimeEntry  19 }


	pdcpThrpTimeDLQci7		 OBJECT-TYPE
		SYNTAX					 Counter32
		MAX-ACCESS			 read-only
		STATUS					 current
		DESCRIPTION			 " -- "
		::=  { pdcpThroughputTimeEntry  20 }


	pdcpThrpTimeDLQci8		 OBJECT-TYPE
		SYNTAX					 Counter32
		MAX-ACCESS			 read-only
		STATUS					 current
		DESCRIPTION			 " -- "
		::=  { pdcpThroughputTimeEntry  21 }


	pdcpThrpTimeDLQci9		 OBJECT-TYPE
		SYNTAX					 Counter32
		MAX-ACCESS			 read-only
		STATUS					 current
		DESCRIPTION			 " -- "
		::=  { pdcpThroughputTimeEntry  22 }


	erabActiveNumberTable		 OBJECT-TYPE
		SYNTAX					 SEQUENCE  OF	 ErabActiveNumberEntry
		MAX-ACCESS			 not-accessible
		STATUS					 current
		DESCRIPTION			 " -- "
		::=  { macrelatedOriginCounter  11 }


	erabActiveNumberEntry		 OBJECT-TYPE
		SYNTAX					 ErabActiveNumberEntry
		MAX-ACCESS			 not-accessible
		STATUS					 current
		DESCRIPTION			 " -- "
		INDEX						{ erabActiveNumberLcId }
		::=  { erabActiveNumberTable  1 }


	ErabActiveNumberEntry		 ::=  SEQUENCE {
		erabActiveNumberLcId					Integer32,
		erabActiveNumberRowStatus					RowStatus,
		erabActiveMeanNbrDL					Counter32,
		erabActiveMeanNbrDLQci1					Counter32,
		erabActiveMeanNbrDLQci2					Counter32,
		erabActiveMeanNbrDLQci3					Counter32,
		erabActiveMeanNbrDLQci4					Counter32,
		erabActiveMeanNbrDLQci5					Counter32,
		erabActiveMeanNbrDLQci6					Counter32,
		erabActiveMeanNbrDLQci7					Counter32,
		erabActiveMeanNbrDLQci8					Counter32,
		erabActiveMeanNbrDLQci9					Counter32,
		erabActiveMaxNbrDL					Counter32,
		erabActiveMaxNbrDLQci1					Counter32,
		erabActiveMaxNbrDLQci2					Counter32,
		erabActiveMaxNbrDLQci3					Counter32,
		erabActiveMaxNbrDLQci4					Counter32,
		erabActiveMaxNbrDLQci5					Counter32,
		erabActiveMaxNbrDLQci6					Counter32,
		erabActiveMaxNbrDLQci7					Counter32,
		erabActiveMaxNbrDLQci8					Counter32,
		erabActiveMaxNbrDLQci9					Counter32,
		erabActiveMeanNbrUL					Counter32,
		erabActiveMeanNbrULQci1					Counter32,
		erabActiveMeanNbrULQci2					Counter32,
		erabActiveMeanNbrULQci3					Counter32,
		erabActiveMeanNbrULQci4					Counter32,
		erabActiveMeanNbrULQci5					Counter32,
		erabActiveMeanNbrULQci6					Counter32,
		erabActiveMeanNbrULQci7					Counter32,
		erabActiveMeanNbrULQci8					Counter32,
		erabActiveMeanNbrULQci9					Counter32,
		erabActiveMaxNbrUL					Counter32,
		erabActiveMaxNbrULQci1					Counter32,
		erabActiveMaxNbrULQci2					Counter32,
		erabActiveMaxNbrULQci3					Counter32,
		erabActiveMaxNbrULQci4					Counter32,
		erabActiveMaxNbrULQci5					Counter32,
		erabActiveMaxNbrULQci6					Counter32,
		erabActiveMaxNbrULQci7					Counter32,
		erabActiveMaxNbrULQci8					Counter32,
		erabActiveMaxNbrULQci9					Counter32
		}


	erabActiveNumberLcId		 OBJECT-TYPE
		SYNTAX					 Integer32( 0 .. 23 )
		MAX-ACCESS			 not-accessible
		STATUS					 current
		DESCRIPTION			 " -- "
		::=  { erabActiveNumberEntry  1 }


	erabActiveNumberRowStatus		 OBJECT-TYPE
		SYNTAX					 RowStatus
		MAX-ACCESS			 read-only
		STATUS					 current
		DESCRIPTION			 " -- "
		::=  { erabActiveNumberEntry  2 }


	erabActiveMeanNbrDL		 OBJECT-TYPE
		SYNTAX					 Counter32
		MAX-ACCESS			 read-only
		STATUS					 current
		DESCRIPTION			 " -- "
		::=  { erabActiveNumberEntry  3 }


	erabActiveMeanNbrDLQci1		 OBJECT-TYPE
		SYNTAX					 Counter32
		MAX-ACCESS			 read-only
		STATUS					 current
		DESCRIPTION			 " -- "
		::=  { erabActiveNumberEntry  4 }


	erabActiveMeanNbrDLQci2		 OBJECT-TYPE
		SYNTAX					 Counter32
		MAX-ACCESS			 read-only
		STATUS					 current
		DESCRIPTION			 " -- "
		::=  { erabActiveNumberEntry  5 }


	erabActiveMeanNbrDLQci3		 OBJECT-TYPE
		SYNTAX					 Counter32
		MAX-ACCESS			 read-only
		STATUS					 current
		DESCRIPTION			 " -- "
		::=  { erabActiveNumberEntry  6 }


	erabActiveMeanNbrDLQci4		 OBJECT-TYPE
		SYNTAX					 Counter32
		MAX-ACCESS			 read-only
		STATUS					 current
		DESCRIPTION			 " -- "
		::=  { erabActiveNumberEntry  7 }


	erabActiveMeanNbrDLQci5		 OBJECT-TYPE
		SYNTAX					 Counter32
		MAX-ACCESS			 read-only
		STATUS					 current
		DESCRIPTION			 " -- "
		::=  { erabActiveNumberEntry  8 }


	erabActiveMeanNbrDLQci6		 OBJECT-TYPE
		SYNTAX					 Counter32
		MAX-ACCESS			 read-only
		STATUS					 current
		DESCRIPTION			 " -- "
		::=  { erabActiveNumberEntry  9 }


	erabActiveMeanNbrDLQci7		 OBJECT-TYPE
		SYNTAX					 Counter32
		MAX-ACCESS			 read-only
		STATUS					 current
		DESCRIPTION			 " -- "
		::=  { erabActiveNumberEntry  10 }


	erabActiveMeanNbrDLQci8		 OBJECT-TYPE
		SYNTAX					 Counter32
		MAX-ACCESS			 read-only
		STATUS					 current
		DESCRIPTION			 " -- "
		::=  { erabActiveNumberEntry  11 }


	erabActiveMeanNbrDLQci9		 OBJECT-TYPE
		SYNTAX					 Counter32
		MAX-ACCESS			 read-only
		STATUS					 current
		DESCRIPTION			 " -- "
		::=  { erabActiveNumberEntry  12 }


	erabActiveMaxNbrDL		 OBJECT-TYPE
		SYNTAX					 Counter32
		MAX-ACCESS			 read-only
		STATUS					 current
		DESCRIPTION			 " -- "
		::=  { erabActiveNumberEntry  13 }


	erabActiveMaxNbrDLQci1		 OBJECT-TYPE
		SYNTAX					 Counter32
		MAX-ACCESS			 read-only
		STATUS					 current
		DESCRIPTION			 " -- "
		::=  { erabActiveNumberEntry  14 }


	erabActiveMaxNbrDLQci2		 OBJECT-TYPE
		SYNTAX					 Counter32
		MAX-ACCESS			 read-only
		STATUS					 current
		DESCRIPTION			 " -- "
		::=  { erabActiveNumberEntry  15 }


	erabActiveMaxNbrDLQci3		 OBJECT-TYPE
		SYNTAX					 Counter32
		MAX-ACCESS			 read-only
		STATUS					 current
		DESCRIPTION			 " -- "
		::=  { erabActiveNumberEntry  16 }


	erabActiveMaxNbrDLQci4		 OBJECT-TYPE
		SYNTAX					 Counter32
		MAX-ACCESS			 read-only
		STATUS					 current
		DESCRIPTION			 " -- "
		::=  { erabActiveNumberEntry  17 }


	erabActiveMaxNbrDLQci5		 OBJECT-TYPE
		SYNTAX					 Counter32
		MAX-ACCESS			 read-only
		STATUS					 current
		DESCRIPTION			 " -- "
		::=  { erabActiveNumberEntry  18 }


	erabActiveMaxNbrDLQci6		 OBJECT-TYPE
		SYNTAX					 Counter32
		MAX-ACCESS			 read-only
		STATUS					 current
		DESCRIPTION			 " -- "
		::=  { erabActiveNumberEntry  19 }


	erabActiveMaxNbrDLQci7		 OBJECT-TYPE
		SYNTAX					 Counter32
		MAX-ACCESS			 read-only
		STATUS					 current
		DESCRIPTION			 " -- "
		::=  { erabActiveNumberEntry  20 }


	erabActiveMaxNbrDLQci8		 OBJECT-TYPE
		SYNTAX					 Counter32
		MAX-ACCESS			 read-only
		STATUS					 current
		DESCRIPTION			 " -- "
		::=  { erabActiveNumberEntry  21 }


	erabActiveMaxNbrDLQci9		 OBJECT-TYPE
		SYNTAX					 Counter32
		MAX-ACCESS			 read-only
		STATUS					 current
		DESCRIPTION			 " -- "
		::=  { erabActiveNumberEntry  22 }


	erabActiveMeanNbrUL		 OBJECT-TYPE
		SYNTAX					 Counter32
		MAX-ACCESS			 read-only
		STATUS					 current
		DESCRIPTION			 " -- "
		::=  { erabActiveNumberEntry  23 }


	erabActiveMeanNbrULQci1		 OBJECT-TYPE
		SYNTAX					 Counter32
		MAX-ACCESS			 read-only
		STATUS					 current
		DESCRIPTION			 " -- "
		::=  { erabActiveNumberEntry  24 }


	erabActiveMeanNbrULQci2		 OBJECT-TYPE
		SYNTAX					 Counter32
		MAX-ACCESS			 read-only
		STATUS					 current
		DESCRIPTION			 " -- "
		::=  { erabActiveNumberEntry  25 }


	erabActiveMeanNbrULQci3		 OBJECT-TYPE
		SYNTAX					 Counter32
		MAX-ACCESS			 read-only
		STATUS					 current
		DESCRIPTION			 " -- "
		::=  { erabActiveNumberEntry  26 }


	erabActiveMeanNbrULQci4		 OBJECT-TYPE
		SYNTAX					 Counter32
		MAX-ACCESS			 read-only
		STATUS					 current
		DESCRIPTION			 " -- "
		::=  { erabActiveNumberEntry  27 }


	erabActiveMeanNbrULQci5		 OBJECT-TYPE
		SYNTAX					 Counter32
		MAX-ACCESS			 read-only
		STATUS					 current
		DESCRIPTION			 " -- "
		::=  { erabActiveNumberEntry  28 }


	erabActiveMeanNbrULQci6		 OBJECT-TYPE
		SYNTAX					 Counter32
		MAX-ACCESS			 read-only
		STATUS					 current
		DESCRIPTION			 " -- "
		::=  { erabActiveNumberEntry  29 }


	erabActiveMeanNbrULQci7		 OBJECT-TYPE
		SYNTAX					 Counter32
		MAX-ACCESS			 read-only
		STATUS					 current
		DESCRIPTION			 " -- "
		::=  { erabActiveNumberEntry  30 }


	erabActiveMeanNbrULQci8		 OBJECT-TYPE
		SYNTAX					 Counter32
		MAX-ACCESS			 read-only
		STATUS					 current
		DESCRIPTION			 " -- "
		::=  { erabActiveNumberEntry  31 }


	erabActiveMeanNbrULQci9		 OBJECT-TYPE
		SYNTAX					 Counter32
		MAX-ACCESS			 read-only
		STATUS					 current
		DESCRIPTION			 " -- "
		::=  { erabActiveNumberEntry  32 }


	erabActiveMaxNbrUL		 OBJECT-TYPE
		SYNTAX					 Counter32
		MAX-ACCESS			 read-only
		STATUS					 current
		DESCRIPTION			 " -- "
		::=  { erabActiveNumberEntry  33 }


	erabActiveMaxNbrULQci1		 OBJECT-TYPE
		SYNTAX					 Counter32
		MAX-ACCESS			 read-only
		STATUS					 current
		DESCRIPTION			 " -- "
		::=  { erabActiveNumberEntry  34 }


	erabActiveMaxNbrULQci2		 OBJECT-TYPE
		SYNTAX					 Counter32
		MAX-ACCESS			 read-only
		STATUS					 current
		DESCRIPTION			 " -- "
		::=  { erabActiveNumberEntry  35 }


	erabActiveMaxNbrULQci3		 OBJECT-TYPE
		SYNTAX					 Counter32
		MAX-ACCESS			 read-only
		STATUS					 current
		DESCRIPTION			 " -- "
		::=  { erabActiveNumberEntry  36 }


	erabActiveMaxNbrULQci4		 OBJECT-TYPE
		SYNTAX					 Counter32
		MAX-ACCESS			 read-only
		STATUS					 current
		DESCRIPTION			 " -- "
		::=  { erabActiveNumberEntry  37 }


	erabActiveMaxNbrULQci5		 OBJECT-TYPE
		SYNTAX					 Counter32
		MAX-ACCESS			 read-only
		STATUS					 current
		DESCRIPTION			 " -- "
		::=  { erabActiveNumberEntry  38 }


	erabActiveMaxNbrULQci6		 OBJECT-TYPE
		SYNTAX					 Counter32
		MAX-ACCESS			 read-only
		STATUS					 current
		DESCRIPTION			 " -- "
		::=  { erabActiveNumberEntry  39 }


	erabActiveMaxNbrULQci7		 OBJECT-TYPE
		SYNTAX					 Counter32
		MAX-ACCESS			 read-only
		STATUS					 current
		DESCRIPTION			 " -- "
		::=  { erabActiveNumberEntry  40 }


	erabActiveMaxNbrULQci8		 OBJECT-TYPE
		SYNTAX					 Counter32
		MAX-ACCESS			 read-only
		STATUS					 current
		DESCRIPTION			 " -- "
		::=  { erabActiveNumberEntry  41 }


	erabActiveMaxNbrULQci9		 OBJECT-TYPE
		SYNTAX					 Counter32
		MAX-ACCESS			 read-only
		STATUS					 current
		DESCRIPTION			 " -- "
		::=  { erabActiveNumberEntry  42 }


	volteSchedulingTable		 OBJECT-TYPE
		SYNTAX					 SEQUENCE  OF	 VolteSchedulingEntry
		MAX-ACCESS			 not-accessible
		STATUS					 current
		DESCRIPTION			 " -- "
		::=  { macrelatedOriginCounter  12 }


	volteSchedulingEntry		 OBJECT-TYPE
		SYNTAX					 VolteSchedulingEntry
		MAX-ACCESS			 not-accessible
		STATUS					 current
		DESCRIPTION			 " -- "
		INDEX						{ volteSchedulingLcId }
		::=  { volteSchedulingTable  1 }


	VolteSchedulingEntry		 ::=  SEQUENCE {
		volteSchedulingLcId					Integer32,
		volteSchedulingRowStatus					RowStatus,
		macNbrSpsTbUlQci1					Counter32,
		macNbrSpsTbDlQci1					Counter32,
		macNbrTbUlQci1					Counter32,
		macNbrTbDlQci1					Counter32,
		macNbrInitTbUlQci1					Counter32,
		macNbrInitTbDlQci1					Counter32,
		macUlScheTimesQCI1					Counter32,
		macDlScheTimesQCI1					Counter32,
		macSpsPrbUl					Counter32,
		macSpsPrbDl					Counter32,
		macNbrSuccInitTbUlQpskQci1					Counter32,
		macNbrSuccInitTbUl16QamQci1					Counter32,
		macNbrSuccInitTbUl64QamQci1					Counter32,
		macNbrSuccInitTbDlQpskQci1					Counter32,
		macNbrSuccInitTbDl16QamQci1					Counter32,
		macNbrSuccInitTbDl64QamQci1					Counter32,
		macNbrTbUlQci2					Counter32,
		macNbrTbDlQci2					Counter32
		}


	volteSchedulingLcId		 OBJECT-TYPE
		SYNTAX					 Integer32( 0 .. 23 )
		MAX-ACCESS			 not-accessible
		STATUS					 current
		DESCRIPTION			 " -- "
		::=  { volteSchedulingEntry  1 }


	volteSchedulingRowStatus		 OBJECT-TYPE
		SYNTAX					 RowStatus
		MAX-ACCESS			 read-only
		STATUS					 current
		DESCRIPTION			 " -- "
		::=  { volteSchedulingEntry  2 }


	macNbrSpsTbUlQci1		 OBJECT-TYPE
		SYNTAX					 Counter32
		MAX-ACCESS			 read-only
		STATUS					 current
		DESCRIPTION			 " -- "
		::=  { volteSchedulingEntry  3 }


	macNbrSpsTbDlQci1		 OBJECT-TYPE
		SYNTAX					 Counter32
		MAX-ACCESS			 read-only
		STATUS					 current
		DESCRIPTION			 " -- "
		::=  { volteSchedulingEntry  4 }


	macNbrTbUlQci1		 OBJECT-TYPE
		SYNTAX					 Counter32
		MAX-ACCESS			 read-only
		STATUS					 current
		DESCRIPTION			 " -- "
		::=  { volteSchedulingEntry  5 }


	macNbrTbDlQci1		 OBJECT-TYPE
		SYNTAX					 Counter32
		MAX-ACCESS			 read-only
		STATUS					 current
		DESCRIPTION			 " -- "
		::=  { volteSchedulingEntry  6 }


	macNbrInitTbUlQci1		 OBJECT-TYPE
		SYNTAX					 Counter32
		MAX-ACCESS			 read-only
		STATUS					 current
		DESCRIPTION			 " -- "
		::=  { volteSchedulingEntry  7 }


	macNbrInitTbDlQci1		 OBJECT-TYPE
		SYNTAX					 Counter32
		MAX-ACCESS			 read-only
		STATUS					 current
		DESCRIPTION			 " -- "
		::=  { volteSchedulingEntry  8 }


	macUlScheTimesQCI1		 OBJECT-TYPE
		SYNTAX					 Counter32
		MAX-ACCESS			 read-only
		STATUS					 current
		DESCRIPTION			 " -- "
		::=  { volteSchedulingEntry  9 }


	macDlScheTimesQCI1		 OBJECT-TYPE
		SYNTAX					 Counter32
		MAX-ACCESS			 read-only
		STATUS					 current
		DESCRIPTION			 " -- "
		::=  { volteSchedulingEntry  10 }


	macSpsPrbUl		 OBJECT-TYPE
		SYNTAX					 Counter32
		MAX-ACCESS			 read-only
		STATUS					 current
		DESCRIPTION			 " -- "
		::=  { volteSchedulingEntry  11 }


	macSpsPrbDl		 OBJECT-TYPE
		SYNTAX					 Counter32
		MAX-ACCESS			 read-only
		STATUS					 current
		DESCRIPTION			 " -- "
		::=  { volteSchedulingEntry  12 }


	macNbrSuccInitTbUlQpskQci1		 OBJECT-TYPE
		SYNTAX					 Counter32
		MAX-ACCESS			 read-only
		STATUS					 current
		DESCRIPTION			 " -- "
		::=  { volteSchedulingEntry  13 }


	macNbrSuccInitTbUl16QamQci1		 OBJECT-TYPE
		SYNTAX					 Counter32
		MAX-ACCESS			 read-only
		STATUS					 current
		DESCRIPTION			 " -- "
		::=  { volteSchedulingEntry  14 }


	macNbrSuccInitTbUl64QamQci1		 OBJECT-TYPE
		SYNTAX					 Counter32
		MAX-ACCESS			 read-only
		STATUS					 current
		DESCRIPTION			 " -- "
		::=  { volteSchedulingEntry  15 }


	macNbrSuccInitTbDlQpskQci1		 OBJECT-TYPE
		SYNTAX					 Counter32
		MAX-ACCESS			 read-only
		STATUS					 current
		DESCRIPTION			 " -- "
		::=  { volteSchedulingEntry  16 }


	macNbrSuccInitTbDl16QamQci1		 OBJECT-TYPE
		SYNTAX					 Counter32
		MAX-ACCESS			 read-only
		STATUS					 current
		DESCRIPTION			 " -- "
		::=  { volteSchedulingEntry  17 }


	macNbrSuccInitTbDl64QamQci1		 OBJECT-TYPE
		SYNTAX					 Counter32
		MAX-ACCESS			 read-only
		STATUS					 current
		DESCRIPTION			 " -- "
		::=  { volteSchedulingEntry  18 }


	macNbrTbUlQci2		 OBJECT-TYPE
		SYNTAX					 Counter32
		MAX-ACCESS			 read-only
		STATUS					 current
		DESCRIPTION			 " -- "
		::=  { volteSchedulingEntry  19 }


	macNbrTbDlQci2		 OBJECT-TYPE
		SYNTAX					 Counter32
		MAX-ACCESS			 read-only
		STATUS					 current
		DESCRIPTION			 " -- "
		::=  { volteSchedulingEntry  20 }


	caPerformanceTable		 OBJECT-TYPE
		SYNTAX					 SEQUENCE  OF	 CaPerformanceEntry
		MAX-ACCESS			 not-accessible
		STATUS					 current
		DESCRIPTION			 " -- "
		::=  { macrelatedOriginCounter  13 }


	caPerformanceEntry		 OBJECT-TYPE
		SYNTAX					 CaPerformanceEntry
		MAX-ACCESS			 not-accessible
		STATUS					 current
		DESCRIPTION			 " -- "
		INDEX						{ caPerformanceLcId }
		::=  { caPerformanceTable  1 }


	CaPerformanceEntry		 ::=  SEQUENCE {
		caPerformanceLcId					Integer32,
		caPerformanceRowStatus					RowStatus,
		rruBorrowFromScellPrbTotDl					Counter32,
		rruLendToPCellPrbTotDl					Counter32,
		rrcActiveMeanNbrPCellDl2CC					Counter32,
		rrcActiveMaxNbrPCellDl2CC					Counter32,
		rrcAdmissionConnTot					Counter32,
		rrcAdmissionConnSampNum					Counter32,
		rrcAdmisssionConnMax					Counter32,
		rruBorrowFromScellPrbTotUl					Counter32,
		rruLendToPCellPrbTotUl					Counter32,
		rrcActiveNbrPCellDl2CC					Counter32,
		macCaActiveSampNbr					Counter32,
		macCASCellActiveAtt					Counter32,
		macCASCellActiveSucc					Counter32,
		macCASCellDeactiveAtt					Counter32,
		macCASCellDeactiveSucc					Counter32,
		macCaActivePrbPCellDl					Counter32,
		macCaActiveTtiPCellDl					Counter32,
		macThrpTimeCaActiveDL2CC					Counter32,
		macCaActiveMacThruPCellDl					Counter32,
		macCaActivePrbPSCellDl					Counter32,
		macCaActiveNbrSCellDl					Counter32,
		macCaActiveMaxNbrSCellDl					Counter32,
		macCaActiveNbrPCellUl2CC					Counter32,
		macCaActiveMaxNbrPCellUl2CC					Counter32,
		macCaActiveNbrSCellUl					Counter32,
		macCaActiveMaxNbrSCellUl					Counter32,
		macCaActivePrbPCellUl					Counter32,
		macCaActiveTtiPCellUl					Counter32,
		macCaActivePrbPSCellUl					Counter32,
		macThrpTimeCaActiveUL2CC					Counter32,
		macCaActiveMacThruPCellUl					Counter32,
		macCaActiveBurstDataThruPCellUl2CC					Counter32,
		macCaActiveThrpTimeUL2CC					Counter32,
		rrcActiveNbrPCellDl2CCTF					Counter32,
		rrcActiveMaxNbrPCellDl2CCTF					Counter32,
		rruBorrowFromScellPrbTotDlTF					Counter32,
		rruLendToPCellPrbTotDlTF					Counter32,
		rruBorrowFromScellPrbTotUlTF					Counter32,
		rruLendToPCellPrbTotUlTF					Counter32,
		rrcActiveNbrPCellDl3CC					Counter32,
		rrcActiveMaxNbrPCellDl3CC					Counter32,
		macCaActiveMacThruSCellUl					Counter32,
		macCaActiveMacThruSCellDl					Counter32
		}


	caPerformanceLcId		 OBJECT-TYPE
		SYNTAX					 Integer32( 0 .. 23 )
		MAX-ACCESS			 not-accessible
		STATUS					 current
		DESCRIPTION			 " -- "
		::=  { caPerformanceEntry  1 }


	caPerformanceRowStatus		 OBJECT-TYPE
		SYNTAX					 RowStatus
		MAX-ACCESS			 read-only
		STATUS					 current
		DESCRIPTION			 " -- "
		::=  { caPerformanceEntry  2 }


	rruBorrowFromScellPrbTotDl		 OBJECT-TYPE
		SYNTAX					 Counter32
		MAX-ACCESS			 read-only
		STATUS					 current
		DESCRIPTION			 " -- "
		::=  { caPerformanceEntry  3 }


	rruLendToPCellPrbTotDl		 OBJECT-TYPE
		SYNTAX					 Counter32
		MAX-ACCESS			 read-only
		STATUS					 current
		DESCRIPTION			 " -- "
		::=  { caPerformanceEntry  4 }


	rrcActiveMeanNbrPCellDl2CC		 OBJECT-TYPE
		SYNTAX					 Counter32
		MAX-ACCESS			 read-only
		STATUS					 current
		DESCRIPTION			 " -- "
		::=  { caPerformanceEntry  5 }


	rrcActiveMaxNbrPCellDl2CC		 OBJECT-TYPE
		SYNTAX					 Counter32
		MAX-ACCESS			 read-only
		STATUS					 current
		DESCRIPTION			 " -- "
		::=  { caPerformanceEntry  6 }


	rrcAdmissionConnTot		 OBJECT-TYPE
		SYNTAX					 Counter32
		MAX-ACCESS			 read-only
		STATUS					 current
		DESCRIPTION			 " -- "
		::=  { caPerformanceEntry  7 }


	rrcAdmissionConnSampNum		 OBJECT-TYPE
		SYNTAX					 Counter32
		MAX-ACCESS			 read-only
		STATUS					 current
		DESCRIPTION			 " -- "
		::=  { caPerformanceEntry  8 }


	rrcAdmisssionConnMax		 OBJECT-TYPE
		SYNTAX					 Counter32
		MAX-ACCESS			 read-only
		STATUS					 current
		DESCRIPTION			 " -- "
		::=  { caPerformanceEntry  9 }


	rruBorrowFromScellPrbTotUl		 OBJECT-TYPE
		SYNTAX					 Counter32
		MAX-ACCESS			 read-only
		STATUS					 current
		DESCRIPTION			 " -- "
		::=  { caPerformanceEntry  10 }


	rruLendToPCellPrbTotUl		 OBJECT-TYPE
		SYNTAX					 Counter32
		MAX-ACCESS			 read-only
		STATUS					 current
		DESCRIPTION			 " -- "
		::=  { caPerformanceEntry  11 }


	rrcActiveNbrPCellDl2CC		 OBJECT-TYPE
		SYNTAX					 Counter32
		MAX-ACCESS			 read-only
		STATUS					 current
		DESCRIPTION			 " -- "
		::=  { caPerformanceEntry  12 }


	macCaActiveSampNbr		 OBJECT-TYPE
		SYNTAX					 Counter32
		MAX-ACCESS			 read-only
		STATUS					 current
		DESCRIPTION			 " -- "
		::=  { caPerformanceEntry  13 }


	macCASCellActiveAtt		 OBJECT-TYPE
		SYNTAX					 Counter32
		MAX-ACCESS			 read-only
		STATUS					 current
		DESCRIPTION			 " -- "
		::=  { caPerformanceEntry  14 }


	macCASCellActiveSucc		 OBJECT-TYPE
		SYNTAX					 Counter32
		MAX-ACCESS			 read-only
		STATUS					 current
		DESCRIPTION			 " -- "
		::=  { caPerformanceEntry  15 }


	macCASCellDeactiveAtt		 OBJECT-TYPE
		SYNTAX					 Counter32
		MAX-ACCESS			 read-only
		STATUS					 current
		DESCRIPTION			 " -- "
		::=  { caPerformanceEntry  16 }


	macCASCellDeactiveSucc		 OBJECT-TYPE
		SYNTAX					 Counter32
		MAX-ACCESS			 read-only
		STATUS					 current
		DESCRIPTION			 " -- "
		::=  { caPerformanceEntry  17 }


	macCaActivePrbPCellDl		 OBJECT-TYPE
		SYNTAX					 Counter32
		MAX-ACCESS			 read-only
		STATUS					 current
		DESCRIPTION			 " -- "
		::=  { caPerformanceEntry  18 }


	macCaActiveTtiPCellDl		 OBJECT-TYPE
		SYNTAX					 Counter32
		MAX-ACCESS			 read-only
		STATUS					 current
		DESCRIPTION			 " -- "
		::=  { caPerformanceEntry  19 }


	macThrpTimeCaActiveDL2CC		 OBJECT-TYPE
		SYNTAX					 Counter32
		MAX-ACCESS			 read-only
		STATUS					 current
		DESCRIPTION			 " -- "
		::=  { caPerformanceEntry  20 }


	macCaActiveMacThruPCellDl		 OBJECT-TYPE
		SYNTAX					 Counter32
		MAX-ACCESS			 read-only
		STATUS					 current
		DESCRIPTION			 " -- "
		::=  { caPerformanceEntry  21 }


	macCaActivePrbPSCellDl		 OBJECT-TYPE
		SYNTAX					 Counter32
		MAX-ACCESS			 read-only
		STATUS					 current
		DESCRIPTION			 " -- "
		::=  { caPerformanceEntry  22 }


	macCaActiveNbrSCellDl		 OBJECT-TYPE
		SYNTAX					 Counter32
		MAX-ACCESS			 read-only
		STATUS					 current
		DESCRIPTION			 " -- "
		::=  { caPerformanceEntry  23 }


	macCaActiveMaxNbrSCellDl		 OBJECT-TYPE
		SYNTAX					 Counter32
		MAX-ACCESS			 read-only
		STATUS					 current
		DESCRIPTION			 " -- "
		::=  { caPerformanceEntry  24 }


	macCaActiveNbrPCellUl2CC		 OBJECT-TYPE
		SYNTAX					 Counter32
		MAX-ACCESS			 read-only
		STATUS					 current
		DESCRIPTION			 " -- "
		::=  { caPerformanceEntry  25 }


	macCaActiveMaxNbrPCellUl2CC		 OBJECT-TYPE
		SYNTAX					 Counter32
		MAX-ACCESS			 read-only
		STATUS					 current
		DESCRIPTION			 " -- "
		::=  { caPerformanceEntry  26 }


	macCaActiveNbrSCellUl		 OBJECT-TYPE
		SYNTAX					 Counter32
		MAX-ACCESS			 read-only
		STATUS					 current
		DESCRIPTION			 " -- "
		::=  { caPerformanceEntry  27 }


	macCaActiveMaxNbrSCellUl		 OBJECT-TYPE
		SYNTAX					 Counter32
		MAX-ACCESS			 read-only
		STATUS					 current
		DESCRIPTION			 " -- "
		::=  { caPerformanceEntry  28 }


	macCaActivePrbPCellUl		 OBJECT-TYPE
		SYNTAX					 Counter32
		MAX-ACCESS			 read-only
		STATUS					 current
		DESCRIPTION			 " -- "
		::=  { caPerformanceEntry  29 }


	macCaActiveTtiPCellUl		 OBJECT-TYPE
		SYNTAX					 Counter32
		MAX-ACCESS			 read-only
		STATUS					 current
		DESCRIPTION			 " -- "
		::=  { caPerformanceEntry  30 }


	macCaActivePrbPSCellUl		 OBJECT-TYPE
		SYNTAX					 Counter32
		MAX-ACCESS			 read-only
		STATUS					 current
		DESCRIPTION			 " -- "
		::=  { caPerformanceEntry  31 }


	macThrpTimeCaActiveUL2CC		 OBJECT-TYPE
		SYNTAX					 Counter32
		MAX-ACCESS			 read-only
		STATUS					 current
		DESCRIPTION			 " -- "
		::=  { caPerformanceEntry  32 }


	macCaActiveMacThruPCellUl		 OBJECT-TYPE
		SYNTAX					 Counter32
		MAX-ACCESS			 read-only
		STATUS					 current
		DESCRIPTION			 " -- "
		::=  { caPerformanceEntry  33 }


	macCaActiveBurstDataThruPCellUl2CC		 OBJECT-TYPE
		SYNTAX					 Counter32
		MAX-ACCESS			 read-only
		STATUS					 current
		DESCRIPTION			 " -- "
		::=  { caPerformanceEntry  34 }


	macCaActiveThrpTimeUL2CC		 OBJECT-TYPE
		SYNTAX					 Counter32
		MAX-ACCESS			 read-only
		STATUS					 current
		DESCRIPTION			 " -- "
		::=  { caPerformanceEntry  35 }


	rrcActiveNbrPCellDl2CCTF		 OBJECT-TYPE
		SYNTAX					 Counter32
		MAX-ACCESS			 read-only
		STATUS					 current
		DESCRIPTION			 " -- "
		::=  { caPerformanceEntry  36 }


	rrcActiveMaxNbrPCellDl2CCTF		 OBJECT-TYPE
		SYNTAX					 Counter32
		MAX-ACCESS			 read-only
		STATUS					 current
		DESCRIPTION			 " -- "
		::=  { caPerformanceEntry  37 }


	rruBorrowFromScellPrbTotDlTF		 OBJECT-TYPE
		SYNTAX					 Counter32
		MAX-ACCESS			 read-only
		STATUS					 current
		DESCRIPTION			 " -- "
		::=  { caPerformanceEntry  38 }


	rruLendToPCellPrbTotDlTF		 OBJECT-TYPE
		SYNTAX					 Counter32
		MAX-ACCESS			 read-only
		STATUS					 current
		DESCRIPTION			 " -- "
		::=  { caPerformanceEntry  39 }


	rruBorrowFromScellPrbTotUlTF		 OBJECT-TYPE
		SYNTAX					 Counter32
		MAX-ACCESS			 read-only
		STATUS					 current
		DESCRIPTION			 " -- "
		::=  { caPerformanceEntry  40 }


	rruLendToPCellPrbTotUlTF		 OBJECT-TYPE
		SYNTAX					 Counter32
		MAX-ACCESS			 read-only
		STATUS					 current
		DESCRIPTION			 " -- "
		::=  { caPerformanceEntry  41 }


	rrcActiveNbrPCellDl3CC		 OBJECT-TYPE
		SYNTAX					 Counter32
		MAX-ACCESS			 read-only
		STATUS					 current
		DESCRIPTION			 " -- "
		::=  { caPerformanceEntry  42 }


	rrcActiveMaxNbrPCellDl3CC		 OBJECT-TYPE
		SYNTAX					 Counter32
		MAX-ACCESS			 read-only
		STATUS					 current
		DESCRIPTION			 " -- "
		::=  { caPerformanceEntry  43 }


	macCaActiveMacThruSCellUl		 OBJECT-TYPE
		SYNTAX					 Counter32
		MAX-ACCESS			 read-only
		STATUS					 current
		DESCRIPTION			 " -- "
		::=  { caPerformanceEntry  44 }


	macCaActiveMacThruSCellDl		 OBJECT-TYPE
		SYNTAX					 Counter32
		MAX-ACCESS			 read-only
		STATUS					 current
		DESCRIPTION			 " -- "
		::=  { caPerformanceEntry  45 }


	scheUEPerTTITable		 OBJECT-TYPE
		SYNTAX					 SEQUENCE  OF	 ScheUEPerTTIEntry
		MAX-ACCESS			 not-accessible
		STATUS					 current
		DESCRIPTION			 " -- "
		::=  { macrelatedOriginCounter  14 }


	scheUEPerTTIEntry		 OBJECT-TYPE
		SYNTAX					 ScheUEPerTTIEntry
		MAX-ACCESS			 not-accessible
		STATUS					 current
		DESCRIPTION			 " -- "
		INDEX						{ scheUEPerTTILcId }
		::=  { scheUEPerTTITable  1 }


	ScheUEPerTTIEntry		 ::=  SEQUENCE {
		scheUEPerTTILcId					Integer32,
		scheUEPerTTIRowStatus					RowStatus,
		macMaxSchUeUl					Counter32,
		macMaxSchUeDl					Counter32
		}


	scheUEPerTTILcId		 OBJECT-TYPE
		SYNTAX					 Integer32( 0 .. 23 )
		MAX-ACCESS			 not-accessible
		STATUS					 current
		DESCRIPTION			 " -- "
		::=  { scheUEPerTTIEntry  1 }


	scheUEPerTTIRowStatus		 OBJECT-TYPE
		SYNTAX					 RowStatus
		MAX-ACCESS			 read-only
		STATUS					 current
		DESCRIPTION			 " -- "
		::=  { scheUEPerTTIEntry  2 }


	macMaxSchUeUl		 OBJECT-TYPE
		SYNTAX					 Counter32
		MAX-ACCESS			 read-only
		STATUS					 current
		DESCRIPTION			 " -- "
		::=  { scheUEPerTTIEntry  3 }


	macMaxSchUeDl		 OBJECT-TYPE
		SYNTAX					 Counter32
		MAX-ACCESS			 read-only
		STATUS					 current
		DESCRIPTION			 " -- "
		::=  { scheUEPerTTIEntry  4 }


	ipThpUlTable		 OBJECT-TYPE
		SYNTAX					 SEQUENCE  OF	 IpThpUlEntry
		MAX-ACCESS			 not-accessible
		STATUS					 current
		DESCRIPTION			 " -- "
		::=  { macrelatedOriginCounter  15 }


	ipThpUlEntry		 OBJECT-TYPE
		SYNTAX					 IpThpUlEntry
		MAX-ACCESS			 not-accessible
		STATUS					 current
		DESCRIPTION			 " -- "
		INDEX						{ ipThpUlLcId }
		::=  { ipThpUlTable  1 }


	IpThpUlEntry		 ::=  SEQUENCE {
		ipThpUlLcId					Integer32,
		ipThpUlRowStatus					RowStatus,
		erabThpTimeUlSum					Counter32,
		erabThpTimeUlQci1					Counter32,
		erabThpTimeUlQci2					Counter32,
		erabThpTimeUlQci3					Counter32,
		erabThpTimeUlQci4					Counter32,
		erabThpTimeUlQci5					Counter32,
		erabThpTimeUlQci6					Counter32,
		erabThpTimeUlQci7					Counter32,
		erabThpTimeUlQci8					Counter32,
		erabThpTimeUlQci9					Counter32,
		drbBurstDataThpULSum					Counter32,
		drbBurstDataThpULQci1					Counter32,
		drbBurstDataThpULQci2					Counter32,
		drbBurstDataThpULQci3					Counter32,
		drbBurstDataThpULQci4					Counter32,
		drbBurstDataThpULQci5					Counter32,
		drbBurstDataThpULQci6					Counter32,
		drbBurstDataThpULQci7					Counter32,
		drbBurstDataThpULQci8					Counter32,
		drbBurstDataThpULQci9					Counter32
		}


	ipThpUlLcId		 OBJECT-TYPE
		SYNTAX					 Integer32( 0 .. 23 )
		MAX-ACCESS			 not-accessible
		STATUS					 current
		DESCRIPTION			 " -- "
		::=  { ipThpUlEntry  1 }


	ipThpUlRowStatus		 OBJECT-TYPE
		SYNTAX					 RowStatus
		MAX-ACCESS			 read-only
		STATUS					 current
		DESCRIPTION			 " -- "
		::=  { ipThpUlEntry  2 }


	erabThpTimeUlSum		 OBJECT-TYPE
		SYNTAX					 Counter32
		MAX-ACCESS			 read-only
		STATUS					 current
		DESCRIPTION			 " -- "
		::=  { ipThpUlEntry  3 }


	erabThpTimeUlQci1		 OBJECT-TYPE
		SYNTAX					 Counter32
		MAX-ACCESS			 read-only
		STATUS					 current
		DESCRIPTION			 " -- "
		::=  { ipThpUlEntry  4 }


	erabThpTimeUlQci2		 OBJECT-TYPE
		SYNTAX					 Counter32
		MAX-ACCESS			 read-only
		STATUS					 current
		DESCRIPTION			 " -- "
		::=  { ipThpUlEntry  5 }


	erabThpTimeUlQci3		 OBJECT-TYPE
		SYNTAX					 Counter32
		MAX-ACCESS			 read-only
		STATUS					 current
		DESCRIPTION			 " -- "
		::=  { ipThpUlEntry  6 }


	erabThpTimeUlQci4		 OBJECT-TYPE
		SYNTAX					 Counter32
		MAX-ACCESS			 read-only
		STATUS					 current
		DESCRIPTION			 " -- "
		::=  { ipThpUlEntry  7 }


	erabThpTimeUlQci5		 OBJECT-TYPE
		SYNTAX					 Counter32
		MAX-ACCESS			 read-only
		STATUS					 current
		DESCRIPTION			 " -- "
		::=  { ipThpUlEntry  8 }


	erabThpTimeUlQci6		 OBJECT-TYPE
		SYNTAX					 Counter32
		MAX-ACCESS			 read-only
		STATUS					 current
		DESCRIPTION			 " -- "
		::=  { ipThpUlEntry  9 }


	erabThpTimeUlQci7		 OBJECT-TYPE
		SYNTAX					 Counter32
		MAX-ACCESS			 read-only
		STATUS					 current
		DESCRIPTION			 " -- "
		::=  { ipThpUlEntry  10 }


	erabThpTimeUlQci8		 OBJECT-TYPE
		SYNTAX					 Counter32
		MAX-ACCESS			 read-only
		STATUS					 current
		DESCRIPTION			 " -- "
		::=  { ipThpUlEntry  11 }


	erabThpTimeUlQci9		 OBJECT-TYPE
		SYNTAX					 Counter32
		MAX-ACCESS			 read-only
		STATUS					 current
		DESCRIPTION			 " -- "
		::=  { ipThpUlEntry  12 }


	drbBurstDataThpULSum		 OBJECT-TYPE
		SYNTAX					 Counter32
		MAX-ACCESS			 read-only
		STATUS					 current
		DESCRIPTION			 " -- "
		::=  { ipThpUlEntry  13 }


	drbBurstDataThpULQci1		 OBJECT-TYPE
		SYNTAX					 Counter32
		MAX-ACCESS			 read-only
		STATUS					 current
		DESCRIPTION			 " -- "
		::=  { ipThpUlEntry  14 }


	drbBurstDataThpULQci2		 OBJECT-TYPE
		SYNTAX					 Counter32
		MAX-ACCESS			 read-only
		STATUS					 current
		DESCRIPTION			 " -- "
		::=  { ipThpUlEntry  15 }


	drbBurstDataThpULQci3		 OBJECT-TYPE
		SYNTAX					 Counter32
		MAX-ACCESS			 read-only
		STATUS					 current
		DESCRIPTION			 " -- "
		::=  { ipThpUlEntry  16 }


	drbBurstDataThpULQci4		 OBJECT-TYPE
		SYNTAX					 Counter32
		MAX-ACCESS			 read-only
		STATUS					 current
		DESCRIPTION			 " -- "
		::=  { ipThpUlEntry  17 }


	drbBurstDataThpULQci5		 OBJECT-TYPE
		SYNTAX					 Counter32
		MAX-ACCESS			 read-only
		STATUS					 current
		DESCRIPTION			 " -- "
		::=  { ipThpUlEntry  18 }


	drbBurstDataThpULQci6		 OBJECT-TYPE
		SYNTAX					 Counter32
		MAX-ACCESS			 read-only
		STATUS					 current
		DESCRIPTION			 " -- "
		::=  { ipThpUlEntry  19 }


	drbBurstDataThpULQci7		 OBJECT-TYPE
		SYNTAX					 Counter32
		MAX-ACCESS			 read-only
		STATUS					 current
		DESCRIPTION			 " -- "
		::=  { ipThpUlEntry  20 }


	drbBurstDataThpULQci8		 OBJECT-TYPE
		SYNTAX					 Counter32
		MAX-ACCESS			 read-only
		STATUS					 current
		DESCRIPTION			 " -- "
		::=  { ipThpUlEntry  21 }


	drbBurstDataThpULQci9		 OBJECT-TYPE
		SYNTAX					 Counter32
		MAX-ACCESS			 read-only
		STATUS					 current
		DESCRIPTION			 " -- "
		::=  { ipThpUlEntry  22 }


	compPerformanceTable		 OBJECT-TYPE
		SYNTAX					 SEQUENCE  OF	 CompPerformanceEntry
		MAX-ACCESS			 not-accessible
		STATUS					 current
		DESCRIPTION			 " -- "
		::=  { macrelatedOriginCounter  16 }


	compPerformanceEntry		 OBJECT-TYPE
		SYNTAX					 CompPerformanceEntry
		MAX-ACCESS			 not-accessible
		STATUS					 current
		DESCRIPTION			 " -- "
		INDEX						{ compPerformanceLcId }
		::=  { compPerformanceTable  1 }


	CompPerformanceEntry		 ::=  SEQUENCE {
		compPerformanceLcId					Integer32,
		compPerformanceRowStatus					RowStatus,
		rruCompPrbTotUl					Counter32,
		rruCompPrbTotDl					Counter32,
		rruCompSfnDl					Counter32,
		rruCompCsDlGBR					Counter32,
		rruCompCsDlNonGBR					Counter32,
		pdcpCompThrputDl					Counter32,
		rruJRSfn					Counter32,
		rruJRUsrGBR					Counter32,
		rruJRUsrNonGBR					Counter32,
		pdcpJRThrput					Counter32
		}


	compPerformanceLcId		 OBJECT-TYPE
		SYNTAX					 Integer32( 0 .. 23 )
		MAX-ACCESS			 not-accessible
		STATUS					 current
		DESCRIPTION			 " -- "
		::=  { compPerformanceEntry  1 }


	compPerformanceRowStatus		 OBJECT-TYPE
		SYNTAX					 RowStatus
		MAX-ACCESS			 read-only
		STATUS					 current
		DESCRIPTION			 " -- "
		::=  { compPerformanceEntry  2 }


	rruCompPrbTotUl		 OBJECT-TYPE
		SYNTAX					 Counter32
		MAX-ACCESS			 read-only
		STATUS					 current
		DESCRIPTION			 " -- "
		::=  { compPerformanceEntry  3 }


	rruCompPrbTotDl		 OBJECT-TYPE
		SYNTAX					 Counter32
		MAX-ACCESS			 read-only
		STATUS					 current
		DESCRIPTION			 " -- "
		::=  { compPerformanceEntry  4 }


	rruCompSfnDl		 OBJECT-TYPE
		SYNTAX					 Counter32
		MAX-ACCESS			 read-only
		STATUS					 current
		DESCRIPTION			 " -- "
		::=  { compPerformanceEntry  5 }


	rruCompCsDlGBR		 OBJECT-TYPE
		SYNTAX					 Counter32
		MAX-ACCESS			 read-only
		STATUS					 current
		DESCRIPTION			 " -- "
		::=  { compPerformanceEntry  6 }


	rruCompCsDlNonGBR		 OBJECT-TYPE
		SYNTAX					 Counter32
		MAX-ACCESS			 read-only
		STATUS					 current
		DESCRIPTION			 " -- "
		::=  { compPerformanceEntry  7 }


	pdcpCompThrputDl		 OBJECT-TYPE
		SYNTAX					 Counter32
		MAX-ACCESS			 read-only
		STATUS					 current
		DESCRIPTION			 " -- "
		::=  { compPerformanceEntry  8 }


	rruJRSfn		 OBJECT-TYPE
		SYNTAX					 Counter32
		MAX-ACCESS			 read-only
		STATUS					 current
		DESCRIPTION			 " -- "
		::=  { compPerformanceEntry  9 }


	rruJRUsrGBR		 OBJECT-TYPE
		SYNTAX					 Counter32
		MAX-ACCESS			 read-only
		STATUS					 current
		DESCRIPTION			 " -- "
		::=  { compPerformanceEntry  10 }


	rruJRUsrNonGBR		 OBJECT-TYPE
		SYNTAX					 Counter32
		MAX-ACCESS			 read-only
		STATUS					 current
		DESCRIPTION			 " -- "
		::=  { compPerformanceEntry  11 }


	pdcpJRThrput		 OBJECT-TYPE
		SYNTAX					 Counter32
		MAX-ACCESS			 read-only
		STATUS					 current
		DESCRIPTION			 " -- "
		::=  { compPerformanceEntry  12 }


	taPerformanceTable		 OBJECT-TYPE
		SYNTAX					 SEQUENCE  OF	 TaPerformanceEntry
		MAX-ACCESS			 not-accessible
		STATUS					 current
		DESCRIPTION			 " -- "
		::=  { macrelatedOriginCounter  17 }


	taPerformanceEntry		 OBJECT-TYPE
		SYNTAX					 TaPerformanceEntry
		MAX-ACCESS			 not-accessible
		STATUS					 current
		DESCRIPTION			 " -- "
		INDEX						{ taPerformanceLcId }
		::=  { taPerformanceTable  1 }


	TaPerformanceEntry		 ::=  SEQUENCE {
		taPerformanceLcId					Integer32,
		taPerformanceRowStatus					RowStatus,
		phyTA0					Counter32,
		phyTA1					Counter32,
		phyTA2					Counter32,
		phyTA3					Counter32,
		phyTA4					Counter32,
		phyTA5					Counter32,
		phyTA6					Counter32,
		phyTA7					Counter32,
		phyTA8					Counter32,
		phyTA9					Counter32,
		phyTA10					Counter32,
		phyTA11					Counter32,
		phyTAMax					Counter32
		}


	taPerformanceLcId		 OBJECT-TYPE
		SYNTAX					 Integer32( 0 .. 23 )
		MAX-ACCESS			 not-accessible
		STATUS					 current
		DESCRIPTION			 " -- "
		::=  { taPerformanceEntry  1 }


	taPerformanceRowStatus		 OBJECT-TYPE
		SYNTAX					 RowStatus
		MAX-ACCESS			 read-only
		STATUS					 current
		DESCRIPTION			 " -- "
		::=  { taPerformanceEntry  2 }


	phyTA0		 OBJECT-TYPE
		SYNTAX					 Counter32
		MAX-ACCESS			 read-only
		STATUS					 current
		DESCRIPTION			 " -- "
		::=  { taPerformanceEntry  3 }


	phyTA1		 OBJECT-TYPE
		SYNTAX					 Counter32
		MAX-ACCESS			 read-only
		STATUS					 current
		DESCRIPTION			 " -- "
		::=  { taPerformanceEntry  4 }


	phyTA2		 OBJECT-TYPE
		SYNTAX					 Counter32
		MAX-ACCESS			 read-only
		STATUS					 current
		DESCRIPTION			 " -- "
		::=  { taPerformanceEntry  5 }


	phyTA3		 OBJECT-TYPE
		SYNTAX					 Counter32
		MAX-ACCESS			 read-only
		STATUS					 current
		DESCRIPTION			 " -- "
		::=  { taPerformanceEntry  6 }


	phyTA4		 OBJECT-TYPE
		SYNTAX					 Counter32
		MAX-ACCESS			 read-only
		STATUS					 current
		DESCRIPTION			 " -- "
		::=  { taPerformanceEntry  7 }


	phyTA5		 OBJECT-TYPE
		SYNTAX					 Counter32
		MAX-ACCESS			 read-only
		STATUS					 current
		DESCRIPTION			 " -- "
		::=  { taPerformanceEntry  8 }


	phyTA6		 OBJECT-TYPE
		SYNTAX					 Counter32
		MAX-ACCESS			 read-only
		STATUS					 current
		DESCRIPTION			 " -- "
		::=  { taPerformanceEntry  9 }


	phyTA7		 OBJECT-TYPE
		SYNTAX					 Counter32
		MAX-ACCESS			 read-only
		STATUS					 current
		DESCRIPTION			 " -- "
		::=  { taPerformanceEntry  10 }


	phyTA8		 OBJECT-TYPE
		SYNTAX					 Counter32
		MAX-ACCESS			 read-only
		STATUS					 current
		DESCRIPTION			 " -- "
		::=  { taPerformanceEntry  11 }


	phyTA9		 OBJECT-TYPE
		SYNTAX					 Counter32
		MAX-ACCESS			 read-only
		STATUS					 current
		DESCRIPTION			 " -- "
		::=  { taPerformanceEntry  12 }


	phyTA10		 OBJECT-TYPE
		SYNTAX					 Counter32
		MAX-ACCESS			 read-only
		STATUS					 current
		DESCRIPTION			 " -- "
		::=  { taPerformanceEntry  13 }


	phyTA11		 OBJECT-TYPE
		SYNTAX					 Counter32
		MAX-ACCESS			 read-only
		STATUS					 current
		DESCRIPTION			 " -- "
		::=  { taPerformanceEntry  14 }


	phyTAMax		 OBJECT-TYPE
		SYNTAX					 Counter32
		MAX-ACCESS			 read-only
		STATUS					 current
		DESCRIPTION			 " -- "
		::=  { taPerformanceEntry  15 }


	dlrbStatisticTable		 OBJECT-TYPE
		SYNTAX					 SEQUENCE  OF	 DlrbStatisticEntry
		MAX-ACCESS			 not-accessible
		STATUS					 current
		DESCRIPTION			 " -- "
		::=  { macrelatedOriginCounter  18 }


	dlrbStatisticEntry		 OBJECT-TYPE
		SYNTAX					 DlrbStatisticEntry
		MAX-ACCESS			 not-accessible
		STATUS					 current
		DESCRIPTION			 " -- "
		INDEX						{ dlrbStatisticLcId }
		::=  { dlrbStatisticTable  1 }


	DlrbStatisticEntry		 ::=  SEQUENCE {
		dlrbStatisticLcId					Integer32,
		dlrbStatisticRowStatus					RowStatus,
		macNbrRbDlTm2					Counter32,
		macNbrRbDlTm3SFBC					Counter32,
		macNbrRbDlTm3SM					Counter32,
		macNbrRbDlTm8SFBC					Counter32,
		macNbrRbDlTm8RANK1BF					Counter32,
		macNbrRbDlTm8RANK2BF					Counter32,
		macNbrRbDlTm7SFBC					Counter32,
		macNbrRbDlTm7BF					Counter32,
		macNbrRbDlUnused					Counter32,
		macNbrRbDlPBCH					Counter32,
		macNbrRbDlTm9SFBC					Counter32,
		macNbrRbDlTm9RANK1BF					Counter32,
		macNbrRbDlTm9RANK2BF					Counter32,
		macNbrRbDlTm9RANK3BF					Counter32,
		macNbrRbDlTm9RANK4BF					Counter32,
		macNbrRbDlTm4SFBC					Counter32,
		macNbrRbDlTm4SM					Counter32
		}


	dlrbStatisticLcId		 OBJECT-TYPE
		SYNTAX					 Integer32( 0 .. 23 )
		MAX-ACCESS			 not-accessible
		STATUS					 current
		DESCRIPTION			 " -- "
		::=  { dlrbStatisticEntry  1 }


	dlrbStatisticRowStatus		 OBJECT-TYPE
		SYNTAX					 RowStatus
		MAX-ACCESS			 read-only
		STATUS					 current
		DESCRIPTION			 " -- "
		::=  { dlrbStatisticEntry  2 }


	macNbrRbDlTm2		 OBJECT-TYPE
		SYNTAX					 Counter32
		MAX-ACCESS			 read-only
		STATUS					 current
		DESCRIPTION			 " -- "
		::=  { dlrbStatisticEntry  3 }


	macNbrRbDlTm3SFBC		 OBJECT-TYPE
		SYNTAX					 Counter32
		MAX-ACCESS			 read-only
		STATUS					 current
		DESCRIPTION			 " -- "
		::=  { dlrbStatisticEntry  4 }


	macNbrRbDlTm3SM		 OBJECT-TYPE
		SYNTAX					 Counter32
		MAX-ACCESS			 read-only
		STATUS					 current
		DESCRIPTION			 " -- "
		::=  { dlrbStatisticEntry  5 }


	macNbrRbDlTm8SFBC		 OBJECT-TYPE
		SYNTAX					 Counter32
		MAX-ACCESS			 read-only
		STATUS					 current
		DESCRIPTION			 " -- "
		::=  { dlrbStatisticEntry  6 }


	macNbrRbDlTm8RANK1BF		 OBJECT-TYPE
		SYNTAX					 Counter32
		MAX-ACCESS			 read-only
		STATUS					 current
		DESCRIPTION			 " -- "
		::=  { dlrbStatisticEntry  7 }


	macNbrRbDlTm8RANK2BF		 OBJECT-TYPE
		SYNTAX					 Counter32
		MAX-ACCESS			 read-only
		STATUS					 current
		DESCRIPTION			 " -- "
		::=  { dlrbStatisticEntry  8 }


	macNbrRbDlTm7SFBC		 OBJECT-TYPE
		SYNTAX					 Counter32
		MAX-ACCESS			 read-only
		STATUS					 current
		DESCRIPTION			 " -- "
		::=  { dlrbStatisticEntry  9 }


	macNbrRbDlTm7BF		 OBJECT-TYPE
		SYNTAX					 Counter32
		MAX-ACCESS			 read-only
		STATUS					 current
		DESCRIPTION			 " -- "
		::=  { dlrbStatisticEntry  10 }


	macNbrRbDlUnused		 OBJECT-TYPE
		SYNTAX					 Counter32
		MAX-ACCESS			 read-only
		STATUS					 current
		DESCRIPTION			 " -- "
		::=  { dlrbStatisticEntry  11 }


	macNbrRbDlPBCH		 OBJECT-TYPE
		SYNTAX					 Counter32
		MAX-ACCESS			 read-only
		STATUS					 current
		DESCRIPTION			 " -- "
		::=  { dlrbStatisticEntry  12 }


	macNbrRbDlTm9SFBC		 OBJECT-TYPE
		SYNTAX					 Counter32
		MAX-ACCESS			 read-only
		STATUS					 current
		DESCRIPTION			 " -- "
		::=  { dlrbStatisticEntry  13 }


	macNbrRbDlTm9RANK1BF		 OBJECT-TYPE
		SYNTAX					 Counter32
		MAX-ACCESS			 read-only
		STATUS					 current
		DESCRIPTION			 " -- "
		::=  { dlrbStatisticEntry  14 }


	macNbrRbDlTm9RANK2BF		 OBJECT-TYPE
		SYNTAX					 Counter32
		MAX-ACCESS			 read-only
		STATUS					 current
		DESCRIPTION			 " -- "
		::=  { dlrbStatisticEntry  15 }


	macNbrRbDlTm9RANK3BF		 OBJECT-TYPE
		SYNTAX					 Counter32
		MAX-ACCESS			 read-only
		STATUS					 current
		DESCRIPTION			 " -- "
		::=  { dlrbStatisticEntry  16 }


	macNbrRbDlTm9RANK4BF		 OBJECT-TYPE
		SYNTAX					 Counter32
		MAX-ACCESS			 read-only
		STATUS					 current
		DESCRIPTION			 " -- "
		::=  { dlrbStatisticEntry  17 }


	macNbrRbDlTm4SFBC		 OBJECT-TYPE
		SYNTAX					 Counter32
		MAX-ACCESS			 read-only
		STATUS					 current
		DESCRIPTION			 " -- "
		::=  { dlrbStatisticEntry  18 }


	macNbrRbDlTm4SM		 OBJECT-TYPE
		SYNTAX					 Counter32
		MAX-ACCESS			 read-only
		STATUS					 current
		DESCRIPTION			 " -- "
		::=  { dlrbStatisticEntry  19 }


	cellCompStatisticTable		 OBJECT-TYPE
		SYNTAX					 SEQUENCE  OF	 CellCompStatisticEntry
		MAX-ACCESS			 not-accessible
		STATUS					 current
		DESCRIPTION			 " -- "
		::=  { macrelatedOriginCounter  19 }


	cellCompStatisticEntry		 OBJECT-TYPE
		SYNTAX					 CellCompStatisticEntry
		MAX-ACCESS			 not-accessible
		STATUS					 current
		DESCRIPTION			 " -- "
		INDEX						{ cellCompStatisticNetLcComponentLcId,cellCompStatisticNetLcComponentIndex }
		::=  { cellCompStatisticTable  1 }


	CellCompStatisticEntry		 ::=  SEQUENCE {
		cellCompStatisticNetLcComponentLcId					Integer32,
		cellCompStatisticNetLcComponentIndex					Integer32,
		cellCompStatisticRowStatus					RowStatus,
		macCellCompThrpUl					Counter32,
		macCellCompThrpDl					Counter32,
		macCellCompUeNumQci1					Counter32,
		macCellCompUeNumQci2					Counter32,
		macCellCompUeNumQci3					Counter32,
		macCellCompUeNumQci4					Counter32,
		macCellCompUeNumQci5					Counter32,
		macCellCompUeNumQci6					Counter32,
		macCellCompUeNumQci7					Counter32,
		macCellCompUeNumQci8					Counter32,
		macCellCompUeNumQci9					Counter32,
		macCellCompUeNum					Counter32,
		macCellCompSampNum					Counter32
		}


	cellCompStatisticNetLcComponentLcId		 OBJECT-TYPE
		SYNTAX					 Integer32( 0 .. 23 )
		MAX-ACCESS			 not-accessible
		STATUS					 current
		DESCRIPTION			 " -- "
		::=  { cellCompStatisticEntry  1 }


	cellCompStatisticNetLcComponentIndex		 OBJECT-TYPE
		SYNTAX					 Integer32( 0 .. 11 )
		MAX-ACCESS			 not-accessible
		STATUS					 current
		DESCRIPTION			 " -- "
		::=  { cellCompStatisticEntry  2 }


	cellCompStatisticRowStatus		 OBJECT-TYPE
		SYNTAX					 RowStatus
		MAX-ACCESS			 read-only
		STATUS					 current
		DESCRIPTION			 " -- "
		::=  { cellCompStatisticEntry  3 }


	macCellCompThrpUl		 OBJECT-TYPE
		SYNTAX					 Counter32
		MAX-ACCESS			 read-only
		STATUS					 current
		DESCRIPTION			 " -- "
		::=  { cellCompStatisticEntry  4 }


	macCellCompThrpDl		 OBJECT-TYPE
		SYNTAX					 Counter32
		MAX-ACCESS			 read-only
		STATUS					 current
		DESCRIPTION			 " -- "
		::=  { cellCompStatisticEntry  5 }


	macCellCompUeNumQci1		 OBJECT-TYPE
		SYNTAX					 Counter32
		MAX-ACCESS			 read-only
		STATUS					 current
		DESCRIPTION			 " -- "
		::=  { cellCompStatisticEntry  6 }


	macCellCompUeNumQci2		 OBJECT-TYPE
		SYNTAX					 Counter32
		MAX-ACCESS			 read-only
		STATUS					 current
		DESCRIPTION			 " -- "
		::=  { cellCompStatisticEntry  7 }


	macCellCompUeNumQci3		 OBJECT-TYPE
		SYNTAX					 Counter32
		MAX-ACCESS			 read-only
		STATUS					 current
		DESCRIPTION			 " -- "
		::=  { cellCompStatisticEntry  8 }


	macCellCompUeNumQci4		 OBJECT-TYPE
		SYNTAX					 Counter32
		MAX-ACCESS			 read-only
		STATUS					 current
		DESCRIPTION			 " -- "
		::=  { cellCompStatisticEntry  9 }


	macCellCompUeNumQci5		 OBJECT-TYPE
		SYNTAX					 Counter32
		MAX-ACCESS			 read-only
		STATUS					 current
		DESCRIPTION			 " -- "
		::=  { cellCompStatisticEntry  10 }


	macCellCompUeNumQci6		 OBJECT-TYPE
		SYNTAX					 Counter32
		MAX-ACCESS			 read-only
		STATUS					 current
		DESCRIPTION			 " -- "
		::=  { cellCompStatisticEntry  11 }


	macCellCompUeNumQci7		 OBJECT-TYPE
		SYNTAX					 Counter32
		MAX-ACCESS			 read-only
		STATUS					 current
		DESCRIPTION			 " -- "
		::=  { cellCompStatisticEntry  12 }


	macCellCompUeNumQci8		 OBJECT-TYPE
		SYNTAX					 Counter32
		MAX-ACCESS			 read-only
		STATUS					 current
		DESCRIPTION			 " -- "
		::=  { cellCompStatisticEntry  13 }


	macCellCompUeNumQci9		 OBJECT-TYPE
		SYNTAX					 Counter32
		MAX-ACCESS			 read-only
		STATUS					 current
		DESCRIPTION			 " -- "
		::=  { cellCompStatisticEntry  14 }


	macCellCompUeNum		 OBJECT-TYPE
		SYNTAX					 Counter32
		MAX-ACCESS			 read-only
		STATUS					 current
		DESCRIPTION			 " -- "
		::=  { cellCompStatisticEntry  15 }


	macCellCompSampNum		 OBJECT-TYPE
		SYNTAX					 Counter32
		MAX-ACCESS			 read-only
		STATUS					 current
		DESCRIPTION			 " -- "
		::=  { cellCompStatisticEntry  16 }


	scheTimesAcoordingMCSTable		 OBJECT-TYPE
		SYNTAX					 SEQUENCE  OF	 ScheTimesAcoordingMCSEntry
		MAX-ACCESS			 not-accessible
		STATUS					 current
		DESCRIPTION			 " -- "
		::=  { macrelatedOriginCounter  20 }


	scheTimesAcoordingMCSEntry		 OBJECT-TYPE
		SYNTAX					 ScheTimesAcoordingMCSEntry
		MAX-ACCESS			 not-accessible
		STATUS					 current
		DESCRIPTION			 " -- "
		INDEX						{ scheTimesAcoordingMCSLcId }
		::=  { scheTimesAcoordingMCSTable  1 }


	ScheTimesAcoordingMCSEntry		 ::=  SEQUENCE {
		scheTimesAcoordingMCSLcId					Integer32,
		scheTimesAcoordingMCSRowStatus					RowStatus,
		nbrschetimesulMcs0					Counter32,
		nbrschetimesulMcs1					Counter32,
		nbrschetimesulMcs2					Counter32,
		nbrschetimesulMcs3					Counter32,
		nbrschetimesulMcs4					Counter32,
		nbrschetimesulMcs5					Counter32,
		nbrschetimesulMcs6					Counter32,
		nbrschetimesulMcs7					Counter32,
		nbrschetimesulMcs8					Counter32,
		nbrschetimesulMcs9					Counter32,
		nbrschetimesulMcs10					Counter32,
		nbrschetimesulMcs11					Counter32,
		nbrschetimesulMcs12					Counter32,
		nbrschetimesulMcs13					Counter32,
		nbrschetimesulMcs14					Counter32,
		nbrschetimesulMcs15					Counter32,
		nbrschetimesulMcs16					Counter32,
		nbrschetimesulMcs17					Counter32,
		nbrschetimesulMcs18					Counter32,
		nbrschetimesulMcs19					Counter32,
		nbrschetimesulMcs20					Counter32,
		nbrschetimesulMcs21					Counter32,
		nbrschetimesulMcs22					Counter32,
		nbrschetimesulMcs23					Counter32,
		nbrschetimesulMcs24					Counter32,
		nbrschetimesulMcs25					Counter32,
		nbrschetimesulMcs26					Counter32,
		nbrschetimesulMcs27					Counter32,
		nbrschetimesulMcs28					Counter32,
		nbrschetimesdlMcs0					Counter32,
		nbrschetimesdlMcs1					Counter32,
		nbrschetimesdlMcs2					Counter32,
		nbrschetimesdlMcs3					Counter32,
		nbrschetimesdlMcs4					Counter32,
		nbrschetimesdlMcs5					Counter32,
		nbrschetimesdlMcs6					Counter32,
		nbrschetimesdlMcs7					Counter32,
		nbrschetimesdlMcs8					Counter32,
		nbrschetimesdlMcs9					Counter32,
		nbrschetimesdlMcs10					Counter32,
		nbrschetimesdlMcs11					Counter32,
		nbrschetimesdlMcs12					Counter32,
		nbrschetimesdlMcs13					Counter32,
		nbrschetimesdlMcs14					Counter32,
		nbrschetimesdlMcs15					Counter32,
		nbrschetimesdlMcs16					Counter32,
		nbrschetimesdlMcs17					Counter32,
		nbrschetimesdlMcs18					Counter32,
		nbrschetimesdlMcs19					Counter32,
		nbrschetimesdlMcs20					Counter32,
		nbrschetimesdlMcs21					Counter32,
		nbrschetimesdlMcs22					Counter32,
		nbrschetimesdlMcs23					Counter32,
		nbrschetimesdlMcs24					Counter32,
		nbrschetimesdlMcs25					Counter32,
		nbrschetimesdlMcs26					Counter32,
		nbrschetimesdlMcs27					Counter32,
		nbrschetimesdlMcs28					Counter32,
		nbrschetimesdlMcs29					Counter32,
		nbrschetimesdlMcs30					Counter32,
		nbrschetimesdlMcs31					Counter32
		}


	scheTimesAcoordingMCSLcId		 OBJECT-TYPE
		SYNTAX					 Integer32( 0 .. 23 )
		MAX-ACCESS			 not-accessible
		STATUS					 current
		DESCRIPTION			 " -- "
		::=  { scheTimesAcoordingMCSEntry  1 }


	scheTimesAcoordingMCSRowStatus		 OBJECT-TYPE
		SYNTAX					 RowStatus
		MAX-ACCESS			 read-only
		STATUS					 current
		DESCRIPTION			 " -- "
		::=  { scheTimesAcoordingMCSEntry  2 }


	nbrschetimesulMcs0		 OBJECT-TYPE
		SYNTAX					 Counter32
		MAX-ACCESS			 read-only
		STATUS					 current
		DESCRIPTION			 " -- "
		::=  { scheTimesAcoordingMCSEntry  3 }


	nbrschetimesulMcs1		 OBJECT-TYPE
		SYNTAX					 Counter32
		MAX-ACCESS			 read-only
		STATUS					 current
		DESCRIPTION			 " -- "
		::=  { scheTimesAcoordingMCSEntry  4 }


	nbrschetimesulMcs2		 OBJECT-TYPE
		SYNTAX					 Counter32
		MAX-ACCESS			 read-only
		STATUS					 current
		DESCRIPTION			 " -- "
		::=  { scheTimesAcoordingMCSEntry  5 }


	nbrschetimesulMcs3		 OBJECT-TYPE
		SYNTAX					 Counter32
		MAX-ACCESS			 read-only
		STATUS					 current
		DESCRIPTION			 " -- "
		::=  { scheTimesAcoordingMCSEntry  6 }


	nbrschetimesulMcs4		 OBJECT-TYPE
		SYNTAX					 Counter32
		MAX-ACCESS			 read-only
		STATUS					 current
		DESCRIPTION			 " -- "
		::=  { scheTimesAcoordingMCSEntry  7 }


	nbrschetimesulMcs5		 OBJECT-TYPE
		SYNTAX					 Counter32
		MAX-ACCESS			 read-only
		STATUS					 current
		DESCRIPTION			 " -- "
		::=  { scheTimesAcoordingMCSEntry  8 }


	nbrschetimesulMcs6		 OBJECT-TYPE
		SYNTAX					 Counter32
		MAX-ACCESS			 read-only
		STATUS					 current
		DESCRIPTION			 " -- "
		::=  { scheTimesAcoordingMCSEntry  9 }


	nbrschetimesulMcs7		 OBJECT-TYPE
		SYNTAX					 Counter32
		MAX-ACCESS			 read-only
		STATUS					 current
		DESCRIPTION			 " -- "
		::=  { scheTimesAcoordingMCSEntry  10 }


	nbrschetimesulMcs8		 OBJECT-TYPE
		SYNTAX					 Counter32
		MAX-ACCESS			 read-only
		STATUS					 current
		DESCRIPTION			 " -- "
		::=  { scheTimesAcoordingMCSEntry  11 }


	nbrschetimesulMcs9		 OBJECT-TYPE
		SYNTAX					 Counter32
		MAX-ACCESS			 read-only
		STATUS					 current
		DESCRIPTION			 " -- "
		::=  { scheTimesAcoordingMCSEntry  12 }


	nbrschetimesulMcs10		 OBJECT-TYPE
		SYNTAX					 Counter32
		MAX-ACCESS			 read-only
		STATUS					 current
		DESCRIPTION			 " -- "
		::=  { scheTimesAcoordingMCSEntry  13 }


	nbrschetimesulMcs11		 OBJECT-TYPE
		SYNTAX					 Counter32
		MAX-ACCESS			 read-only
		STATUS					 current
		DESCRIPTION			 " -- "
		::=  { scheTimesAcoordingMCSEntry  14 }


	nbrschetimesulMcs12		 OBJECT-TYPE
		SYNTAX					 Counter32
		MAX-ACCESS			 read-only
		STATUS					 current
		DESCRIPTION			 " -- "
		::=  { scheTimesAcoordingMCSEntry  15 }


	nbrschetimesulMcs13		 OBJECT-TYPE
		SYNTAX					 Counter32
		MAX-ACCESS			 read-only
		STATUS					 current
		DESCRIPTION			 " -- "
		::=  { scheTimesAcoordingMCSEntry  16 }


	nbrschetimesulMcs14		 OBJECT-TYPE
		SYNTAX					 Counter32
		MAX-ACCESS			 read-only
		STATUS					 current
		DESCRIPTION			 " -- "
		::=  { scheTimesAcoordingMCSEntry  17 }


	nbrschetimesulMcs15		 OBJECT-TYPE
		SYNTAX					 Counter32
		MAX-ACCESS			 read-only
		STATUS					 current
		DESCRIPTION			 " -- "
		::=  { scheTimesAcoordingMCSEntry  18 }


	nbrschetimesulMcs16		 OBJECT-TYPE
		SYNTAX					 Counter32
		MAX-ACCESS			 read-only
		STATUS					 current
		DESCRIPTION			 " -- "
		::=  { scheTimesAcoordingMCSEntry  19 }


	nbrschetimesulMcs17		 OBJECT-TYPE
		SYNTAX					 Counter32
		MAX-ACCESS			 read-only
		STATUS					 current
		DESCRIPTION			 " -- "
		::=  { scheTimesAcoordingMCSEntry  20 }


	nbrschetimesulMcs18		 OBJECT-TYPE
		SYNTAX					 Counter32
		MAX-ACCESS			 read-only
		STATUS					 current
		DESCRIPTION			 " -- "
		::=  { scheTimesAcoordingMCSEntry  21 }


	nbrschetimesulMcs19		 OBJECT-TYPE
		SYNTAX					 Counter32
		MAX-ACCESS			 read-only
		STATUS					 current
		DESCRIPTION			 " -- "
		::=  { scheTimesAcoordingMCSEntry  22 }


	nbrschetimesulMcs20		 OBJECT-TYPE
		SYNTAX					 Counter32
		MAX-ACCESS			 read-only
		STATUS					 current
		DESCRIPTION			 " -- "
		::=  { scheTimesAcoordingMCSEntry  23 }


	nbrschetimesulMcs21		 OBJECT-TYPE
		SYNTAX					 Counter32
		MAX-ACCESS			 read-only
		STATUS					 current
		DESCRIPTION			 " -- "
		::=  { scheTimesAcoordingMCSEntry  24 }


	nbrschetimesulMcs22		 OBJECT-TYPE
		SYNTAX					 Counter32
		MAX-ACCESS			 read-only
		STATUS					 current
		DESCRIPTION			 " -- "
		::=  { scheTimesAcoordingMCSEntry  25 }


	nbrschetimesulMcs23		 OBJECT-TYPE
		SYNTAX					 Counter32
		MAX-ACCESS			 read-only
		STATUS					 current
		DESCRIPTION			 " -- "
		::=  { scheTimesAcoordingMCSEntry  26 }


	nbrschetimesulMcs24		 OBJECT-TYPE
		SYNTAX					 Counter32
		MAX-ACCESS			 read-only
		STATUS					 current
		DESCRIPTION			 " -- "
		::=  { scheTimesAcoordingMCSEntry  27 }


	nbrschetimesulMcs25		 OBJECT-TYPE
		SYNTAX					 Counter32
		MAX-ACCESS			 read-only
		STATUS					 current
		DESCRIPTION			 " -- "
		::=  { scheTimesAcoordingMCSEntry  28 }


	nbrschetimesulMcs26		 OBJECT-TYPE
		SYNTAX					 Counter32
		MAX-ACCESS			 read-only
		STATUS					 current
		DESCRIPTION			 " -- "
		::=  { scheTimesAcoordingMCSEntry  29 }


	nbrschetimesulMcs27		 OBJECT-TYPE
		SYNTAX					 Counter32
		MAX-ACCESS			 read-only
		STATUS					 current
		DESCRIPTION			 " -- "
		::=  { scheTimesAcoordingMCSEntry  30 }


	nbrschetimesulMcs28		 OBJECT-TYPE
		SYNTAX					 Counter32
		MAX-ACCESS			 read-only
		STATUS					 current
		DESCRIPTION			 " -- "
		::=  { scheTimesAcoordingMCSEntry  31 }


	nbrschetimesdlMcs0		 OBJECT-TYPE
		SYNTAX					 Counter32
		MAX-ACCESS			 read-only
		STATUS					 current
		DESCRIPTION			 " -- "
		::=  { scheTimesAcoordingMCSEntry  32 }


	nbrschetimesdlMcs1		 OBJECT-TYPE
		SYNTAX					 Counter32
		MAX-ACCESS			 read-only
		STATUS					 current
		DESCRIPTION			 " -- "
		::=  { scheTimesAcoordingMCSEntry  33 }


	nbrschetimesdlMcs2		 OBJECT-TYPE
		SYNTAX					 Counter32
		MAX-ACCESS			 read-only
		STATUS					 current
		DESCRIPTION			 " -- "
		::=  { scheTimesAcoordingMCSEntry  34 }


	nbrschetimesdlMcs3		 OBJECT-TYPE
		SYNTAX					 Counter32
		MAX-ACCESS			 read-only
		STATUS					 current
		DESCRIPTION			 " -- "
		::=  { scheTimesAcoordingMCSEntry  35 }


	nbrschetimesdlMcs4		 OBJECT-TYPE
		SYNTAX					 Counter32
		MAX-ACCESS			 read-only
		STATUS					 current
		DESCRIPTION			 " -- "
		::=  { scheTimesAcoordingMCSEntry  36 }


	nbrschetimesdlMcs5		 OBJECT-TYPE
		SYNTAX					 Counter32
		MAX-ACCESS			 read-only
		STATUS					 current
		DESCRIPTION			 " -- "
		::=  { scheTimesAcoordingMCSEntry  37 }


	nbrschetimesdlMcs6		 OBJECT-TYPE
		SYNTAX					 Counter32
		MAX-ACCESS			 read-only
		STATUS					 current
		DESCRIPTION			 " -- "
		::=  { scheTimesAcoordingMCSEntry  38 }


	nbrschetimesdlMcs7		 OBJECT-TYPE
		SYNTAX					 Counter32
		MAX-ACCESS			 read-only
		STATUS					 current
		DESCRIPTION			 " -- "
		::=  { scheTimesAcoordingMCSEntry  39 }


	nbrschetimesdlMcs8		 OBJECT-TYPE
		SYNTAX					 Counter32
		MAX-ACCESS			 read-only
		STATUS					 current
		DESCRIPTION			 " -- "
		::=  { scheTimesAcoordingMCSEntry  40 }


	nbrschetimesdlMcs9		 OBJECT-TYPE
		SYNTAX					 Counter32
		MAX-ACCESS			 read-only
		STATUS					 current
		DESCRIPTION			 " -- "
		::=  { scheTimesAcoordingMCSEntry  41 }


	nbrschetimesdlMcs10		 OBJECT-TYPE
		SYNTAX					 Counter32
		MAX-ACCESS			 read-only
		STATUS					 current
		DESCRIPTION			 " -- "
		::=  { scheTimesAcoordingMCSEntry  42 }


	nbrschetimesdlMcs11		 OBJECT-TYPE
		SYNTAX					 Counter32
		MAX-ACCESS			 read-only
		STATUS					 current
		DESCRIPTION			 " -- "
		::=  { scheTimesAcoordingMCSEntry  43 }


	nbrschetimesdlMcs12		 OBJECT-TYPE
		SYNTAX					 Counter32
		MAX-ACCESS			 read-only
		STATUS					 current
		DESCRIPTION			 " -- "
		::=  { scheTimesAcoordingMCSEntry  44 }


	nbrschetimesdlMcs13		 OBJECT-TYPE
		SYNTAX					 Counter32
		MAX-ACCESS			 read-only
		STATUS					 current
		DESCRIPTION			 " -- "
		::=  { scheTimesAcoordingMCSEntry  45 }


	nbrschetimesdlMcs14		 OBJECT-TYPE
		SYNTAX					 Counter32
		MAX-ACCESS			 read-only
		STATUS					 current
		DESCRIPTION			 " -- "
		::=  { scheTimesAcoordingMCSEntry  46 }


	nbrschetimesdlMcs15		 OBJECT-TYPE
		SYNTAX					 Counter32
		MAX-ACCESS			 read-only
		STATUS					 current
		DESCRIPTION			 " -- "
		::=  { scheTimesAcoordingMCSEntry  47 }


	nbrschetimesdlMcs16		 OBJECT-TYPE
		SYNTAX					 Counter32
		MAX-ACCESS			 read-only
		STATUS					 current
		DESCRIPTION			 " -- "
		::=  { scheTimesAcoordingMCSEntry  48 }


	nbrschetimesdlMcs17		 OBJECT-TYPE
		SYNTAX					 Counter32
		MAX-ACCESS			 read-only
		STATUS					 current
		DESCRIPTION			 " -- "
		::=  { scheTimesAcoordingMCSEntry  49 }


	nbrschetimesdlMcs18		 OBJECT-TYPE
		SYNTAX					 Counter32
		MAX-ACCESS			 read-only
		STATUS					 current
		DESCRIPTION			 " -- "
		::=  { scheTimesAcoordingMCSEntry  50 }


	nbrschetimesdlMcs19		 OBJECT-TYPE
		SYNTAX					 Counter32
		MAX-ACCESS			 read-only
		STATUS					 current
		DESCRIPTION			 " -- "
		::=  { scheTimesAcoordingMCSEntry  51 }


	nbrschetimesdlMcs20		 OBJECT-TYPE
		SYNTAX					 Counter32
		MAX-ACCESS			 read-only
		STATUS					 current
		DESCRIPTION			 " -- "
		::=  { scheTimesAcoordingMCSEntry  52 }


	nbrschetimesdlMcs21		 OBJECT-TYPE
		SYNTAX					 Counter32
		MAX-ACCESS			 read-only
		STATUS					 current
		DESCRIPTION			 " -- "
		::=  { scheTimesAcoordingMCSEntry  53 }


	nbrschetimesdlMcs22		 OBJECT-TYPE
		SYNTAX					 Counter32
		MAX-ACCESS			 read-only
		STATUS					 current
		DESCRIPTION			 " -- "
		::=  { scheTimesAcoordingMCSEntry  54 }


	nbrschetimesdlMcs23		 OBJECT-TYPE
		SYNTAX					 Counter32
		MAX-ACCESS			 read-only
		STATUS					 current
		DESCRIPTION			 " -- "
		::=  { scheTimesAcoordingMCSEntry  55 }


	nbrschetimesdlMcs24		 OBJECT-TYPE
		SYNTAX					 Counter32
		MAX-ACCESS			 read-only
		STATUS					 current
		DESCRIPTION			 " -- "
		::=  { scheTimesAcoordingMCSEntry  56 }


	nbrschetimesdlMcs25		 OBJECT-TYPE
		SYNTAX					 Counter32
		MAX-ACCESS			 read-only
		STATUS					 current
		DESCRIPTION			 " -- "
		::=  { scheTimesAcoordingMCSEntry  57 }


	nbrschetimesdlMcs26		 OBJECT-TYPE
		SYNTAX					 Counter32
		MAX-ACCESS			 read-only
		STATUS					 current
		DESCRIPTION			 " -- "
		::=  { scheTimesAcoordingMCSEntry  58 }


	nbrschetimesdlMcs27		 OBJECT-TYPE
		SYNTAX					 Counter32
		MAX-ACCESS			 read-only
		STATUS					 current
		DESCRIPTION			 " -- "
		::=  { scheTimesAcoordingMCSEntry  59 }


	nbrschetimesdlMcs28		 OBJECT-TYPE
		SYNTAX					 Counter32
		MAX-ACCESS			 read-only
		STATUS					 current
		DESCRIPTION			 " -- "
		::=  { scheTimesAcoordingMCSEntry  60 }


	nbrschetimesdlMcs29		 OBJECT-TYPE
		SYNTAX					 Counter32
		MAX-ACCESS			 read-only
		STATUS					 current
		DESCRIPTION			 " -- "
		::=  { scheTimesAcoordingMCSEntry  61 }


	nbrschetimesdlMcs30		 OBJECT-TYPE
		SYNTAX					 Counter32
		MAX-ACCESS			 read-only
		STATUS					 current
		DESCRIPTION			 " -- "
		::=  { scheTimesAcoordingMCSEntry  62 }


	nbrschetimesdlMcs31		 OBJECT-TYPE
		SYNTAX					 Counter32
		MAX-ACCESS			 read-only
		STATUS					 current
		DESCRIPTION			 " -- "
		::=  { scheTimesAcoordingMCSEntry  63 }


	schePrbAcoordingMCSTable		 OBJECT-TYPE
		SYNTAX					 SEQUENCE  OF	 SchePrbAcoordingMCSEntry
		MAX-ACCESS			 not-accessible
		STATUS					 current
		DESCRIPTION			 " -- "
		::=  { macrelatedOriginCounter  21 }


	schePrbAcoordingMCSEntry		 OBJECT-TYPE
		SYNTAX					 SchePrbAcoordingMCSEntry
		MAX-ACCESS			 not-accessible
		STATUS					 current
		DESCRIPTION			 " -- "
		INDEX						{ schePrbAcoordingMCSLcId }
		::=  { schePrbAcoordingMCSTable  1 }


	SchePrbAcoordingMCSEntry		 ::=  SEQUENCE {
		schePrbAcoordingMCSLcId					Integer32,
		schePrbAcoordingMCSRowStatus					RowStatus,
		nbrscheprbulMcs0					Counter32,
		nbrscheprbulMcs1					Counter32,
		nbrscheprbulMcs2					Counter32,
		nbrscheprbulMcs3					Counter32,
		nbrscheprbulMcs4					Counter32,
		nbrscheprbulMcs5					Counter32,
		nbrscheprbulMcs6					Counter32,
		nbrscheprbulMcs7					Counter32,
		nbrscheprbulMcs8					Counter32,
		nbrscheprbulMcs9					Counter32,
		nbrscheprbulMcs10					Counter32,
		nbrscheprbulMcs11					Counter32,
		nbrscheprbulMcs12					Counter32,
		nbrscheprbulMcs13					Counter32,
		nbrscheprbulMcs14					Counter32,
		nbrscheprbulMcs15					Counter32,
		nbrscheprbulMcs16					Counter32,
		nbrscheprbulMcs17					Counter32,
		nbrscheprbulMcs18					Counter32,
		nbrscheprbulMcs19					Counter32,
		nbrscheprbulMcs20					Counter32,
		nbrscheprbulMcs21					Counter32,
		nbrscheprbulMcs22					Counter32,
		nbrscheprbulMcs23					Counter32,
		nbrscheprbulMcs24					Counter32,
		nbrscheprbulMcs25					Counter32,
		nbrscheprbulMcs26					Counter32,
		nbrscheprbulMcs27					Counter32,
		nbrscheprbulMcs28					Counter32,
		nbrscheprbdlMcs0					Counter32,
		nbrscheprbdlMcs1					Counter32,
		nbrscheprbdlMcs2					Counter32,
		nbrscheprbdlMcs3					Counter32,
		nbrscheprbdlMcs4					Counter32,
		nbrscheprbdlMcs5					Counter32,
		nbrscheprbdlMcs6					Counter32,
		nbrscheprbdlMcs7					Counter32,
		nbrscheprbdlMcs8					Counter32,
		nbrscheprbdlMcs9					Counter32,
		nbrscheprbdlMcs10					Counter32,
		nbrscheprbdlMcs11					Counter32,
		nbrscheprbdlMcs12					Counter32,
		nbrscheprbdlMcs13					Counter32,
		nbrscheprbdlMcs14					Counter32,
		nbrscheprbdlMcs15					Counter32,
		nbrscheprbdlMcs16					Counter32,
		nbrscheprbdlMcs17					Counter32,
		nbrscheprbdlMcs18					Counter32,
		nbrscheprbdlMcs19					Counter32,
		nbrscheprbdlMcs20					Counter32,
		nbrscheprbdlMcs21					Counter32,
		nbrscheprbdlMcs22					Counter32,
		nbrscheprbdlMcs23					Counter32,
		nbrscheprbdlMcs24					Counter32,
		nbrscheprbdlMcs25					Counter32,
		nbrscheprbdlMcs26					Counter32,
		nbrscheprbdlMcs27					Counter32,
		nbrscheprbdlMcs28					Counter32,
		nbrscheprbdlMcs29					Counter32,
		nbrscheprbdlMcs30					Counter32,
		nbrscheprbdlMcs31					Counter32
		}


	schePrbAcoordingMCSLcId		 OBJECT-TYPE
		SYNTAX					 Integer32( 0 .. 23 )
		MAX-ACCESS			 not-accessible
		STATUS					 current
		DESCRIPTION			 " -- "
		::=  { schePrbAcoordingMCSEntry  1 }


	schePrbAcoordingMCSRowStatus		 OBJECT-TYPE
		SYNTAX					 RowStatus
		MAX-ACCESS			 read-only
		STATUS					 current
		DESCRIPTION			 " -- "
		::=  { schePrbAcoordingMCSEntry  2 }


	nbrscheprbulMcs0		 OBJECT-TYPE
		SYNTAX					 Counter32
		MAX-ACCESS			 read-only
		STATUS					 current
		DESCRIPTION			 " -- "
		::=  { schePrbAcoordingMCSEntry  3 }


	nbrscheprbulMcs1		 OBJECT-TYPE
		SYNTAX					 Counter32
		MAX-ACCESS			 read-only
		STATUS					 current
		DESCRIPTION			 " -- "
		::=  { schePrbAcoordingMCSEntry  4 }


	nbrscheprbulMcs2		 OBJECT-TYPE
		SYNTAX					 Counter32
		MAX-ACCESS			 read-only
		STATUS					 current
		DESCRIPTION			 " -- "
		::=  { schePrbAcoordingMCSEntry  5 }


	nbrscheprbulMcs3		 OBJECT-TYPE
		SYNTAX					 Counter32
		MAX-ACCESS			 read-only
		STATUS					 current
		DESCRIPTION			 " -- "
		::=  { schePrbAcoordingMCSEntry  6 }


	nbrscheprbulMcs4		 OBJECT-TYPE
		SYNTAX					 Counter32
		MAX-ACCESS			 read-only
		STATUS					 current
		DESCRIPTION			 " -- "
		::=  { schePrbAcoordingMCSEntry  7 }


	nbrscheprbulMcs5		 OBJECT-TYPE
		SYNTAX					 Counter32
		MAX-ACCESS			 read-only
		STATUS					 current
		DESCRIPTION			 " -- "
		::=  { schePrbAcoordingMCSEntry  8 }


	nbrscheprbulMcs6		 OBJECT-TYPE
		SYNTAX					 Counter32
		MAX-ACCESS			 read-only
		STATUS					 current
		DESCRIPTION			 " -- "
		::=  { schePrbAcoordingMCSEntry  9 }


	nbrscheprbulMcs7		 OBJECT-TYPE
		SYNTAX					 Counter32
		MAX-ACCESS			 read-only
		STATUS					 current
		DESCRIPTION			 " -- "
		::=  { schePrbAcoordingMCSEntry  10 }


	nbrscheprbulMcs8		 OBJECT-TYPE
		SYNTAX					 Counter32
		MAX-ACCESS			 read-only
		STATUS					 current
		DESCRIPTION			 " -- "
		::=  { schePrbAcoordingMCSEntry  11 }


	nbrscheprbulMcs9		 OBJECT-TYPE
		SYNTAX					 Counter32
		MAX-ACCESS			 read-only
		STATUS					 current
		DESCRIPTION			 " -- "
		::=  { schePrbAcoordingMCSEntry  12 }


	nbrscheprbulMcs10		 OBJECT-TYPE
		SYNTAX					 Counter32
		MAX-ACCESS			 read-only
		STATUS					 current
		DESCRIPTION			 " -- "
		::=  { schePrbAcoordingMCSEntry  13 }


	nbrscheprbulMcs11		 OBJECT-TYPE
		SYNTAX					 Counter32
		MAX-ACCESS			 read-only
		STATUS					 current
		DESCRIPTION			 " -- "
		::=  { schePrbAcoordingMCSEntry  14 }


	nbrscheprbulMcs12		 OBJECT-TYPE
		SYNTAX					 Counter32
		MAX-ACCESS			 read-only
		STATUS					 current
		DESCRIPTION			 " -- "
		::=  { schePrbAcoordingMCSEntry  15 }


	nbrscheprbulMcs13		 OBJECT-TYPE
		SYNTAX					 Counter32
		MAX-ACCESS			 read-only
		STATUS					 current
		DESCRIPTION			 " -- "
		::=  { schePrbAcoordingMCSEntry  16 }


	nbrscheprbulMcs14		 OBJECT-TYPE
		SYNTAX					 Counter32
		MAX-ACCESS			 read-only
		STATUS					 current
		DESCRIPTION			 " -- "
		::=  { schePrbAcoordingMCSEntry  17 }


	nbrscheprbulMcs15		 OBJECT-TYPE
		SYNTAX					 Counter32
		MAX-ACCESS			 read-only
		STATUS					 current
		DESCRIPTION			 " -- "
		::=  { schePrbAcoordingMCSEntry  18 }


	nbrscheprbulMcs16		 OBJECT-TYPE
		SYNTAX					 Counter32
		MAX-ACCESS			 read-only
		STATUS					 current
		DESCRIPTION			 " -- "
		::=  { schePrbAcoordingMCSEntry  19 }


	nbrscheprbulMcs17		 OBJECT-TYPE
		SYNTAX					 Counter32
		MAX-ACCESS			 read-only
		STATUS					 current
		DESCRIPTION			 " -- "
		::=  { schePrbAcoordingMCSEntry  20 }


	nbrscheprbulMcs18		 OBJECT-TYPE
		SYNTAX					 Counter32
		MAX-ACCESS			 read-only
		STATUS					 current
		DESCRIPTION			 " -- "
		::=  { schePrbAcoordingMCSEntry  21 }


	nbrscheprbulMcs19		 OBJECT-TYPE
		SYNTAX					 Counter32
		MAX-ACCESS			 read-only
		STATUS					 current
		DESCRIPTION			 " -- "
		::=  { schePrbAcoordingMCSEntry  22 }


	nbrscheprbulMcs20		 OBJECT-TYPE
		SYNTAX					 Counter32
		MAX-ACCESS			 read-only
		STATUS					 current
		DESCRIPTION			 " -- "
		::=  { schePrbAcoordingMCSEntry  23 }


	nbrscheprbulMcs21		 OBJECT-TYPE
		SYNTAX					 Counter32
		MAX-ACCESS			 read-only
		STATUS					 current
		DESCRIPTION			 " -- "
		::=  { schePrbAcoordingMCSEntry  24 }


	nbrscheprbulMcs22		 OBJECT-TYPE
		SYNTAX					 Counter32
		MAX-ACCESS			 read-only
		STATUS					 current
		DESCRIPTION			 " -- "
		::=  { schePrbAcoordingMCSEntry  25 }


	nbrscheprbulMcs23		 OBJECT-TYPE
		SYNTAX					 Counter32
		MAX-ACCESS			 read-only
		STATUS					 current
		DESCRIPTION			 " -- "
		::=  { schePrbAcoordingMCSEntry  26 }


	nbrscheprbulMcs24		 OBJECT-TYPE
		SYNTAX					 Counter32
		MAX-ACCESS			 read-only
		STATUS					 current
		DESCRIPTION			 " -- "
		::=  { schePrbAcoordingMCSEntry  27 }


	nbrscheprbulMcs25		 OBJECT-TYPE
		SYNTAX					 Counter32
		MAX-ACCESS			 read-only
		STATUS					 current
		DESCRIPTION			 " -- "
		::=  { schePrbAcoordingMCSEntry  28 }


	nbrscheprbulMcs26		 OBJECT-TYPE
		SYNTAX					 Counter32
		MAX-ACCESS			 read-only
		STATUS					 current
		DESCRIPTION			 " -- "
		::=  { schePrbAcoordingMCSEntry  29 }


	nbrscheprbulMcs27		 OBJECT-TYPE
		SYNTAX					 Counter32
		MAX-ACCESS			 read-only
		STATUS					 current
		DESCRIPTION			 " -- "
		::=  { schePrbAcoordingMCSEntry  30 }


	nbrscheprbulMcs28		 OBJECT-TYPE
		SYNTAX					 Counter32
		MAX-ACCESS			 read-only
		STATUS					 current
		DESCRIPTION			 " -- "
		::=  { schePrbAcoordingMCSEntry  31 }


	nbrscheprbdlMcs0		 OBJECT-TYPE
		SYNTAX					 Counter32
		MAX-ACCESS			 read-only
		STATUS					 current
		DESCRIPTION			 " -- "
		::=  { schePrbAcoordingMCSEntry  32 }


	nbrscheprbdlMcs1		 OBJECT-TYPE
		SYNTAX					 Counter32
		MAX-ACCESS			 read-only
		STATUS					 current
		DESCRIPTION			 " -- "
		::=  { schePrbAcoordingMCSEntry  33 }


	nbrscheprbdlMcs2		 OBJECT-TYPE
		SYNTAX					 Counter32
		MAX-ACCESS			 read-only
		STATUS					 current
		DESCRIPTION			 " -- "
		::=  { schePrbAcoordingMCSEntry  34 }


	nbrscheprbdlMcs3		 OBJECT-TYPE
		SYNTAX					 Counter32
		MAX-ACCESS			 read-only
		STATUS					 current
		DESCRIPTION			 " -- "
		::=  { schePrbAcoordingMCSEntry  35 }


	nbrscheprbdlMcs4		 OBJECT-TYPE
		SYNTAX					 Counter32
		MAX-ACCESS			 read-only
		STATUS					 current
		DESCRIPTION			 " -- "
		::=  { schePrbAcoordingMCSEntry  36 }


	nbrscheprbdlMcs5		 OBJECT-TYPE
		SYNTAX					 Counter32
		MAX-ACCESS			 read-only
		STATUS					 current
		DESCRIPTION			 " -- "
		::=  { schePrbAcoordingMCSEntry  37 }


	nbrscheprbdlMcs6		 OBJECT-TYPE
		SYNTAX					 Counter32
		MAX-ACCESS			 read-only
		STATUS					 current
		DESCRIPTION			 " -- "
		::=  { schePrbAcoordingMCSEntry  38 }


	nbrscheprbdlMcs7		 OBJECT-TYPE
		SYNTAX					 Counter32
		MAX-ACCESS			 read-only
		STATUS					 current
		DESCRIPTION			 " -- "
		::=  { schePrbAcoordingMCSEntry  39 }


	nbrscheprbdlMcs8		 OBJECT-TYPE
		SYNTAX					 Counter32
		MAX-ACCESS			 read-only
		STATUS					 current
		DESCRIPTION			 " -- "
		::=  { schePrbAcoordingMCSEntry  40 }


	nbrscheprbdlMcs9		 OBJECT-TYPE
		SYNTAX					 Counter32
		MAX-ACCESS			 read-only
		STATUS					 current
		DESCRIPTION			 " -- "
		::=  { schePrbAcoordingMCSEntry  41 }


	nbrscheprbdlMcs10		 OBJECT-TYPE
		SYNTAX					 Counter32
		MAX-ACCESS			 read-only
		STATUS					 current
		DESCRIPTION			 " -- "
		::=  { schePrbAcoordingMCSEntry  42 }


	nbrscheprbdlMcs11		 OBJECT-TYPE
		SYNTAX					 Counter32
		MAX-ACCESS			 read-only
		STATUS					 current
		DESCRIPTION			 " -- "
		::=  { schePrbAcoordingMCSEntry  43 }


	nbrscheprbdlMcs12		 OBJECT-TYPE
		SYNTAX					 Counter32
		MAX-ACCESS			 read-only
		STATUS					 current
		DESCRIPTION			 " -- "
		::=  { schePrbAcoordingMCSEntry  44 }


	nbrscheprbdlMcs13		 OBJECT-TYPE
		SYNTAX					 Counter32
		MAX-ACCESS			 read-only
		STATUS					 current
		DESCRIPTION			 " -- "
		::=  { schePrbAcoordingMCSEntry  45 }


	nbrscheprbdlMcs14		 OBJECT-TYPE
		SYNTAX					 Counter32
		MAX-ACCESS			 read-only
		STATUS					 current
		DESCRIPTION			 " -- "
		::=  { schePrbAcoordingMCSEntry  46 }


	nbrscheprbdlMcs15		 OBJECT-TYPE
		SYNTAX					 Counter32
		MAX-ACCESS			 read-only
		STATUS					 current
		DESCRIPTION			 " -- "
		::=  { schePrbAcoordingMCSEntry  47 }


	nbrscheprbdlMcs16		 OBJECT-TYPE
		SYNTAX					 Counter32
		MAX-ACCESS			 read-only
		STATUS					 current
		DESCRIPTION			 " -- "
		::=  { schePrbAcoordingMCSEntry  48 }


	nbrscheprbdlMcs17		 OBJECT-TYPE
		SYNTAX					 Counter32
		MAX-ACCESS			 read-only
		STATUS					 current
		DESCRIPTION			 " -- "
		::=  { schePrbAcoordingMCSEntry  49 }


	nbrscheprbdlMcs18		 OBJECT-TYPE
		SYNTAX					 Counter32
		MAX-ACCESS			 read-only
		STATUS					 current
		DESCRIPTION			 " -- "
		::=  { schePrbAcoordingMCSEntry  50 }


	nbrscheprbdlMcs19		 OBJECT-TYPE
		SYNTAX					 Counter32
		MAX-ACCESS			 read-only
		STATUS					 current
		DESCRIPTION			 " -- "
		::=  { schePrbAcoordingMCSEntry  51 }


	nbrscheprbdlMcs20		 OBJECT-TYPE
		SYNTAX					 Counter32
		MAX-ACCESS			 read-only
		STATUS					 current
		DESCRIPTION			 " -- "
		::=  { schePrbAcoordingMCSEntry  52 }


	nbrscheprbdlMcs21		 OBJECT-TYPE
		SYNTAX					 Counter32
		MAX-ACCESS			 read-only
		STATUS					 current
		DESCRIPTION			 " -- "
		::=  { schePrbAcoordingMCSEntry  53 }


	nbrscheprbdlMcs22		 OBJECT-TYPE
		SYNTAX					 Counter32
		MAX-ACCESS			 read-only
		STATUS					 current
		DESCRIPTION			 " -- "
		::=  { schePrbAcoordingMCSEntry  54 }


	nbrscheprbdlMcs23		 OBJECT-TYPE
		SYNTAX					 Counter32
		MAX-ACCESS			 read-only
		STATUS					 current
		DESCRIPTION			 " -- "
		::=  { schePrbAcoordingMCSEntry  55 }


	nbrscheprbdlMcs24		 OBJECT-TYPE
		SYNTAX					 Counter32
		MAX-ACCESS			 read-only
		STATUS					 current
		DESCRIPTION			 " -- "
		::=  { schePrbAcoordingMCSEntry  56 }


	nbrscheprbdlMcs25		 OBJECT-TYPE
		SYNTAX					 Counter32
		MAX-ACCESS			 read-only
		STATUS					 current
		DESCRIPTION			 " -- "
		::=  { schePrbAcoordingMCSEntry  57 }


	nbrscheprbdlMcs26		 OBJECT-TYPE
		SYNTAX					 Counter32
		MAX-ACCESS			 read-only
		STATUS					 current
		DESCRIPTION			 " -- "
		::=  { schePrbAcoordingMCSEntry  58 }


	nbrscheprbdlMcs27		 OBJECT-TYPE
		SYNTAX					 Counter32
		MAX-ACCESS			 read-only
		STATUS					 current
		DESCRIPTION			 " -- "
		::=  { schePrbAcoordingMCSEntry  59 }


	nbrscheprbdlMcs28		 OBJECT-TYPE
		SYNTAX					 Counter32
		MAX-ACCESS			 read-only
		STATUS					 current
		DESCRIPTION			 " -- "
		::=  { schePrbAcoordingMCSEntry  60 }


	nbrscheprbdlMcs29		 OBJECT-TYPE
		SYNTAX					 Counter32
		MAX-ACCESS			 read-only
		STATUS					 current
		DESCRIPTION			 " -- "
		::=  { schePrbAcoordingMCSEntry  61 }


	nbrscheprbdlMcs30		 OBJECT-TYPE
		SYNTAX					 Counter32
		MAX-ACCESS			 read-only
		STATUS					 current
		DESCRIPTION			 " -- "
		::=  { schePrbAcoordingMCSEntry  62 }


	nbrscheprbdlMcs31		 OBJECT-TYPE
		SYNTAX					 Counter32
		MAX-ACCESS			 read-only
		STATUS					 current
		DESCRIPTION			 " -- "
		::=  { schePrbAcoordingMCSEntry  63 }


	scheTimesAcoordingSFNTable		 OBJECT-TYPE
		SYNTAX					 SEQUENCE  OF	 ScheTimesAcoordingSFNEntry
		MAX-ACCESS			 not-accessible
		STATUS					 current
		DESCRIPTION			 " -- "
		::=  { macrelatedOriginCounter  22 }


	scheTimesAcoordingSFNEntry		 OBJECT-TYPE
		SYNTAX					 ScheTimesAcoordingSFNEntry
		MAX-ACCESS			 not-accessible
		STATUS					 current
		DESCRIPTION			 " -- "
		INDEX						{ scheTimesAcoordingSFNLcId }
		::=  { scheTimesAcoordingSFNTable  1 }


	ScheTimesAcoordingSFNEntry		 ::=  SEQUENCE {
		scheTimesAcoordingSFNLcId					Integer32,
		scheTimesAcoordingSFNRowStatus					RowStatus,
		srbNbrScheTimesSfn0					Counter32,
		srbNbrScheTimesSfn1					Counter32,
		srbNbrScheTimesSfn2					Counter32,
		srbNbrScheTimesSfn3					Counter32,
		srbNbrScheTimesSfn4					Counter32,
		srbNbrScheTimesSfn5					Counter32,
		srbNbrScheTimesSfn6					Counter32,
		srbNbrScheTimesSfn7					Counter32,
		srbNbrScheTimesSfn8					Counter32,
		srbNbrScheTimesSfn9					Counter32,
		drbNbrScheTimesSfn0					Counter32,
		drbNbrScheTimesSfn1					Counter32,
		drbNbrScheTimesSfn2					Counter32,
		drbNbrScheTimesSfn3					Counter32,
		drbNbrScheTimesSfn4					Counter32,
		drbNbrScheTimesSfn5					Counter32,
		drbNbrScheTimesSfn6					Counter32,
		drbNbrScheTimesSfn7					Counter32,
		drbNbrScheTimesSfn8					Counter32,
		drbNbrScheTimesSfn9					Counter32,
		srNbrScheTimesTotol					Counter32,
		srNbrScheTimesSfn2					Counter32,
		srNbrScheTimesSfn7					Counter32
		}


	scheTimesAcoordingSFNLcId		 OBJECT-TYPE
		SYNTAX					 Integer32( 0 .. 23 )
		MAX-ACCESS			 not-accessible
		STATUS					 current
		DESCRIPTION			 " -- "
		::=  { scheTimesAcoordingSFNEntry  1 }


	scheTimesAcoordingSFNRowStatus		 OBJECT-TYPE
		SYNTAX					 RowStatus
		MAX-ACCESS			 read-only
		STATUS					 current
		DESCRIPTION			 " -- "
		::=  { scheTimesAcoordingSFNEntry  2 }


	srbNbrScheTimesSfn0		 OBJECT-TYPE
		SYNTAX					 Counter32
		MAX-ACCESS			 read-only
		STATUS					 current
		DESCRIPTION			 " -- "
		::=  { scheTimesAcoordingSFNEntry  3 }


	srbNbrScheTimesSfn1		 OBJECT-TYPE
		SYNTAX					 Counter32
		MAX-ACCESS			 read-only
		STATUS					 current
		DESCRIPTION			 " -- "
		::=  { scheTimesAcoordingSFNEntry  4 }


	srbNbrScheTimesSfn2		 OBJECT-TYPE
		SYNTAX					 Counter32
		MAX-ACCESS			 read-only
		STATUS					 current
		DESCRIPTION			 " -- "
		::=  { scheTimesAcoordingSFNEntry  5 }


	srbNbrScheTimesSfn3		 OBJECT-TYPE
		SYNTAX					 Counter32
		MAX-ACCESS			 read-only
		STATUS					 current
		DESCRIPTION			 " -- "
		::=  { scheTimesAcoordingSFNEntry  6 }


	srbNbrScheTimesSfn4		 OBJECT-TYPE
		SYNTAX					 Counter32
		MAX-ACCESS			 read-only
		STATUS					 current
		DESCRIPTION			 " -- "
		::=  { scheTimesAcoordingSFNEntry  7 }


	srbNbrScheTimesSfn5		 OBJECT-TYPE
		SYNTAX					 Counter32
		MAX-ACCESS			 read-only
		STATUS					 current
		DESCRIPTION			 " -- "
		::=  { scheTimesAcoordingSFNEntry  8 }


	srbNbrScheTimesSfn6		 OBJECT-TYPE
		SYNTAX					 Counter32
		MAX-ACCESS			 read-only
		STATUS					 current
		DESCRIPTION			 " -- "
		::=  { scheTimesAcoordingSFNEntry  9 }


	srbNbrScheTimesSfn7		 OBJECT-TYPE
		SYNTAX					 Counter32
		MAX-ACCESS			 read-only
		STATUS					 current
		DESCRIPTION			 " -- "
		::=  { scheTimesAcoordingSFNEntry  10 }


	srbNbrScheTimesSfn8		 OBJECT-TYPE
		SYNTAX					 Counter32
		MAX-ACCESS			 read-only
		STATUS					 current
		DESCRIPTION			 " -- "
		::=  { scheTimesAcoordingSFNEntry  11 }


	srbNbrScheTimesSfn9		 OBJECT-TYPE
		SYNTAX					 Counter32
		MAX-ACCESS			 read-only
		STATUS					 current
		DESCRIPTION			 " -- "
		::=  { scheTimesAcoordingSFNEntry  12 }


	drbNbrScheTimesSfn0		 OBJECT-TYPE
		SYNTAX					 Counter32
		MAX-ACCESS			 read-only
		STATUS					 current
		DESCRIPTION			 " -- "
		::=  { scheTimesAcoordingSFNEntry  13 }


	drbNbrScheTimesSfn1		 OBJECT-TYPE
		SYNTAX					 Counter32
		MAX-ACCESS			 read-only
		STATUS					 current
		DESCRIPTION			 " -- "
		::=  { scheTimesAcoordingSFNEntry  14 }


	drbNbrScheTimesSfn2		 OBJECT-TYPE
		SYNTAX					 Counter32
		MAX-ACCESS			 read-only
		STATUS					 current
		DESCRIPTION			 " -- "
		::=  { scheTimesAcoordingSFNEntry  15 }


	drbNbrScheTimesSfn3		 OBJECT-TYPE
		SYNTAX					 Counter32
		MAX-ACCESS			 read-only
		STATUS					 current
		DESCRIPTION			 " -- "
		::=  { scheTimesAcoordingSFNEntry  16 }


	drbNbrScheTimesSfn4		 OBJECT-TYPE
		SYNTAX					 Counter32
		MAX-ACCESS			 read-only
		STATUS					 current
		DESCRIPTION			 " -- "
		::=  { scheTimesAcoordingSFNEntry  17 }


	drbNbrScheTimesSfn5		 OBJECT-TYPE
		SYNTAX					 Counter32
		MAX-ACCESS			 read-only
		STATUS					 current
		DESCRIPTION			 " -- "
		::=  { scheTimesAcoordingSFNEntry  18 }


	drbNbrScheTimesSfn6		 OBJECT-TYPE
		SYNTAX					 Counter32
		MAX-ACCESS			 read-only
		STATUS					 current
		DESCRIPTION			 " -- "
		::=  { scheTimesAcoordingSFNEntry  19 }


	drbNbrScheTimesSfn7		 OBJECT-TYPE
		SYNTAX					 Counter32
		MAX-ACCESS			 read-only
		STATUS					 current
		DESCRIPTION			 " -- "
		::=  { scheTimesAcoordingSFNEntry  20 }


	drbNbrScheTimesSfn8		 OBJECT-TYPE
		SYNTAX					 Counter32
		MAX-ACCESS			 read-only
		STATUS					 current
		DESCRIPTION			 " -- "
		::=  { scheTimesAcoordingSFNEntry  21 }


	drbNbrScheTimesSfn9		 OBJECT-TYPE
		SYNTAX					 Counter32
		MAX-ACCESS			 read-only
		STATUS					 current
		DESCRIPTION			 " -- "
		::=  { scheTimesAcoordingSFNEntry  22 }


	srNbrScheTimesTotol		 OBJECT-TYPE
		SYNTAX					 Counter32
		MAX-ACCESS			 read-only
		STATUS					 current
		DESCRIPTION			 " -- "
		::=  { scheTimesAcoordingSFNEntry  23 }


	srNbrScheTimesSfn2		 OBJECT-TYPE
		SYNTAX					 Counter32
		MAX-ACCESS			 read-only
		STATUS					 current
		DESCRIPTION			 " -- "
		::=  { scheTimesAcoordingSFNEntry  24 }


	srNbrScheTimesSfn7		 OBJECT-TYPE
		SYNTAX					 Counter32
		MAX-ACCESS			 read-only
		STATUS					 current
		DESCRIPTION			 " -- "
		::=  { scheTimesAcoordingSFNEntry  25 }


	edgeUserStatisticTable		 OBJECT-TYPE
		SYNTAX					 SEQUENCE  OF	 EdgeUserStatisticEntry
		MAX-ACCESS			 not-accessible
		STATUS					 current
		DESCRIPTION			 " -- "
		::=  { macrelatedOriginCounter  23 }


	edgeUserStatisticEntry		 OBJECT-TYPE
		SYNTAX					 EdgeUserStatisticEntry
		MAX-ACCESS			 not-accessible
		STATUS					 current
		DESCRIPTION			 " -- "
		INDEX						{ edgeUserStatisticLcId }
		::=  { edgeUserStatisticTable  1 }


	EdgeUserStatisticEntry		 ::=  SEQUENCE {
		edgeUserStatisticLcId					Integer32,
		edgeUserStatisticRowStatus					RowStatus,
		macPdschPrbAssnDlEdgeUser					Counter32,
		macPuschPrbAssnUlEdgeUser					Counter32,
		pdcpUpOctDlEdgeUser					Counter32,
		pdcpUpOctDlCentreUser					Counter32,
		macScheTimeDlEdgeUser					Counter32,
		macScheTimeDlCentreUser					Counter32,
		rrcConnTolDlEdgeUser					Counter32,
		rrcConnTolDlCentreUser					Counter32,
		rrcUserSampNbr					Counter32,
		rrcConnTolUlEdgeUser					Counter32,
		pdcpUpOctUlEdgeUser					Counter32,
		pdcpBurstDataUlEdgeUser					Counter32,
		macScheTimeUlEdgeUser					Counter32
		}


	edgeUserStatisticLcId		 OBJECT-TYPE
		SYNTAX					 Integer32( 0 .. 23 )
		MAX-ACCESS			 not-accessible
		STATUS					 current
		DESCRIPTION			 " -- "
		::=  { edgeUserStatisticEntry  1 }


	edgeUserStatisticRowStatus		 OBJECT-TYPE
		SYNTAX					 RowStatus
		MAX-ACCESS			 read-only
		STATUS					 current
		DESCRIPTION			 " -- "
		::=  { edgeUserStatisticEntry  2 }


	macPdschPrbAssnDlEdgeUser		 OBJECT-TYPE
		SYNTAX					 Counter32
		MAX-ACCESS			 read-only
		STATUS					 current
		DESCRIPTION			 " -- "
		::=  { edgeUserStatisticEntry  3 }


	macPuschPrbAssnUlEdgeUser		 OBJECT-TYPE
		SYNTAX					 Counter32
		MAX-ACCESS			 read-only
		STATUS					 current
		DESCRIPTION			 " -- "
		::=  { edgeUserStatisticEntry  4 }


	pdcpUpOctDlEdgeUser		 OBJECT-TYPE
		SYNTAX					 Counter32
		MAX-ACCESS			 read-only
		STATUS					 current
		DESCRIPTION			 " -- "
		::=  { edgeUserStatisticEntry  5 }


	pdcpUpOctDlCentreUser		 OBJECT-TYPE
		SYNTAX					 Counter32
		MAX-ACCESS			 read-only
		STATUS					 current
		DESCRIPTION			 " -- "
		::=  { edgeUserStatisticEntry  6 }


	macScheTimeDlEdgeUser		 OBJECT-TYPE
		SYNTAX					 Counter32
		MAX-ACCESS			 read-only
		STATUS					 current
		DESCRIPTION			 " -- "
		::=  { edgeUserStatisticEntry  7 }


	macScheTimeDlCentreUser		 OBJECT-TYPE
		SYNTAX					 Counter32
		MAX-ACCESS			 read-only
		STATUS					 current
		DESCRIPTION			 " -- "
		::=  { edgeUserStatisticEntry  8 }


	rrcConnTolDlEdgeUser		 OBJECT-TYPE
		SYNTAX					 Counter32
		MAX-ACCESS			 read-only
		STATUS					 current
		DESCRIPTION			 " -- "
		::=  { edgeUserStatisticEntry  9 }


	rrcConnTolDlCentreUser		 OBJECT-TYPE
		SYNTAX					 Counter32
		MAX-ACCESS			 read-only
		STATUS					 current
		DESCRIPTION			 " -- "
		::=  { edgeUserStatisticEntry  10 }


	rrcUserSampNbr		 OBJECT-TYPE
		SYNTAX					 Counter32
		MAX-ACCESS			 read-only
		STATUS					 current
		DESCRIPTION			 " -- "
		::=  { edgeUserStatisticEntry  11 }


	rrcConnTolUlEdgeUser		 OBJECT-TYPE
		SYNTAX					 Counter32
		MAX-ACCESS			 read-only
		STATUS					 current
		DESCRIPTION			 " -- "
		::=  { edgeUserStatisticEntry  12 }


	pdcpUpOctUlEdgeUser		 OBJECT-TYPE
		SYNTAX					 Counter32
		MAX-ACCESS			 read-only
		STATUS					 current
		DESCRIPTION			 " -- "
		::=  { edgeUserStatisticEntry  13 }


	pdcpBurstDataUlEdgeUser		 OBJECT-TYPE
		SYNTAX					 Counter32
		MAX-ACCESS			 read-only
		STATUS					 current
		DESCRIPTION			 " -- "
		::=  { edgeUserStatisticEntry  14 }


	macScheTimeUlEdgeUser		 OBJECT-TYPE
		SYNTAX					 Counter32
		MAX-ACCESS			 read-only
		STATUS					 current
		DESCRIPTION			 " -- "
		::=  { edgeUserStatisticEntry  15 }


	mimoPerformanceTable		 OBJECT-TYPE
		SYNTAX					 SEQUENCE  OF	 MimoPerformanceEntry
		MAX-ACCESS			 not-accessible
		STATUS					 current
		DESCRIPTION			 " -- "
		::=  { macrelatedOriginCounter  24 }


	mimoPerformanceEntry		 OBJECT-TYPE
		SYNTAX					 MimoPerformanceEntry
		MAX-ACCESS			 not-accessible
		STATUS					 current
		DESCRIPTION			 " -- "
		INDEX						{ mimoPerformanceLcId }
		::=  { mimoPerformanceTable  1 }


	MimoPerformanceEntry		 ::=  SEQUENCE {
		mimoPerformanceLcId					Integer32,
		mimoPerformanceRowStatus					RowStatus,
		macMumimoPairSfnUl					Counter32,
		macMumimoPairRbUlRank1					Counter32,
		macMumimoPairRbUlRank2					Counter32,
		macMumimoThrputUlRank1					Counter32,
		macMumimoThrputUlRank2					Counter32,
		macMumimoUserUlRank1					Counter32,
		macMumimoPairUserUlRank2					Counter32,
		macMumimoMaxPairUserUl					Counter32,
		macMumimoThrpTimeUlRank1					Counter32,
		macMumimoThrpTimeUlRank2					Counter32,
		macMumimoPairSfnDl					Counter32,
		macMumimoRbDlRank1					Counter32,
		macMumimoPairRbDlRank2					Counter32,
		macMumimoThrputDlRank1					Counter32,
		macMumimoThrputDlRank2					Counter32,
		macMumimoUserDlRank1					Counter32,
		macMumimoPairUserDlRank2					Counter32,
		macMumimoMaxPairUserDl					Counter32,
		macMumimoThrpTimeDlRank1					Counter32,
		macMumimoThrpTimeDlRank2					Counter32
		}


	mimoPerformanceLcId		 OBJECT-TYPE
		SYNTAX					 Integer32( 0 .. 23 )
		MAX-ACCESS			 not-accessible
		STATUS					 current
		DESCRIPTION			 " -- "
		::=  { mimoPerformanceEntry  1 }


	mimoPerformanceRowStatus		 OBJECT-TYPE
		SYNTAX					 RowStatus
		MAX-ACCESS			 read-only
		STATUS					 current
		DESCRIPTION			 " -- "
		::=  { mimoPerformanceEntry  2 }


	macMumimoPairSfnUl		 OBJECT-TYPE
		SYNTAX					 Counter32
		MAX-ACCESS			 read-only
		STATUS					 current
		DESCRIPTION			 " -- "
		::=  { mimoPerformanceEntry  3 }


	macMumimoPairRbUlRank1		 OBJECT-TYPE
		SYNTAX					 Counter32
		MAX-ACCESS			 read-only
		STATUS					 current
		DESCRIPTION			 " -- "
		::=  { mimoPerformanceEntry  4 }


	macMumimoPairRbUlRank2		 OBJECT-TYPE
		SYNTAX					 Counter32
		MAX-ACCESS			 read-only
		STATUS					 current
		DESCRIPTION			 " -- "
		::=  { mimoPerformanceEntry  5 }


	macMumimoThrputUlRank1		 OBJECT-TYPE
		SYNTAX					 Counter32
		MAX-ACCESS			 read-only
		STATUS					 current
		DESCRIPTION			 " -- "
		::=  { mimoPerformanceEntry  6 }


	macMumimoThrputUlRank2		 OBJECT-TYPE
		SYNTAX					 Counter32
		MAX-ACCESS			 read-only
		STATUS					 current
		DESCRIPTION			 " -- "
		::=  { mimoPerformanceEntry  7 }


	macMumimoUserUlRank1		 OBJECT-TYPE
		SYNTAX					 Counter32
		MAX-ACCESS			 read-only
		STATUS					 current
		DESCRIPTION			 " -- "
		::=  { mimoPerformanceEntry  8 }


	macMumimoPairUserUlRank2		 OBJECT-TYPE
		SYNTAX					 Counter32
		MAX-ACCESS			 read-only
		STATUS					 current
		DESCRIPTION			 " -- "
		::=  { mimoPerformanceEntry  9 }


	macMumimoMaxPairUserUl		 OBJECT-TYPE
		SYNTAX					 Counter32
		MAX-ACCESS			 read-only
		STATUS					 current
		DESCRIPTION			 " -- "
		::=  { mimoPerformanceEntry  10 }


	macMumimoThrpTimeUlRank1		 OBJECT-TYPE
		SYNTAX					 Counter32
		MAX-ACCESS			 read-only
		STATUS					 current
		DESCRIPTION			 " -- "
		::=  { mimoPerformanceEntry  11 }


	macMumimoThrpTimeUlRank2		 OBJECT-TYPE
		SYNTAX					 Counter32
		MAX-ACCESS			 read-only
		STATUS					 current
		DESCRIPTION			 " -- "
		::=  { mimoPerformanceEntry  12 }


	macMumimoPairSfnDl		 OBJECT-TYPE
		SYNTAX					 Counter32
		MAX-ACCESS			 read-only
		STATUS					 current
		DESCRIPTION			 " -- "
		::=  { mimoPerformanceEntry  13 }


	macMumimoRbDlRank1		 OBJECT-TYPE
		SYNTAX					 Counter32
		MAX-ACCESS			 read-only
		STATUS					 current
		DESCRIPTION			 " -- "
		::=  { mimoPerformanceEntry  14 }


	macMumimoPairRbDlRank2		 OBJECT-TYPE
		SYNTAX					 Counter32
		MAX-ACCESS			 read-only
		STATUS					 current
		DESCRIPTION			 " -- "
		::=  { mimoPerformanceEntry  15 }


	macMumimoThrputDlRank1		 OBJECT-TYPE
		SYNTAX					 Counter32
		MAX-ACCESS			 read-only
		STATUS					 current
		DESCRIPTION			 " -- "
		::=  { mimoPerformanceEntry  16 }


	macMumimoThrputDlRank2		 OBJECT-TYPE
		SYNTAX					 Counter32
		MAX-ACCESS			 read-only
		STATUS					 current
		DESCRIPTION			 " -- "
		::=  { mimoPerformanceEntry  17 }


	macMumimoUserDlRank1		 OBJECT-TYPE
		SYNTAX					 Counter32
		MAX-ACCESS			 read-only
		STATUS					 current
		DESCRIPTION			 " -- "
		::=  { mimoPerformanceEntry  18 }


	macMumimoPairUserDlRank2		 OBJECT-TYPE
		SYNTAX					 Counter32
		MAX-ACCESS			 read-only
		STATUS					 current
		DESCRIPTION			 " -- "
		::=  { mimoPerformanceEntry  19 }


	macMumimoMaxPairUserDl		 OBJECT-TYPE
		SYNTAX					 Counter32
		MAX-ACCESS			 read-only
		STATUS					 current
		DESCRIPTION			 " -- "
		::=  { mimoPerformanceEntry  20 }


	macMumimoThrpTimeDlRank1		 OBJECT-TYPE
		SYNTAX					 Counter32
		MAX-ACCESS			 read-only
		STATUS					 current
		DESCRIPTION			 " -- "
		::=  { mimoPerformanceEntry  21 }


	macMumimoThrpTimeDlRank2		 OBJECT-TYPE
		SYNTAX					 Counter32
		MAX-ACCESS			 read-only
		STATUS					 current
		DESCRIPTION			 " -- "
		::=  { mimoPerformanceEntry  22 }


	macPresetPerformanceTable		 OBJECT-TYPE
		SYNTAX					 SEQUENCE  OF	 MacPresetPerformanceEntry
		MAX-ACCESS			 not-accessible
		STATUS					 current
		DESCRIPTION			 " -- "
		::=  { macrelatedOriginCounter  25 }


	macPresetPerformanceEntry		 OBJECT-TYPE
		SYNTAX					 MacPresetPerformanceEntry
		MAX-ACCESS			 not-accessible
		STATUS					 current
		DESCRIPTION			 " -- "
		INDEX						{ macPresetPerformanceLcId }
		::=  { macPresetPerformanceTable  1 }


	MacPresetPerformanceEntry		 ::=  SEQUENCE {
		macPresetPerformanceLcId					Integer32,
		macPresetPerformanceRowStatus					RowStatus,
		macPreset1					Counter32,
		macPreset2					Counter32,
		macPreset3					Counter32,
		macPreset4					Counter32,
		macPreset5					Counter32,
		macPreset6					Counter32,
		macPreset7					Counter32,
		macPreset8					Counter32,
		macPreset9					Counter32,
		macPreset10					Counter32,
		macPreset11					Counter32,
		macPreset12					Counter32,
		macPreset13					Counter32,
		macPreset14					Counter32,
		macPreset15					Counter32,
		macPreset16					Counter32,
		macPreset17					Counter32,
		macPreset18					Counter32,
		macPreset19					Counter32,
		macPreset20					Counter32,
		macPreset21					Counter32,
		macPreset22					Counter32,
		macPreset23					Counter32,
		macPreset24					Counter32,
		macPreset25					Counter32,
		macPreset26					Counter32,
		macPreset27					Counter32,
		macPreset28					Counter32,
		macPreset29					Counter32,
		macPreset30					Counter32,
		macPreset31					Counter32,
		macPreset32					Counter32,
		macPreset33					Counter32,
		macPreset34					Counter32,
		macPreset35					Counter32,
		macPreset36					Counter32,
		macPreset37					Counter32,
		macPreset38					Counter32,
		macPreset39					Counter32,
		macPreset40					Counter32
		}


	macPresetPerformanceLcId		 OBJECT-TYPE
		SYNTAX					 Integer32( 0 .. 23 )
		MAX-ACCESS			 not-accessible
		STATUS					 current
		DESCRIPTION			 " -- "
		::=  { macPresetPerformanceEntry  1 }


	macPresetPerformanceRowStatus		 OBJECT-TYPE
		SYNTAX					 RowStatus
		MAX-ACCESS			 read-only
		STATUS					 current
		DESCRIPTION			 " -- "
		::=  { macPresetPerformanceEntry  2 }


	macPreset1		 OBJECT-TYPE
		SYNTAX					 Counter32
		MAX-ACCESS			 read-only
		STATUS					 current
		DESCRIPTION			 " -- "
		::=  { macPresetPerformanceEntry  3 }


	macPreset2		 OBJECT-TYPE
		SYNTAX					 Counter32
		MAX-ACCESS			 read-only
		STATUS					 current
		DESCRIPTION			 " -- "
		::=  { macPresetPerformanceEntry  4 }


	macPreset3		 OBJECT-TYPE
		SYNTAX					 Counter32
		MAX-ACCESS			 read-only
		STATUS					 current
		DESCRIPTION			 " -- "
		::=  { macPresetPerformanceEntry  5 }


	macPreset4		 OBJECT-TYPE
		SYNTAX					 Counter32
		MAX-ACCESS			 read-only
		STATUS					 current
		DESCRIPTION			 " -- "
		::=  { macPresetPerformanceEntry  6 }


	macPreset5		 OBJECT-TYPE
		SYNTAX					 Counter32
		MAX-ACCESS			 read-only
		STATUS					 current
		DESCRIPTION			 " -- "
		::=  { macPresetPerformanceEntry  7 }


	macPreset6		 OBJECT-TYPE
		SYNTAX					 Counter32
		MAX-ACCESS			 read-only
		STATUS					 current
		DESCRIPTION			 " -- "
		::=  { macPresetPerformanceEntry  8 }


	macPreset7		 OBJECT-TYPE
		SYNTAX					 Counter32
		MAX-ACCESS			 read-only
		STATUS					 current
		DESCRIPTION			 " -- "
		::=  { macPresetPerformanceEntry  9 }


	macPreset8		 OBJECT-TYPE
		SYNTAX					 Counter32
		MAX-ACCESS			 read-only
		STATUS					 current
		DESCRIPTION			 " -- "
		::=  { macPresetPerformanceEntry  10 }


	macPreset9		 OBJECT-TYPE
		SYNTAX					 Counter32
		MAX-ACCESS			 read-only
		STATUS					 current
		DESCRIPTION			 " -- "
		::=  { macPresetPerformanceEntry  11 }


	macPreset10		 OBJECT-TYPE
		SYNTAX					 Counter32
		MAX-ACCESS			 read-only
		STATUS					 current
		DESCRIPTION			 " -- "
		::=  { macPresetPerformanceEntry  12 }


	macPreset11		 OBJECT-TYPE
		SYNTAX					 Counter32
		MAX-ACCESS			 read-only
		STATUS					 current
		DESCRIPTION			 " -- "
		::=  { macPresetPerformanceEntry  13 }


	macPreset12		 OBJECT-TYPE
		SYNTAX					 Counter32
		MAX-ACCESS			 read-only
		STATUS					 current
		DESCRIPTION			 " -- "
		::=  { macPresetPerformanceEntry  14 }


	macPreset13		 OBJECT-TYPE
		SYNTAX					 Counter32
		MAX-ACCESS			 read-only
		STATUS					 current
		DESCRIPTION			 " -- "
		::=  { macPresetPerformanceEntry  15 }


	macPreset14		 OBJECT-TYPE
		SYNTAX					 Counter32
		MAX-ACCESS			 read-only
		STATUS					 current
		DESCRIPTION			 " -- "
		::=  { macPresetPerformanceEntry  16 }


	macPreset15		 OBJECT-TYPE
		SYNTAX					 Counter32
		MAX-ACCESS			 read-only
		STATUS					 current
		DESCRIPTION			 " -- "
		::=  { macPresetPerformanceEntry  17 }


	macPreset16		 OBJECT-TYPE
		SYNTAX					 Counter32
		MAX-ACCESS			 read-only
		STATUS					 current
		DESCRIPTION			 " -- "
		::=  { macPresetPerformanceEntry  18 }


	macPreset17		 OBJECT-TYPE
		SYNTAX					 Counter32
		MAX-ACCESS			 read-only
		STATUS					 current
		DESCRIPTION			 " -- "
		::=  { macPresetPerformanceEntry  19 }


	macPreset18		 OBJECT-TYPE
		SYNTAX					 Counter32
		MAX-ACCESS			 read-only
		STATUS					 current
		DESCRIPTION			 " -- "
		::=  { macPresetPerformanceEntry  20 }


	macPreset19		 OBJECT-TYPE
		SYNTAX					 Counter32
		MAX-ACCESS			 read-only
		STATUS					 current
		DESCRIPTION			 " -- "
		::=  { macPresetPerformanceEntry  21 }


	macPreset20		 OBJECT-TYPE
		SYNTAX					 Counter32
		MAX-ACCESS			 read-only
		STATUS					 current
		DESCRIPTION			 " -- "
		::=  { macPresetPerformanceEntry  22 }


	macPreset21		 OBJECT-TYPE
		SYNTAX					 Counter32
		MAX-ACCESS			 read-only
		STATUS					 current
		DESCRIPTION			 " -- "
		::=  { macPresetPerformanceEntry  23 }


	macPreset22		 OBJECT-TYPE
		SYNTAX					 Counter32
		MAX-ACCESS			 read-only
		STATUS					 current
		DESCRIPTION			 " -- "
		::=  { macPresetPerformanceEntry  24 }


	macPreset23		 OBJECT-TYPE
		SYNTAX					 Counter32
		MAX-ACCESS			 read-only
		STATUS					 current
		DESCRIPTION			 " -- "
		::=  { macPresetPerformanceEntry  25 }


	macPreset24		 OBJECT-TYPE
		SYNTAX					 Counter32
		MAX-ACCESS			 read-only
		STATUS					 current
		DESCRIPTION			 " -- "
		::=  { macPresetPerformanceEntry  26 }


	macPreset25		 OBJECT-TYPE
		SYNTAX					 Counter32
		MAX-ACCESS			 read-only
		STATUS					 current
		DESCRIPTION			 " -- "
		::=  { macPresetPerformanceEntry  27 }


	macPreset26		 OBJECT-TYPE
		SYNTAX					 Counter32
		MAX-ACCESS			 read-only
		STATUS					 current
		DESCRIPTION			 " -- "
		::=  { macPresetPerformanceEntry  28 }


	macPreset27		 OBJECT-TYPE
		SYNTAX					 Counter32
		MAX-ACCESS			 read-only
		STATUS					 current
		DESCRIPTION			 " -- "
		::=  { macPresetPerformanceEntry  29 }


	macPreset28		 OBJECT-TYPE
		SYNTAX					 Counter32
		MAX-ACCESS			 read-only
		STATUS					 current
		DESCRIPTION			 " -- "
		::=  { macPresetPerformanceEntry  30 }


	macPreset29		 OBJECT-TYPE
		SYNTAX					 Counter32
		MAX-ACCESS			 read-only
		STATUS					 current
		DESCRIPTION			 " -- "
		::=  { macPresetPerformanceEntry  31 }


	macPreset30		 OBJECT-TYPE
		SYNTAX					 Counter32
		MAX-ACCESS			 read-only
		STATUS					 current
		DESCRIPTION			 " -- "
		::=  { macPresetPerformanceEntry  32 }


	macPreset31		 OBJECT-TYPE
		SYNTAX					 Counter32
		MAX-ACCESS			 read-only
		STATUS					 current
		DESCRIPTION			 " -- "
		::=  { macPresetPerformanceEntry  33 }


	macPreset32		 OBJECT-TYPE
		SYNTAX					 Counter32
		MAX-ACCESS			 read-only
		STATUS					 current
		DESCRIPTION			 " -- "
		::=  { macPresetPerformanceEntry  34 }


	macPreset33		 OBJECT-TYPE
		SYNTAX					 Counter32
		MAX-ACCESS			 read-only
		STATUS					 current
		DESCRIPTION			 " -- "
		::=  { macPresetPerformanceEntry  35 }


	macPreset34		 OBJECT-TYPE
		SYNTAX					 Counter32
		MAX-ACCESS			 read-only
		STATUS					 current
		DESCRIPTION			 " -- "
		::=  { macPresetPerformanceEntry  36 }


	macPreset35		 OBJECT-TYPE
		SYNTAX					 Counter32
		MAX-ACCESS			 read-only
		STATUS					 current
		DESCRIPTION			 " -- "
		::=  { macPresetPerformanceEntry  37 }


	macPreset36		 OBJECT-TYPE
		SYNTAX					 Counter32
		MAX-ACCESS			 read-only
		STATUS					 current
		DESCRIPTION			 " -- "
		::=  { macPresetPerformanceEntry  38 }


	macPreset37		 OBJECT-TYPE
		SYNTAX					 Counter32
		MAX-ACCESS			 read-only
		STATUS					 current
		DESCRIPTION			 " -- "
		::=  { macPresetPerformanceEntry  39 }


	macPreset38		 OBJECT-TYPE
		SYNTAX					 Counter32
		MAX-ACCESS			 read-only
		STATUS					 current
		DESCRIPTION			 " -- "
		::=  { macPresetPerformanceEntry  40 }


	macPreset39		 OBJECT-TYPE
		SYNTAX					 Counter32
		MAX-ACCESS			 read-only
		STATUS					 current
		DESCRIPTION			 " -- "
		::=  { macPresetPerformanceEntry  41 }


	macPreset40		 OBJECT-TYPE
		SYNTAX					 Counter32
		MAX-ACCESS			 read-only
		STATUS					 current
		DESCRIPTION			 " -- "
		::=  { macPresetPerformanceEntry  42 }


	videoPerfOfMacTable		 OBJECT-TYPE
		SYNTAX					 SEQUENCE  OF	 VideoPerfOfMacEntry
		MAX-ACCESS			 not-accessible
		STATUS					 current
		DESCRIPTION			 " -- "
		::=  { macrelatedOriginCounter  26 }


	videoPerfOfMacEntry		 OBJECT-TYPE
		SYNTAX					 VideoPerfOfMacEntry
		MAX-ACCESS			 not-accessible
		STATUS					 current
		DESCRIPTION			 " -- "
		INDEX						{ videoPerfOfMacLcId }
		::=  { videoPerfOfMacTable  1 }


	VideoPerfOfMacEntry		 ::=  SEQUENCE {
		videoPerfOfMacLcId					Integer32,
		videoPerfOfMacRowStatus					RowStatus,
		macVideoSchDl					Counter32,
		macVideoUsedPrbPerSfnDlMax					Counter32,
		macVideoUsedPrbPerSfnDlAvg					Counter32,
		macVideoSendBitLenSucDl					Counter32,
		macVideoUsedPrbPerSfnUlMax					Counter32,
		macVideoUsedPrbPerSfnUlAvg					Counter32,
		macVideoRevBitLenSucUl					Counter32
		}


	videoPerfOfMacLcId		 OBJECT-TYPE
		SYNTAX					 Integer32( 0 .. 23 )
		MAX-ACCESS			 not-accessible
		STATUS					 current
		DESCRIPTION			 " -- "
		::=  { videoPerfOfMacEntry  1 }


	videoPerfOfMacRowStatus		 OBJECT-TYPE
		SYNTAX					 RowStatus
		MAX-ACCESS			 read-only
		STATUS					 current
		DESCRIPTION			 " -- "
		::=  { videoPerfOfMacEntry  2 }


	macVideoSchDl		 OBJECT-TYPE
		SYNTAX					 Counter32
		MAX-ACCESS			 read-only
		STATUS					 current
		DESCRIPTION			 " -- "
		::=  { videoPerfOfMacEntry  3 }


	macVideoUsedPrbPerSfnDlMax		 OBJECT-TYPE
		SYNTAX					 Counter32
		MAX-ACCESS			 read-only
		STATUS					 current
		DESCRIPTION			 " -- "
		::=  { videoPerfOfMacEntry  4 }


	macVideoUsedPrbPerSfnDlAvg		 OBJECT-TYPE
		SYNTAX					 Counter32
		MAX-ACCESS			 read-only
		STATUS					 current
		DESCRIPTION			 " -- "
		::=  { videoPerfOfMacEntry  5 }


	macVideoSendBitLenSucDl		 OBJECT-TYPE
		SYNTAX					 Counter32
		MAX-ACCESS			 read-only
		STATUS					 current
		DESCRIPTION			 " -- "
		::=  { videoPerfOfMacEntry  6 }


	macVideoUsedPrbPerSfnUlMax		 OBJECT-TYPE
		SYNTAX					 Counter32
		MAX-ACCESS			 read-only
		STATUS					 current
		DESCRIPTION			 " -- "
		::=  { videoPerfOfMacEntry  7 }


	macVideoUsedPrbPerSfnUlAvg		 OBJECT-TYPE
		SYNTAX					 Counter32
		MAX-ACCESS			 read-only
		STATUS					 current
		DESCRIPTION			 " -- "
		::=  { videoPerfOfMacEntry  8 }


	macVideoRevBitLenSucUl		 OBJECT-TYPE
		SYNTAX					 Counter32
		MAX-ACCESS			 read-only
		STATUS					 current
		DESCRIPTION			 " -- "
		::=  { videoPerfOfMacEntry  9 }


	phrPerformTable		 OBJECT-TYPE
		SYNTAX					 SEQUENCE  OF	 PhrPerformEntry
		MAX-ACCESS			 not-accessible
		STATUS					 current
		DESCRIPTION			 " -- "
		::=  { macrelatedOriginCounter  27 }


	phrPerformEntry		 OBJECT-TYPE
		SYNTAX					 PhrPerformEntry
		MAX-ACCESS			 not-accessible
		STATUS					 current
		DESCRIPTION			 " -- "
		INDEX						{ phrPerformLcId }
		::=  { phrPerformTable  1 }


	PhrPerformEntry		 ::=  SEQUENCE {
		phrPerformLcId					Integer32,
		phrPerformRowStatus					RowStatus,
		macPhrIndex0					Counter32,
		macPhrIndex1					Counter32,
		macPhrIndex2					Counter32,
		macPhrIndex3					Counter32,
		macPhrIndex4					Counter32,
		macPhrIndex5					Counter32,
		macPhrIndex6					Counter32,
		macPhrIndex7					Counter32,
		macPhrIndex8					Counter32,
		macPhrIndex9					Counter32,
		macPhrIndex10					Counter32,
		macPhrIndex11					Counter32,
		macPhrIndex12					Counter32,
		macPhrIndex13					Counter32,
		macPhrIndex14					Counter32,
		macPhrIndex15					Counter32,
		macPhrIndex16					Counter32,
		macPhrIndex17					Counter32,
		macPhrIndex18					Counter32,
		macPhrIndex19					Counter32,
		macPhrIndex20					Counter32,
		macPhrIndex21					Counter32,
		macPhrIndex22					Counter32,
		macPhrIndex23					Counter32,
		macPhrIndex24					Counter32,
		macPhrIndex25					Counter32,
		macPhrIndex26					Counter32,
		macPhrIndex27					Counter32,
		macPhrIndex28					Counter32,
		macPhrIndex29					Counter32,
		macPhrIndex30					Counter32,
		macPhrIndex31					Counter32,
		macPhrIndex32					Counter32,
		macPhrIndex33					Counter32,
		macPhrIndex34					Counter32,
		macPhrIndex35					Counter32,
		macPhrIndex36					Counter32,
		macPhrIndex37					Counter32,
		macPhrIndex38					Counter32,
		macPhrIndex39					Counter32,
		macPhrIndex40					Counter32,
		macPhrIndex41					Counter32,
		macPhrIndex42					Counter32,
		macPhrIndex43					Counter32,
		macPhrIndex44					Counter32,
		macPhrIndex45					Counter32,
		macPhrIndex46					Counter32,
		macPhrIndex47					Counter32,
		macPhrIndex48					Counter32,
		macPhrIndex49					Counter32,
		macPhrIndex50					Counter32,
		macPhrIndex51					Counter32,
		macPhrIndex52					Counter32,
		macPhrIndex53					Counter32,
		macPhrIndex54					Counter32,
		macPhrIndex55					Counter32,
		macPhrIndex56					Counter32,
		macPhrIndex57					Counter32,
		macPhrIndex58					Counter32,
		macPhrIndex59					Counter32,
		macPhrIndex60					Counter32,
		macPhrIndex61					Counter32,
		macPhrIndex62					Counter32,
		macPhrIndex63					Counter32
		}


	phrPerformLcId		 OBJECT-TYPE
		SYNTAX					 Integer32( 0 .. 23 )
		MAX-ACCESS			 not-accessible
		STATUS					 current
		DESCRIPTION			 " -- "
		::=  { phrPerformEntry  1 }


	phrPerformRowStatus		 OBJECT-TYPE
		SYNTAX					 RowStatus
		MAX-ACCESS			 read-only
		STATUS					 current
		DESCRIPTION			 " -- "
		::=  { phrPerformEntry  2 }


	macPhrIndex0		 OBJECT-TYPE
		SYNTAX					 Counter32
		MAX-ACCESS			 read-only
		STATUS					 current
		DESCRIPTION			 " -- "
		::=  { phrPerformEntry  3 }


	macPhrIndex1		 OBJECT-TYPE
		SYNTAX					 Counter32
		MAX-ACCESS			 read-only
		STATUS					 current
		DESCRIPTION			 " -- "
		::=  { phrPerformEntry  4 }


	macPhrIndex2		 OBJECT-TYPE
		SYNTAX					 Counter32
		MAX-ACCESS			 read-only
		STATUS					 current
		DESCRIPTION			 " -- "
		::=  { phrPerformEntry  5 }


	macPhrIndex3		 OBJECT-TYPE
		SYNTAX					 Counter32
		MAX-ACCESS			 read-only
		STATUS					 current
		DESCRIPTION			 " -- "
		::=  { phrPerformEntry  6 }


	macPhrIndex4		 OBJECT-TYPE
		SYNTAX					 Counter32
		MAX-ACCESS			 read-only
		STATUS					 current
		DESCRIPTION			 " -- "
		::=  { phrPerformEntry  7 }


	macPhrIndex5		 OBJECT-TYPE
		SYNTAX					 Counter32
		MAX-ACCESS			 read-only
		STATUS					 current
		DESCRIPTION			 " -- "
		::=  { phrPerformEntry  8 }


	macPhrIndex6		 OBJECT-TYPE
		SYNTAX					 Counter32
		MAX-ACCESS			 read-only
		STATUS					 current
		DESCRIPTION			 " -- "
		::=  { phrPerformEntry  9 }


	macPhrIndex7		 OBJECT-TYPE
		SYNTAX					 Counter32
		MAX-ACCESS			 read-only
		STATUS					 current
		DESCRIPTION			 " -- "
		::=  { phrPerformEntry  10 }


	macPhrIndex8		 OBJECT-TYPE
		SYNTAX					 Counter32
		MAX-ACCESS			 read-only
		STATUS					 current
		DESCRIPTION			 " -- "
		::=  { phrPerformEntry  11 }


	macPhrIndex9		 OBJECT-TYPE
		SYNTAX					 Counter32
		MAX-ACCESS			 read-only
		STATUS					 current
		DESCRIPTION			 " -- "
		::=  { phrPerformEntry  12 }


	macPhrIndex10		 OBJECT-TYPE
		SYNTAX					 Counter32
		MAX-ACCESS			 read-only
		STATUS					 current
		DESCRIPTION			 " -- "
		::=  { phrPerformEntry  13 }


	macPhrIndex11		 OBJECT-TYPE
		SYNTAX					 Counter32
		MAX-ACCESS			 read-only
		STATUS					 current
		DESCRIPTION			 " -- "
		::=  { phrPerformEntry  14 }


	macPhrIndex12		 OBJECT-TYPE
		SYNTAX					 Counter32
		MAX-ACCESS			 read-only
		STATUS					 current
		DESCRIPTION			 " -- "
		::=  { phrPerformEntry  15 }


	macPhrIndex13		 OBJECT-TYPE
		SYNTAX					 Counter32
		MAX-ACCESS			 read-only
		STATUS					 current
		DESCRIPTION			 " -- "
		::=  { phrPerformEntry  16 }


	macPhrIndex14		 OBJECT-TYPE
		SYNTAX					 Counter32
		MAX-ACCESS			 read-only
		STATUS					 current
		DESCRIPTION			 " -- "
		::=  { phrPerformEntry  17 }


	macPhrIndex15		 OBJECT-TYPE
		SYNTAX					 Counter32
		MAX-ACCESS			 read-only
		STATUS					 current
		DESCRIPTION			 " -- "
		::=  { phrPerformEntry  18 }


	macPhrIndex16		 OBJECT-TYPE
		SYNTAX					 Counter32
		MAX-ACCESS			 read-only
		STATUS					 current
		DESCRIPTION			 " -- "
		::=  { phrPerformEntry  19 }


	macPhrIndex17		 OBJECT-TYPE
		SYNTAX					 Counter32
		MAX-ACCESS			 read-only
		STATUS					 current
		DESCRIPTION			 " -- "
		::=  { phrPerformEntry  20 }


	macPhrIndex18		 OBJECT-TYPE
		SYNTAX					 Counter32
		MAX-ACCESS			 read-only
		STATUS					 current
		DESCRIPTION			 " -- "
		::=  { phrPerformEntry  21 }


	macPhrIndex19		 OBJECT-TYPE
		SYNTAX					 Counter32
		MAX-ACCESS			 read-only
		STATUS					 current
		DESCRIPTION			 " -- "
		::=  { phrPerformEntry  22 }


	macPhrIndex20		 OBJECT-TYPE
		SYNTAX					 Counter32
		MAX-ACCESS			 read-only
		STATUS					 current
		DESCRIPTION			 " -- "
		::=  { phrPerformEntry  23 }


	macPhrIndex21		 OBJECT-TYPE
		SYNTAX					 Counter32
		MAX-ACCESS			 read-only
		STATUS					 current
		DESCRIPTION			 " -- "
		::=  { phrPerformEntry  24 }


	macPhrIndex22		 OBJECT-TYPE
		SYNTAX					 Counter32
		MAX-ACCESS			 read-only
		STATUS					 current
		DESCRIPTION			 " -- "
		::=  { phrPerformEntry  25 }


	macPhrIndex23		 OBJECT-TYPE
		SYNTAX					 Counter32
		MAX-ACCESS			 read-only
		STATUS					 current
		DESCRIPTION			 " -- "
		::=  { phrPerformEntry  26 }


	macPhrIndex24		 OBJECT-TYPE
		SYNTAX					 Counter32
		MAX-ACCESS			 read-only
		STATUS					 current
		DESCRIPTION			 " -- "
		::=  { phrPerformEntry  27 }


	macPhrIndex25		 OBJECT-TYPE
		SYNTAX					 Counter32
		MAX-ACCESS			 read-only
		STATUS					 current
		DESCRIPTION			 " -- "
		::=  { phrPerformEntry  28 }


	macPhrIndex26		 OBJECT-TYPE
		SYNTAX					 Counter32
		MAX-ACCESS			 read-only
		STATUS					 current
		DESCRIPTION			 " -- "
		::=  { phrPerformEntry  29 }


	macPhrIndex27		 OBJECT-TYPE
		SYNTAX					 Counter32
		MAX-ACCESS			 read-only
		STATUS					 current
		DESCRIPTION			 " -- "
		::=  { phrPerformEntry  30 }


	macPhrIndex28		 OBJECT-TYPE
		SYNTAX					 Counter32
		MAX-ACCESS			 read-only
		STATUS					 current
		DESCRIPTION			 " -- "
		::=  { phrPerformEntry  31 }


	macPhrIndex29		 OBJECT-TYPE
		SYNTAX					 Counter32
		MAX-ACCESS			 read-only
		STATUS					 current
		DESCRIPTION			 " -- "
		::=  { phrPerformEntry  32 }


	macPhrIndex30		 OBJECT-TYPE
		SYNTAX					 Counter32
		MAX-ACCESS			 read-only
		STATUS					 current
		DESCRIPTION			 " -- "
		::=  { phrPerformEntry  33 }


	macPhrIndex31		 OBJECT-TYPE
		SYNTAX					 Counter32
		MAX-ACCESS			 read-only
		STATUS					 current
		DESCRIPTION			 " -- "
		::=  { phrPerformEntry  34 }


	macPhrIndex32		 OBJECT-TYPE
		SYNTAX					 Counter32
		MAX-ACCESS			 read-only
		STATUS					 current
		DESCRIPTION			 " -- "
		::=  { phrPerformEntry  35 }


	macPhrIndex33		 OBJECT-TYPE
		SYNTAX					 Counter32
		MAX-ACCESS			 read-only
		STATUS					 current
		DESCRIPTION			 " -- "
		::=  { phrPerformEntry  36 }


	macPhrIndex34		 OBJECT-TYPE
		SYNTAX					 Counter32
		MAX-ACCESS			 read-only
		STATUS					 current
		DESCRIPTION			 " -- "
		::=  { phrPerformEntry  37 }


	macPhrIndex35		 OBJECT-TYPE
		SYNTAX					 Counter32
		MAX-ACCESS			 read-only
		STATUS					 current
		DESCRIPTION			 " -- "
		::=  { phrPerformEntry  38 }


	macPhrIndex36		 OBJECT-TYPE
		SYNTAX					 Counter32
		MAX-ACCESS			 read-only
		STATUS					 current
		DESCRIPTION			 " -- "
		::=  { phrPerformEntry  39 }


	macPhrIndex37		 OBJECT-TYPE
		SYNTAX					 Counter32
		MAX-ACCESS			 read-only
		STATUS					 current
		DESCRIPTION			 " -- "
		::=  { phrPerformEntry  40 }


	macPhrIndex38		 OBJECT-TYPE
		SYNTAX					 Counter32
		MAX-ACCESS			 read-only
		STATUS					 current
		DESCRIPTION			 " -- "
		::=  { phrPerformEntry  41 }


	macPhrIndex39		 OBJECT-TYPE
		SYNTAX					 Counter32
		MAX-ACCESS			 read-only
		STATUS					 current
		DESCRIPTION			 " -- "
		::=  { phrPerformEntry  42 }


	macPhrIndex40		 OBJECT-TYPE
		SYNTAX					 Counter32
		MAX-ACCESS			 read-only
		STATUS					 current
		DESCRIPTION			 " -- "
		::=  { phrPerformEntry  43 }


	macPhrIndex41		 OBJECT-TYPE
		SYNTAX					 Counter32
		MAX-ACCESS			 read-only
		STATUS					 current
		DESCRIPTION			 " -- "
		::=  { phrPerformEntry  44 }


	macPhrIndex42		 OBJECT-TYPE
		SYNTAX					 Counter32
		MAX-ACCESS			 read-only
		STATUS					 current
		DESCRIPTION			 " -- "
		::=  { phrPerformEntry  45 }


	macPhrIndex43		 OBJECT-TYPE
		SYNTAX					 Counter32
		MAX-ACCESS			 read-only
		STATUS					 current
		DESCRIPTION			 " -- "
		::=  { phrPerformEntry  46 }


	macPhrIndex44		 OBJECT-TYPE
		SYNTAX					 Counter32
		MAX-ACCESS			 read-only
		STATUS					 current
		DESCRIPTION			 " -- "
		::=  { phrPerformEntry  47 }


	macPhrIndex45		 OBJECT-TYPE
		SYNTAX					 Counter32
		MAX-ACCESS			 read-only
		STATUS					 current
		DESCRIPTION			 " -- "
		::=  { phrPerformEntry  48 }


	macPhrIndex46		 OBJECT-TYPE
		SYNTAX					 Counter32
		MAX-ACCESS			 read-only
		STATUS					 current
		DESCRIPTION			 " -- "
		::=  { phrPerformEntry  49 }


	macPhrIndex47		 OBJECT-TYPE
		SYNTAX					 Counter32
		MAX-ACCESS			 read-only
		STATUS					 current
		DESCRIPTION			 " -- "
		::=  { phrPerformEntry  50 }


	macPhrIndex48		 OBJECT-TYPE
		SYNTAX					 Counter32
		MAX-ACCESS			 read-only
		STATUS					 current
		DESCRIPTION			 " -- "
		::=  { phrPerformEntry  51 }


	macPhrIndex49		 OBJECT-TYPE
		SYNTAX					 Counter32
		MAX-ACCESS			 read-only
		STATUS					 current
		DESCRIPTION			 " -- "
		::=  { phrPerformEntry  52 }


	macPhrIndex50		 OBJECT-TYPE
		SYNTAX					 Counter32
		MAX-ACCESS			 read-only
		STATUS					 current
		DESCRIPTION			 " -- "
		::=  { phrPerformEntry  53 }


	macPhrIndex51		 OBJECT-TYPE
		SYNTAX					 Counter32
		MAX-ACCESS			 read-only
		STATUS					 current
		DESCRIPTION			 " -- "
		::=  { phrPerformEntry  54 }


	macPhrIndex52		 OBJECT-TYPE
		SYNTAX					 Counter32
		MAX-ACCESS			 read-only
		STATUS					 current
		DESCRIPTION			 " -- "
		::=  { phrPerformEntry  55 }


	macPhrIndex53		 OBJECT-TYPE
		SYNTAX					 Counter32
		MAX-ACCESS			 read-only
		STATUS					 current
		DESCRIPTION			 " -- "
		::=  { phrPerformEntry  56 }


	macPhrIndex54		 OBJECT-TYPE
		SYNTAX					 Counter32
		MAX-ACCESS			 read-only
		STATUS					 current
		DESCRIPTION			 " -- "
		::=  { phrPerformEntry  57 }


	macPhrIndex55		 OBJECT-TYPE
		SYNTAX					 Counter32
		MAX-ACCESS			 read-only
		STATUS					 current
		DESCRIPTION			 " -- "
		::=  { phrPerformEntry  58 }


	macPhrIndex56		 OBJECT-TYPE
		SYNTAX					 Counter32
		MAX-ACCESS			 read-only
		STATUS					 current
		DESCRIPTION			 " -- "
		::=  { phrPerformEntry  59 }


	macPhrIndex57		 OBJECT-TYPE
		SYNTAX					 Counter32
		MAX-ACCESS			 read-only
		STATUS					 current
		DESCRIPTION			 " -- "
		::=  { phrPerformEntry  60 }


	macPhrIndex58		 OBJECT-TYPE
		SYNTAX					 Counter32
		MAX-ACCESS			 read-only
		STATUS					 current
		DESCRIPTION			 " -- "
		::=  { phrPerformEntry  61 }


	macPhrIndex59		 OBJECT-TYPE
		SYNTAX					 Counter32
		MAX-ACCESS			 read-only
		STATUS					 current
		DESCRIPTION			 " -- "
		::=  { phrPerformEntry  62 }


	macPhrIndex60		 OBJECT-TYPE
		SYNTAX					 Counter32
		MAX-ACCESS			 read-only
		STATUS					 current
		DESCRIPTION			 " -- "
		::=  { phrPerformEntry  63 }


	macPhrIndex61		 OBJECT-TYPE
		SYNTAX					 Counter32
		MAX-ACCESS			 read-only
		STATUS					 current
		DESCRIPTION			 " -- "
		::=  { phrPerformEntry  64 }


	macPhrIndex62		 OBJECT-TYPE
		SYNTAX					 Counter32
		MAX-ACCESS			 read-only
		STATUS					 current
		DESCRIPTION			 " -- "
		::=  { phrPerformEntry  65 }


	macPhrIndex63		 OBJECT-TYPE
		SYNTAX					 Counter32
		MAX-ACCESS			 read-only
		STATUS					 current
		DESCRIPTION			 " -- "
		::=  { phrPerformEntry  66 }


	perfOfMacForTestTable		 OBJECT-TYPE
		SYNTAX					 SEQUENCE  OF	 PerfOfMacForTestEntry
		MAX-ACCESS			 not-accessible
		STATUS					 current
		DESCRIPTION			 " -- "
		::=  { macrelatedOriginCounter  28 }


	perfOfMacForTestEntry		 OBJECT-TYPE
		SYNTAX					 PerfOfMacForTestEntry
		MAX-ACCESS			 not-accessible
		STATUS					 current
		DESCRIPTION			 " -- "
		INDEX						{ perfOfMacForTestLcId }
		::=  { perfOfMacForTestTable  1 }


	PerfOfMacForTestEntry		 ::=  SEQUENCE {
		perfOfMacForTestLcId					Integer32,
		perfOfMacForTestRowStatus					RowStatus,
		macVipNumDataUl					Counter32,
		macVipNumDataDl					Counter32,
		macVipNumVolte					Counter32,
		macVipNumVedio					Counter32,
		macVipNumGoldVoice					Counter32,
		macVipNumDisconfGv					Counter32
		}


	perfOfMacForTestLcId		 OBJECT-TYPE
		SYNTAX					 Integer32( 0 .. 23 )
		MAX-ACCESS			 not-accessible
		STATUS					 current
		DESCRIPTION			 " -- "
		::=  { perfOfMacForTestEntry  1 }


	perfOfMacForTestRowStatus		 OBJECT-TYPE
		SYNTAX					 RowStatus
		MAX-ACCESS			 read-only
		STATUS					 current
		DESCRIPTION			 " -- "
		::=  { perfOfMacForTestEntry  2 }


	macVipNumDataUl		 OBJECT-TYPE
		SYNTAX					 Counter32
		MAX-ACCESS			 read-only
		STATUS					 current
		DESCRIPTION			 " -- "
		::=  { perfOfMacForTestEntry  3 }


	macVipNumDataDl		 OBJECT-TYPE
		SYNTAX					 Counter32
		MAX-ACCESS			 read-only
		STATUS					 current
		DESCRIPTION			 " -- "
		::=  { perfOfMacForTestEntry  4 }


	macVipNumVolte		 OBJECT-TYPE
		SYNTAX					 Counter32
		MAX-ACCESS			 read-only
		STATUS					 current
		DESCRIPTION			 " -- "
		::=  { perfOfMacForTestEntry  5 }


	macVipNumVedio		 OBJECT-TYPE
		SYNTAX					 Counter32
		MAX-ACCESS			 read-only
		STATUS					 current
		DESCRIPTION			 " -- "
		::=  { perfOfMacForTestEntry  6 }


	macVipNumGoldVoice		 OBJECT-TYPE
		SYNTAX					 Counter32
		MAX-ACCESS			 read-only
		STATUS					 current
		DESCRIPTION			 " -- "
		::=  { perfOfMacForTestEntry  7 }


	macVipNumDisconfGv		 OBJECT-TYPE
		SYNTAX					 Counter32
		MAX-ACCESS			 read-only
		STATUS					 current
		DESCRIPTION			 " -- "
		::=  { perfOfMacForTestEntry  8 }


	massiveMIMOTable		 OBJECT-TYPE
		SYNTAX					 SEQUENCE  OF	 MassiveMIMOEntry
		MAX-ACCESS			 not-accessible
		STATUS					 current
		DESCRIPTION			 " -- "
		::=  { macrelatedOriginCounter  29 }


	massiveMIMOEntry		 OBJECT-TYPE
		SYNTAX					 MassiveMIMOEntry
		MAX-ACCESS			 not-accessible
		STATUS					 current
		DESCRIPTION			 " -- "
		INDEX						{ massiveMIMOLcId }
		::=  { massiveMIMOTable  1 }


	MassiveMIMOEntry		 ::=  SEQUENCE {
		massiveMIMOLcId					Integer32,
		massiveMIMORowStatus					RowStatus,
		macNbrRbUlMassiveMimoSM1					Counter32,
		macNbrRbUlMassiveMimoSM2					Counter32,
		macNbrRbUlMassiveMimoSM3					Counter32,
		macNbrRbUlMassiveMimoSM4					Counter32,
		macNbrRbUlMassiveMimoSM5					Counter32,
		macNbrRbUlMassiveMimoSM6					Counter32,
		macNbrRbUlMassiveMimoSM7					Counter32,
		macNbrRbUlMassiveMimoSM8					Counter32,
		macNbrRbDlMassiveMimoSM1					Counter32,
		macNbrRbDlMassiveMimoSM2					Counter32,
		macNbrRbDlMassiveMimoSM3					Counter32,
		macNbrRbDlMassiveMimoSM4					Counter32,
		macNbrRbDlMassiveMimoSM5					Counter32,
		macNbrRbDlMassiveMimoSM6					Counter32,
		macNbrRbDlMassiveMimoSM7					Counter32,
		macNbrRbDlMassiveMimoSM8					Counter32,
		macNbrRbDlMassiveMimoSM9					Counter32,
		macNbrRbDlMassiveMimoSM10					Counter32,
		macNbrRbDlMassiveMimoSM11					Counter32,
		macNbrRbDlMassiveMimoSM12					Counter32,
		macNbrRbDlMassiveMimoSM13					Counter32,
		macNbrRbDlMassiveMimoSM14					Counter32,
		macNbrRbDlMassiveMimoSM15					Counter32,
		macNbrRbDlMassiveMimoSM16					Counter32,
		macNbrErrTbUlMassiveMimoSM1					Counter32,
		macNbrErrTbUlMassiveMimoSM2					Counter32,
		macNbrErrTbUlMassiveMimoSM3					Counter32,
		macNbrErrTbUlMassiveMimoSM4					Counter32,
		macNbrErrTbUlMassiveMimoSM5					Counter32,
		macNbrErrTbUlMassiveMimoSM6					Counter32,
		macNbrErrTbUlMassiveMimoSM7					Counter32,
		macNbrErrTbUlMassiveMimoSM8					Counter32,
		macNbrErrTbDlMassiveMimoSM1					Counter32,
		macNbrErrTbDlMassiveMimoSM2					Counter32,
		macNbrErrTbDlMassiveMimoSM3					Counter32,
		macNbrErrTbDlMassiveMimoSM4					Counter32,
		macNbrErrTbDlMassiveMimoSM5					Counter32,
		macNbrErrTbDlMassiveMimoSM6					Counter32,
		macNbrErrTbDlMassiveMimoSM7					Counter32,
		macNbrErrTbDlMassiveMimoSM8					Counter32,
		macNbrErrTbDlMassiveMimoSM9					Counter32,
		macNbrErrTbDlMassiveMimoSM10					Counter32,
		macNbrErrTbDlMassiveMimoSM11					Counter32,
		macNbrErrTbDlMassiveMimoSM12					Counter32,
		macNbrErrTbDlMassiveMimoSM13					Counter32,
		macNbrErrTbDlMassiveMimoSM14					Counter32,
		macNbrErrTbDlMassiveMimoSM15					Counter32,
		macNbrErrTbDlMassiveMimoSM16					Counter32,
		macNbrTbUlMassiveMimoSM1					Counter32,
		macNbrTbUlMassiveMimoSM2					Counter32,
		macNbrTbUlMassiveMimoSM3					Counter32,
		macNbrTbUlMassiveMimoSM4					Counter32,
		macNbrTbUlMassiveMimoSM5					Counter32,
		macNbrTbUlMassiveMimoSM6					Counter32,
		macNbrTbUlMassiveMimoSM7					Counter32,
		macNbrTbUlMassiveMimoSM8					Counter32,
		macNbrTbDlMassiveMimoSM1					Counter32,
		macNbrTbDlMassiveMimoSM2					Counter32,
		macNbrTbDlMassiveMimoSM3					Counter32,
		macNbrTbDlMassiveMimoSM4					Counter32,
		macNbrTbDlMassiveMimoSM5					Counter32,
		macNbrTbDlMassiveMimoSM6					Counter32,
		macNbrTbDlMassiveMimoSM7					Counter32,
		macNbrTbDlMassiveMimoSM8					Counter32,
		macNbrTbDlMassiveMimoSM9					Counter32,
		macNbrTbDlMassiveMimoSM10					Counter32,
		macNbrTbDlMassiveMimoSM11					Counter32,
		macNbrTbDlMassiveMimoSM12					Counter32,
		macNbrTbDlMassiveMimoSM13					Counter32,
		macNbrTbDlMassiveMimoSM14					Counter32,
		macNbrTbDlMassiveMimoSM15					Counter32,
		macNbrTbDlMassiveMimoSM16					Counter32,
		macOctUlMassiveMimoSM1					Counter32,
		macOctUlMassiveMimoSM2					Counter32,
		macOctUlMassiveMimoSM3					Counter32,
		macOctUlMassiveMimoSM4					Counter32,
		macOctUlMassiveMimoSM5					Counter32,
		macOctUlMassiveMimoSM6					Counter32,
		macOctUlMassiveMimoSM7					Counter32,
		macOctUlMassiveMimoSM8					Counter32,
		macOctDlMassiveMimoSM1					Counter32,
		macOctDlMassiveMimoSM2					Counter32,
		macOctDlMassiveMimoSM3					Counter32,
		macOctDlMassiveMimoSM4					Counter32,
		macOctDlMassiveMimoSM5					Counter32,
		macOctDlMassiveMimoSM6					Counter32,
		macOctDlMassiveMimoSM7					Counter32,
		macOctDlMassiveMimoSM8					Counter32,
		macOctDlMassiveMimoSM9					Counter32,
		macOctDlMassiveMimoSM10					Counter32,
		macOctDlMassiveMimoSM11					Counter32,
		macOctDlMassiveMimoSM12					Counter32,
		macOctDlMassiveMimoSM13					Counter32,
		macOctDlMassiveMimoSM14					Counter32,
		macOctDlMassiveMimoSM15					Counter32,
		macOctDlMassiveMimoSM16					Counter32,
		macDlMassiveMimoPair01					Counter32,
		macDlMassiveMimoPair02					Counter32,
		macDlMassiveMimoPair03					Counter32
		}


	massiveMIMOLcId		 OBJECT-TYPE
		SYNTAX					 Integer32( 0 .. 23 )
		MAX-ACCESS			 not-accessible
		STATUS					 current
		DESCRIPTION			 " -- "
		::=  { massiveMIMOEntry  1 }


	massiveMIMORowStatus		 OBJECT-TYPE
		SYNTAX					 RowStatus
		MAX-ACCESS			 read-only
		STATUS					 current
		DESCRIPTION			 " -- "
		::=  { massiveMIMOEntry  2 }


	macNbrRbUlMassiveMimoSM1		 OBJECT-TYPE
		SYNTAX					 Counter32
		MAX-ACCESS			 read-only
		STATUS					 current
		DESCRIPTION			 " -- "
		::=  { massiveMIMOEntry  3 }


	macNbrRbUlMassiveMimoSM2		 OBJECT-TYPE
		SYNTAX					 Counter32
		MAX-ACCESS			 read-only
		STATUS					 current
		DESCRIPTION			 " -- "
		::=  { massiveMIMOEntry  4 }


	macNbrRbUlMassiveMimoSM3		 OBJECT-TYPE
		SYNTAX					 Counter32
		MAX-ACCESS			 read-only
		STATUS					 current
		DESCRIPTION			 " -- "
		::=  { massiveMIMOEntry  5 }


	macNbrRbUlMassiveMimoSM4		 OBJECT-TYPE
		SYNTAX					 Counter32
		MAX-ACCESS			 read-only
		STATUS					 current
		DESCRIPTION			 " -- "
		::=  { massiveMIMOEntry  6 }


	macNbrRbUlMassiveMimoSM5		 OBJECT-TYPE
		SYNTAX					 Counter32
		MAX-ACCESS			 read-only
		STATUS					 current
		DESCRIPTION			 " -- "
		::=  { massiveMIMOEntry  7 }


	macNbrRbUlMassiveMimoSM6		 OBJECT-TYPE
		SYNTAX					 Counter32
		MAX-ACCESS			 read-only
		STATUS					 current
		DESCRIPTION			 " -- "
		::=  { massiveMIMOEntry  8 }


	macNbrRbUlMassiveMimoSM7		 OBJECT-TYPE
		SYNTAX					 Counter32
		MAX-ACCESS			 read-only
		STATUS					 current
		DESCRIPTION			 " -- "
		::=  { massiveMIMOEntry  9 }


	macNbrRbUlMassiveMimoSM8		 OBJECT-TYPE
		SYNTAX					 Counter32
		MAX-ACCESS			 read-only
		STATUS					 current
		DESCRIPTION			 " -- "
		::=  { massiveMIMOEntry  10 }


	macNbrRbDlMassiveMimoSM1		 OBJECT-TYPE
		SYNTAX					 Counter32
		MAX-ACCESS			 read-only
		STATUS					 current
		DESCRIPTION			 " -- "
		::=  { massiveMIMOEntry  11 }


	macNbrRbDlMassiveMimoSM2		 OBJECT-TYPE
		SYNTAX					 Counter32
		MAX-ACCESS			 read-only
		STATUS					 current
		DESCRIPTION			 " -- "
		::=  { massiveMIMOEntry  12 }


	macNbrRbDlMassiveMimoSM3		 OBJECT-TYPE
		SYNTAX					 Counter32
		MAX-ACCESS			 read-only
		STATUS					 current
		DESCRIPTION			 " -- "
		::=  { massiveMIMOEntry  13 }


	macNbrRbDlMassiveMimoSM4		 OBJECT-TYPE
		SYNTAX					 Counter32
		MAX-ACCESS			 read-only
		STATUS					 current
		DESCRIPTION			 " -- "
		::=  { massiveMIMOEntry  14 }


	macNbrRbDlMassiveMimoSM5		 OBJECT-TYPE
		SYNTAX					 Counter32
		MAX-ACCESS			 read-only
		STATUS					 current
		DESCRIPTION			 " -- "
		::=  { massiveMIMOEntry  15 }


	macNbrRbDlMassiveMimoSM6		 OBJECT-TYPE
		SYNTAX					 Counter32
		MAX-ACCESS			 read-only
		STATUS					 current
		DESCRIPTION			 " -- "
		::=  { massiveMIMOEntry  16 }


	macNbrRbDlMassiveMimoSM7		 OBJECT-TYPE
		SYNTAX					 Counter32
		MAX-ACCESS			 read-only
		STATUS					 current
		DESCRIPTION			 " -- "
		::=  { massiveMIMOEntry  17 }


	macNbrRbDlMassiveMimoSM8		 OBJECT-TYPE
		SYNTAX					 Counter32
		MAX-ACCESS			 read-only
		STATUS					 current
		DESCRIPTION			 " -- "
		::=  { massiveMIMOEntry  18 }


	macNbrRbDlMassiveMimoSM9		 OBJECT-TYPE
		SYNTAX					 Counter32
		MAX-ACCESS			 read-only
		STATUS					 current
		DESCRIPTION			 " -- "
		::=  { massiveMIMOEntry  19 }


	macNbrRbDlMassiveMimoSM10		 OBJECT-TYPE
		SYNTAX					 Counter32
		MAX-ACCESS			 read-only
		STATUS					 current
		DESCRIPTION			 " -- "
		::=  { massiveMIMOEntry  20 }


	macNbrRbDlMassiveMimoSM11		 OBJECT-TYPE
		SYNTAX					 Counter32
		MAX-ACCESS			 read-only
		STATUS					 current
		DESCRIPTION			 " -- "
		::=  { massiveMIMOEntry  21 }


	macNbrRbDlMassiveMimoSM12		 OBJECT-TYPE
		SYNTAX					 Counter32
		MAX-ACCESS			 read-only
		STATUS					 current
		DESCRIPTION			 " -- "
		::=  { massiveMIMOEntry  22 }


	macNbrRbDlMassiveMimoSM13		 OBJECT-TYPE
		SYNTAX					 Counter32
		MAX-ACCESS			 read-only
		STATUS					 current
		DESCRIPTION			 " -- "
		::=  { massiveMIMOEntry  23 }


	macNbrRbDlMassiveMimoSM14		 OBJECT-TYPE
		SYNTAX					 Counter32
		MAX-ACCESS			 read-only
		STATUS					 current
		DESCRIPTION			 " -- "
		::=  { massiveMIMOEntry  24 }


	macNbrRbDlMassiveMimoSM15		 OBJECT-TYPE
		SYNTAX					 Counter32
		MAX-ACCESS			 read-only
		STATUS					 current
		DESCRIPTION			 " -- "
		::=  { massiveMIMOEntry  25 }


	macNbrRbDlMassiveMimoSM16		 OBJECT-TYPE
		SYNTAX					 Counter32
		MAX-ACCESS			 read-only
		STATUS					 current
		DESCRIPTION			 " -- "
		::=  { massiveMIMOEntry  26 }


	macNbrErrTbUlMassiveMimoSM1		 OBJECT-TYPE
		SYNTAX					 Counter32
		MAX-ACCESS			 read-only
		STATUS					 current
		DESCRIPTION			 " -- "
		::=  { massiveMIMOEntry  27 }


	macNbrErrTbUlMassiveMimoSM2		 OBJECT-TYPE
		SYNTAX					 Counter32
		MAX-ACCESS			 read-only
		STATUS					 current
		DESCRIPTION			 " -- "
		::=  { massiveMIMOEntry  28 }


	macNbrErrTbUlMassiveMimoSM3		 OBJECT-TYPE
		SYNTAX					 Counter32
		MAX-ACCESS			 read-only
		STATUS					 current
		DESCRIPTION			 " -- "
		::=  { massiveMIMOEntry  29 }


	macNbrErrTbUlMassiveMimoSM4		 OBJECT-TYPE
		SYNTAX					 Counter32
		MAX-ACCESS			 read-only
		STATUS					 current
		DESCRIPTION			 " -- "
		::=  { massiveMIMOEntry  30 }


	macNbrErrTbUlMassiveMimoSM5		 OBJECT-TYPE
		SYNTAX					 Counter32
		MAX-ACCESS			 read-only
		STATUS					 current
		DESCRIPTION			 " -- "
		::=  { massiveMIMOEntry  31 }


	macNbrErrTbUlMassiveMimoSM6		 OBJECT-TYPE
		SYNTAX					 Counter32
		MAX-ACCESS			 read-only
		STATUS					 current
		DESCRIPTION			 " -- "
		::=  { massiveMIMOEntry  32 }


	macNbrErrTbUlMassiveMimoSM7		 OBJECT-TYPE
		SYNTAX					 Counter32
		MAX-ACCESS			 read-only
		STATUS					 current
		DESCRIPTION			 " -- "
		::=  { massiveMIMOEntry  33 }


	macNbrErrTbUlMassiveMimoSM8		 OBJECT-TYPE
		SYNTAX					 Counter32
		MAX-ACCESS			 read-only
		STATUS					 current
		DESCRIPTION			 " -- "
		::=  { massiveMIMOEntry  34 }


	macNbrErrTbDlMassiveMimoSM1		 OBJECT-TYPE
		SYNTAX					 Counter32
		MAX-ACCESS			 read-only
		STATUS					 current
		DESCRIPTION			 " -- "
		::=  { massiveMIMOEntry  35 }


	macNbrErrTbDlMassiveMimoSM2		 OBJECT-TYPE
		SYNTAX					 Counter32
		MAX-ACCESS			 read-only
		STATUS					 current
		DESCRIPTION			 " -- "
		::=  { massiveMIMOEntry  36 }


	macNbrErrTbDlMassiveMimoSM3		 OBJECT-TYPE
		SYNTAX					 Counter32
		MAX-ACCESS			 read-only
		STATUS					 current
		DESCRIPTION			 " -- "
		::=  { massiveMIMOEntry  37 }


	macNbrErrTbDlMassiveMimoSM4		 OBJECT-TYPE
		SYNTAX					 Counter32
		MAX-ACCESS			 read-only
		STATUS					 current
		DESCRIPTION			 " -- "
		::=  { massiveMIMOEntry  38 }


	macNbrErrTbDlMassiveMimoSM5		 OBJECT-TYPE
		SYNTAX					 Counter32
		MAX-ACCESS			 read-only
		STATUS					 current
		DESCRIPTION			 " -- "
		::=  { massiveMIMOEntry  39 }


	macNbrErrTbDlMassiveMimoSM6		 OBJECT-TYPE
		SYNTAX					 Counter32
		MAX-ACCESS			 read-only
		STATUS					 current
		DESCRIPTION			 " -- "
		::=  { massiveMIMOEntry  40 }


	macNbrErrTbDlMassiveMimoSM7		 OBJECT-TYPE
		SYNTAX					 Counter32
		MAX-ACCESS			 read-only
		STATUS					 current
		DESCRIPTION			 " -- "
		::=  { massiveMIMOEntry  41 }


	macNbrErrTbDlMassiveMimoSM8		 OBJECT-TYPE
		SYNTAX					 Counter32
		MAX-ACCESS			 read-only
		STATUS					 current
		DESCRIPTION			 " -- "
		::=  { massiveMIMOEntry  42 }


	macNbrErrTbDlMassiveMimoSM9		 OBJECT-TYPE
		SYNTAX					 Counter32
		MAX-ACCESS			 read-only
		STATUS					 current
		DESCRIPTION			 " -- "
		::=  { massiveMIMOEntry  43 }


	macNbrErrTbDlMassiveMimoSM10		 OBJECT-TYPE
		SYNTAX					 Counter32
		MAX-ACCESS			 read-only
		STATUS					 current
		DESCRIPTION			 " -- "
		::=  { massiveMIMOEntry  44 }


	macNbrErrTbDlMassiveMimoSM11		 OBJECT-TYPE
		SYNTAX					 Counter32
		MAX-ACCESS			 read-only
		STATUS					 current
		DESCRIPTION			 " -- "
		::=  { massiveMIMOEntry  45 }


	macNbrErrTbDlMassiveMimoSM12		 OBJECT-TYPE
		SYNTAX					 Counter32
		MAX-ACCESS			 read-only
		STATUS					 current
		DESCRIPTION			 " -- "
		::=  { massiveMIMOEntry  46 }


	macNbrErrTbDlMassiveMimoSM13		 OBJECT-TYPE
		SYNTAX					 Counter32
		MAX-ACCESS			 read-only
		STATUS					 current
		DESCRIPTION			 " -- "
		::=  { massiveMIMOEntry  47 }


	macNbrErrTbDlMassiveMimoSM14		 OBJECT-TYPE
		SYNTAX					 Counter32
		MAX-ACCESS			 read-only
		STATUS					 current
		DESCRIPTION			 " -- "
		::=  { massiveMIMOEntry  48 }


	macNbrErrTbDlMassiveMimoSM15		 OBJECT-TYPE
		SYNTAX					 Counter32
		MAX-ACCESS			 read-only
		STATUS					 current
		DESCRIPTION			 " -- "
		::=  { massiveMIMOEntry  49 }


	macNbrErrTbDlMassiveMimoSM16		 OBJECT-TYPE
		SYNTAX					 Counter32
		MAX-ACCESS			 read-only
		STATUS					 current
		DESCRIPTION			 " -- "
		::=  { massiveMIMOEntry  50 }


	macNbrTbUlMassiveMimoSM1		 OBJECT-TYPE
		SYNTAX					 Counter32
		MAX-ACCESS			 read-only
		STATUS					 current
		DESCRIPTION			 " -- "
		::=  { massiveMIMOEntry  51 }


	macNbrTbUlMassiveMimoSM2		 OBJECT-TYPE
		SYNTAX					 Counter32
		MAX-ACCESS			 read-only
		STATUS					 current
		DESCRIPTION			 " -- "
		::=  { massiveMIMOEntry  52 }


	macNbrTbUlMassiveMimoSM3		 OBJECT-TYPE
		SYNTAX					 Counter32
		MAX-ACCESS			 read-only
		STATUS					 current
		DESCRIPTION			 " -- "
		::=  { massiveMIMOEntry  53 }


	macNbrTbUlMassiveMimoSM4		 OBJECT-TYPE
		SYNTAX					 Counter32
		MAX-ACCESS			 read-only
		STATUS					 current
		DESCRIPTION			 " -- "
		::=  { massiveMIMOEntry  54 }


	macNbrTbUlMassiveMimoSM5		 OBJECT-TYPE
		SYNTAX					 Counter32
		MAX-ACCESS			 read-only
		STATUS					 current
		DESCRIPTION			 " -- "
		::=  { massiveMIMOEntry  55 }


	macNbrTbUlMassiveMimoSM6		 OBJECT-TYPE
		SYNTAX					 Counter32
		MAX-ACCESS			 read-only
		STATUS					 current
		DESCRIPTION			 " -- "
		::=  { massiveMIMOEntry  56 }


	macNbrTbUlMassiveMimoSM7		 OBJECT-TYPE
		SYNTAX					 Counter32
		MAX-ACCESS			 read-only
		STATUS					 current
		DESCRIPTION			 " -- "
		::=  { massiveMIMOEntry  57 }


	macNbrTbUlMassiveMimoSM8		 OBJECT-TYPE
		SYNTAX					 Counter32
		MAX-ACCESS			 read-only
		STATUS					 current
		DESCRIPTION			 " -- "
		::=  { massiveMIMOEntry  58 }


	macNbrTbDlMassiveMimoSM1		 OBJECT-TYPE
		SYNTAX					 Counter32
		MAX-ACCESS			 read-only
		STATUS					 current
		DESCRIPTION			 " -- "
		::=  { massiveMIMOEntry  59 }


	macNbrTbDlMassiveMimoSM2		 OBJECT-TYPE
		SYNTAX					 Counter32
		MAX-ACCESS			 read-only
		STATUS					 current
		DESCRIPTION			 " -- "
		::=  { massiveMIMOEntry  60 }


	macNbrTbDlMassiveMimoSM3		 OBJECT-TYPE
		SYNTAX					 Counter32
		MAX-ACCESS			 read-only
		STATUS					 current
		DESCRIPTION			 " -- "
		::=  { massiveMIMOEntry  61 }


	macNbrTbDlMassiveMimoSM4		 OBJECT-TYPE
		SYNTAX					 Counter32
		MAX-ACCESS			 read-only
		STATUS					 current
		DESCRIPTION			 " -- "
		::=  { massiveMIMOEntry  62 }


	macNbrTbDlMassiveMimoSM5		 OBJECT-TYPE
		SYNTAX					 Counter32
		MAX-ACCESS			 read-only
		STATUS					 current
		DESCRIPTION			 " -- "
		::=  { massiveMIMOEntry  63 }


	macNbrTbDlMassiveMimoSM6		 OBJECT-TYPE
		SYNTAX					 Counter32
		MAX-ACCESS			 read-only
		STATUS					 current
		DESCRIPTION			 " -- "
		::=  { massiveMIMOEntry  64 }


	macNbrTbDlMassiveMimoSM7		 OBJECT-TYPE
		SYNTAX					 Counter32
		MAX-ACCESS			 read-only
		STATUS					 current
		DESCRIPTION			 " -- "
		::=  { massiveMIMOEntry  65 }


	macNbrTbDlMassiveMimoSM8		 OBJECT-TYPE
		SYNTAX					 Counter32
		MAX-ACCESS			 read-only
		STATUS					 current
		DESCRIPTION			 " -- "
		::=  { massiveMIMOEntry  66 }


	macNbrTbDlMassiveMimoSM9		 OBJECT-TYPE
		SYNTAX					 Counter32
		MAX-ACCESS			 read-only
		STATUS					 current
		DESCRIPTION			 " -- "
		::=  { massiveMIMOEntry  67 }


	macNbrTbDlMassiveMimoSM10		 OBJECT-TYPE
		SYNTAX					 Counter32
		MAX-ACCESS			 read-only
		STATUS					 current
		DESCRIPTION			 " -- "
		::=  { massiveMIMOEntry  68 }


	macNbrTbDlMassiveMimoSM11		 OBJECT-TYPE
		SYNTAX					 Counter32
		MAX-ACCESS			 read-only
		STATUS					 current
		DESCRIPTION			 " -- "
		::=  { massiveMIMOEntry  69 }


	macNbrTbDlMassiveMimoSM12		 OBJECT-TYPE
		SYNTAX					 Counter32
		MAX-ACCESS			 read-only
		STATUS					 current
		DESCRIPTION			 " -- "
		::=  { massiveMIMOEntry  70 }


	macNbrTbDlMassiveMimoSM13		 OBJECT-TYPE
		SYNTAX					 Counter32
		MAX-ACCESS			 read-only
		STATUS					 current
		DESCRIPTION			 " -- "
		::=  { massiveMIMOEntry  71 }


	macNbrTbDlMassiveMimoSM14		 OBJECT-TYPE
		SYNTAX					 Counter32
		MAX-ACCESS			 read-only
		STATUS					 current
		DESCRIPTION			 " -- "
		::=  { massiveMIMOEntry  72 }


	macNbrTbDlMassiveMimoSM15		 OBJECT-TYPE
		SYNTAX					 Counter32
		MAX-ACCESS			 read-only
		STATUS					 current
		DESCRIPTION			 " -- "
		::=  { massiveMIMOEntry  73 }


	macNbrTbDlMassiveMimoSM16		 OBJECT-TYPE
		SYNTAX					 Counter32
		MAX-ACCESS			 read-only
		STATUS					 current
		DESCRIPTION			 " -- "
		::=  { massiveMIMOEntry  74 }


	macOctUlMassiveMimoSM1		 OBJECT-TYPE
		SYNTAX					 Counter32
		MAX-ACCESS			 read-only
		STATUS					 current
		DESCRIPTION			 " -- "
		::=  { massiveMIMOEntry  75 }


	macOctUlMassiveMimoSM2		 OBJECT-TYPE
		SYNTAX					 Counter32
		MAX-ACCESS			 read-only
		STATUS					 current
		DESCRIPTION			 " -- "
		::=  { massiveMIMOEntry  76 }


	macOctUlMassiveMimoSM3		 OBJECT-TYPE
		SYNTAX					 Counter32
		MAX-ACCESS			 read-only
		STATUS					 current
		DESCRIPTION			 " -- "
		::=  { massiveMIMOEntry  77 }


	macOctUlMassiveMimoSM4		 OBJECT-TYPE
		SYNTAX					 Counter32
		MAX-ACCESS			 read-only
		STATUS					 current
		DESCRIPTION			 " -- "
		::=  { massiveMIMOEntry  78 }


	macOctUlMassiveMimoSM5		 OBJECT-TYPE
		SYNTAX					 Counter32
		MAX-ACCESS			 read-only
		STATUS					 current
		DESCRIPTION			 " -- "
		::=  { massiveMIMOEntry  79 }


	macOctUlMassiveMimoSM6		 OBJECT-TYPE
		SYNTAX					 Counter32
		MAX-ACCESS			 read-only
		STATUS					 current
		DESCRIPTION			 " -- "
		::=  { massiveMIMOEntry  80 }


	macOctUlMassiveMimoSM7		 OBJECT-TYPE
		SYNTAX					 Counter32
		MAX-ACCESS			 read-only
		STATUS					 current
		DESCRIPTION			 " -- "
		::=  { massiveMIMOEntry  81 }


	macOctUlMassiveMimoSM8		 OBJECT-TYPE
		SYNTAX					 Counter32
		MAX-ACCESS			 read-only
		STATUS					 current
		DESCRIPTION			 " -- "
		::=  { massiveMIMOEntry  82 }


	macOctDlMassiveMimoSM1		 OBJECT-TYPE
		SYNTAX					 Counter32
		MAX-ACCESS			 read-only
		STATUS					 current
		DESCRIPTION			 " -- "
		::=  { massiveMIMOEntry  83 }


	macOctDlMassiveMimoSM2		 OBJECT-TYPE
		SYNTAX					 Counter32
		MAX-ACCESS			 read-only
		STATUS					 current
		DESCRIPTION			 " -- "
		::=  { massiveMIMOEntry  84 }


	macOctDlMassiveMimoSM3		 OBJECT-TYPE
		SYNTAX					 Counter32
		MAX-ACCESS			 read-only
		STATUS					 current
		DESCRIPTION			 " -- "
		::=  { massiveMIMOEntry  85 }


	macOctDlMassiveMimoSM4		 OBJECT-TYPE
		SYNTAX					 Counter32
		MAX-ACCESS			 read-only
		STATUS					 current
		DESCRIPTION			 " -- "
		::=  { massiveMIMOEntry  86 }


	macOctDlMassiveMimoSM5		 OBJECT-TYPE
		SYNTAX					 Counter32
		MAX-ACCESS			 read-only
		STATUS					 current
		DESCRIPTION			 " -- "
		::=  { massiveMIMOEntry  87 }


	macOctDlMassiveMimoSM6		 OBJECT-TYPE
		SYNTAX					 Counter32
		MAX-ACCESS			 read-only
		STATUS					 current
		DESCRIPTION			 " -- "
		::=  { massiveMIMOEntry  88 }


	macOctDlMassiveMimoSM7		 OBJECT-TYPE
		SYNTAX					 Counter32
		MAX-ACCESS			 read-only
		STATUS					 current
		DESCRIPTION			 " -- "
		::=  { massiveMIMOEntry  89 }


	macOctDlMassiveMimoSM8		 OBJECT-TYPE
		SYNTAX					 Counter32
		MAX-ACCESS			 read-only
		STATUS					 current
		DESCRIPTION			 " -- "
		::=  { massiveMIMOEntry  90 }


	macOctDlMassiveMimoSM9		 OBJECT-TYPE
		SYNTAX					 Counter32
		MAX-ACCESS			 read-only
		STATUS					 current
		DESCRIPTION			 " -- "
		::=  { massiveMIMOEntry  91 }


	macOctDlMassiveMimoSM10		 OBJECT-TYPE
		SYNTAX					 Counter32
		MAX-ACCESS			 read-only
		STATUS					 current
		DESCRIPTION			 " -- "
		::=  { massiveMIMOEntry  92 }


	macOctDlMassiveMimoSM11		 OBJECT-TYPE
		SYNTAX					 Counter32
		MAX-ACCESS			 read-only
		STATUS					 current
		DESCRIPTION			 " -- "
		::=  { massiveMIMOEntry  93 }


	macOctDlMassiveMimoSM12		 OBJECT-TYPE
		SYNTAX					 Counter32
		MAX-ACCESS			 read-only
		STATUS					 current
		DESCRIPTION			 " -- "
		::=  { massiveMIMOEntry  94 }


	macOctDlMassiveMimoSM13		 OBJECT-TYPE
		SYNTAX					 Counter32
		MAX-ACCESS			 read-only
		STATUS					 current
		DESCRIPTION			 " -- "
		::=  { massiveMIMOEntry  95 }


	macOctDlMassiveMimoSM14		 OBJECT-TYPE
		SYNTAX					 Counter32
		MAX-ACCESS			 read-only
		STATUS					 current
		DESCRIPTION			 " -- "
		::=  { massiveMIMOEntry  96 }


	macOctDlMassiveMimoSM15		 OBJECT-TYPE
		SYNTAX					 Counter32
		MAX-ACCESS			 read-only
		STATUS					 current
		DESCRIPTION			 " -- "
		::=  { massiveMIMOEntry  97 }


	macOctDlMassiveMimoSM16		 OBJECT-TYPE
		SYNTAX					 Counter32
		MAX-ACCESS			 read-only
		STATUS					 current
		DESCRIPTION			 " -- "
		::=  { massiveMIMOEntry  98 }


	macDlMassiveMimoPair01		 OBJECT-TYPE
		SYNTAX					 Counter32
		MAX-ACCESS			 read-only
		STATUS					 current
		DESCRIPTION			 " -- "
		::=  { massiveMIMOEntry  99 }


	macDlMassiveMimoPair02		 OBJECT-TYPE
		SYNTAX					 Counter32
		MAX-ACCESS			 read-only
		STATUS					 current
		DESCRIPTION			 " -- "
		::=  { massiveMIMOEntry  100 }


	macDlMassiveMimoPair03		 OBJECT-TYPE
		SYNTAX					 Counter32
		MAX-ACCESS			 read-only
		STATUS					 current
		DESCRIPTION			 " -- "
		::=  { massiveMIMOEntry  101 }


	pdcprelatedOriginCounter		 OBJECT IDENTIFIER
		::=  { pmOriginCounterGrpInfo  4 }


	pdcpRatioSITable		 OBJECT-TYPE
		SYNTAX					 SEQUENCE  OF	 PdcpRatioSIEntry
		MAX-ACCESS			 not-accessible
		STATUS					 current
		DESCRIPTION			 " -- "
		::=  { pdcprelatedOriginCounter  1 }


	pdcpRatioSIEntry		 OBJECT-TYPE
		SYNTAX					 PdcpRatioSIEntry
		MAX-ACCESS			 not-accessible
		STATUS					 current
		DESCRIPTION			 " -- "
		INDEX						{ pdcpRatioSILcId }
		::=  { pdcpRatioSITable  1 }


	PdcpRatioSIEntry		 ::=  SEQUENCE {
		pdcpRatioSILcId					Integer32,
		pdcpRatioSIRowStatus					RowStatus,
		drbPdcpSduBitLenDlQci1					Counter32,
		drbPdcpSduBitLenDlQci2					Counter32,
		drbPdcpSduBitLenDlQci3					Counter32,
		drbPdcpSduBitLenDlQci4					Counter32,
		drbPdcpSduBitLenDlQci5					Counter32,
		drbPdcpSduBitLenDlQci6					Counter32,
		drbPdcpSduBitLenDlQci7					Counter32,
		drbPdcpSduBitLenDlQci8					Counter32,
		drbPdcpSduBitLenDlQci9					Counter32,
		drbPdcpSduBitLenUlQci1					Counter32,
		drbPdcpSduBitLenUlQci2					Counter32,
		drbPdcpSduBitLenUlQci3					Counter32,
		drbPdcpSduBitLenUlQci4					Counter32,
		drbPdcpSduBitLenUlQci5					Counter32,
		drbPdcpSduBitLenUlQci6					Counter32,
		drbPdcpSduBitLenUlQci7					Counter32,
		drbPdcpSduBitLenUlQci8					Counter32,
		drbPdcpSduBitLenUlQci9					Counter32,
		srbPdcpSduBitLenDl					Counter32,
		srbPdcpSduBitLenUl					Counter32,
		drbPdcpSduBitRatioDlMax					Counter32,
		drbPdcpSduBitRatioUlMax					Counter32,
		stasticperiod					Counter32
		}


	pdcpRatioSILcId		 OBJECT-TYPE
		SYNTAX					 Integer32( 0 .. 23 )
		MAX-ACCESS			 not-accessible
		STATUS					 current
		DESCRIPTION			 " -- "
		::=  { pdcpRatioSIEntry  1 }


	pdcpRatioSIRowStatus		 OBJECT-TYPE
		SYNTAX					 RowStatus
		MAX-ACCESS			 read-only
		STATUS					 current
		DESCRIPTION			 " -- "
		::=  { pdcpRatioSIEntry  2 }


	drbPdcpSduBitLenDlQci1		 OBJECT-TYPE
		SYNTAX					 Counter32
		MAX-ACCESS			 read-only
		STATUS					 current
		DESCRIPTION			 " -- "
		::=  { pdcpRatioSIEntry  3 }


	drbPdcpSduBitLenDlQci2		 OBJECT-TYPE
		SYNTAX					 Counter32
		MAX-ACCESS			 read-only
		STATUS					 current
		DESCRIPTION			 " -- "
		::=  { pdcpRatioSIEntry  4 }


	drbPdcpSduBitLenDlQci3		 OBJECT-TYPE
		SYNTAX					 Counter32
		MAX-ACCESS			 read-only
		STATUS					 current
		DESCRIPTION			 " -- "
		::=  { pdcpRatioSIEntry  5 }


	drbPdcpSduBitLenDlQci4		 OBJECT-TYPE
		SYNTAX					 Counter32
		MAX-ACCESS			 read-only
		STATUS					 current
		DESCRIPTION			 " -- "
		::=  { pdcpRatioSIEntry  6 }


	drbPdcpSduBitLenDlQci5		 OBJECT-TYPE
		SYNTAX					 Counter32
		MAX-ACCESS			 read-only
		STATUS					 current
		DESCRIPTION			 " -- "
		::=  { pdcpRatioSIEntry  7 }


	drbPdcpSduBitLenDlQci6		 OBJECT-TYPE
		SYNTAX					 Counter32
		MAX-ACCESS			 read-only
		STATUS					 current
		DESCRIPTION			 " -- "
		::=  { pdcpRatioSIEntry  8 }


	drbPdcpSduBitLenDlQci7		 OBJECT-TYPE
		SYNTAX					 Counter32
		MAX-ACCESS			 read-only
		STATUS					 current
		DESCRIPTION			 " -- "
		::=  { pdcpRatioSIEntry  9 }


	drbPdcpSduBitLenDlQci8		 OBJECT-TYPE
		SYNTAX					 Counter32
		MAX-ACCESS			 read-only
		STATUS					 current
		DESCRIPTION			 " -- "
		::=  { pdcpRatioSIEntry  10 }


	drbPdcpSduBitLenDlQci9		 OBJECT-TYPE
		SYNTAX					 Counter32
		MAX-ACCESS			 read-only
		STATUS					 current
		DESCRIPTION			 " -- "
		::=  { pdcpRatioSIEntry  11 }


	drbPdcpSduBitLenUlQci1		 OBJECT-TYPE
		SYNTAX					 Counter32
		MAX-ACCESS			 read-only
		STATUS					 current
		DESCRIPTION			 " -- "
		::=  { pdcpRatioSIEntry  12 }


	drbPdcpSduBitLenUlQci2		 OBJECT-TYPE
		SYNTAX					 Counter32
		MAX-ACCESS			 read-only
		STATUS					 current
		DESCRIPTION			 " -- "
		::=  { pdcpRatioSIEntry  13 }


	drbPdcpSduBitLenUlQci3		 OBJECT-TYPE
		SYNTAX					 Counter32
		MAX-ACCESS			 read-only
		STATUS					 current
		DESCRIPTION			 " -- "
		::=  { pdcpRatioSIEntry  14 }


	drbPdcpSduBitLenUlQci4		 OBJECT-TYPE
		SYNTAX					 Counter32
		MAX-ACCESS			 read-only
		STATUS					 current
		DESCRIPTION			 " -- "
		::=  { pdcpRatioSIEntry  15 }


	drbPdcpSduBitLenUlQci5		 OBJECT-TYPE
		SYNTAX					 Counter32
		MAX-ACCESS			 read-only
		STATUS					 current
		DESCRIPTION			 " -- "
		::=  { pdcpRatioSIEntry  16 }


	drbPdcpSduBitLenUlQci6		 OBJECT-TYPE
		SYNTAX					 Counter32
		MAX-ACCESS			 read-only
		STATUS					 current
		DESCRIPTION			 " -- "
		::=  { pdcpRatioSIEntry  17 }


	drbPdcpSduBitLenUlQci7		 OBJECT-TYPE
		SYNTAX					 Counter32
		MAX-ACCESS			 read-only
		STATUS					 current
		DESCRIPTION			 " -- "
		::=  { pdcpRatioSIEntry  18 }


	drbPdcpSduBitLenUlQci8		 OBJECT-TYPE
		SYNTAX					 Counter32
		MAX-ACCESS			 read-only
		STATUS					 current
		DESCRIPTION			 " -- "
		::=  { pdcpRatioSIEntry  19 }


	drbPdcpSduBitLenUlQci9		 OBJECT-TYPE
		SYNTAX					 Counter32
		MAX-ACCESS			 read-only
		STATUS					 current
		DESCRIPTION			 " -- "
		::=  { pdcpRatioSIEntry  20 }


	srbPdcpSduBitLenDl		 OBJECT-TYPE
		SYNTAX					 Counter32
		MAX-ACCESS			 read-only
		STATUS					 current
		DESCRIPTION			 " -- "
		::=  { pdcpRatioSIEntry  21 }


	srbPdcpSduBitLenUl		 OBJECT-TYPE
		SYNTAX					 Counter32
		MAX-ACCESS			 read-only
		STATUS					 current
		DESCRIPTION			 " -- "
		::=  { pdcpRatioSIEntry  22 }


	drbPdcpSduBitRatioDlMax		 OBJECT-TYPE
		SYNTAX					 Counter32
		MAX-ACCESS			 read-only
		STATUS					 current
		DESCRIPTION			 " -- "
		::=  { pdcpRatioSIEntry  23 }


	drbPdcpSduBitRatioUlMax		 OBJECT-TYPE
		SYNTAX					 Counter32
		MAX-ACCESS			 read-only
		STATUS					 current
		DESCRIPTION			 " -- "
		::=  { pdcpRatioSIEntry  24 }


	stasticperiod		 OBJECT-TYPE
		SYNTAX					 Counter32
		MAX-ACCESS			 read-only
		STATUS					 current
		DESCRIPTION			 " -- "
		::=  { pdcpRatioSIEntry  25 }


	pdcpDlPacketDelayTable		 OBJECT-TYPE
		SYNTAX					 SEQUENCE  OF	 PdcpDlPacketDelayEntry
		MAX-ACCESS			 not-accessible
		STATUS					 current
		DESCRIPTION			 " -- "
		::=  { pdcprelatedOriginCounter  2 }


	pdcpDlPacketDelayEntry		 OBJECT-TYPE
		SYNTAX					 PdcpDlPacketDelayEntry
		MAX-ACCESS			 not-accessible
		STATUS					 current
		DESCRIPTION			 " -- "
		INDEX						{ pdcpDlPacketDelayLcId }
		::=  { pdcpDlPacketDelayTable  1 }


	PdcpDlPacketDelayEntry		 ::=  SEQUENCE {
		pdcpDlPacketDelayLcId					Integer32,
		pdcpDlPacketDelayRowStatus					RowStatus,
		drbPdcpSduDelayDlQci1					Counter32,
		drbPdcpSduDelayDlQci2					Counter32,
		drbPdcpSduDelayDlQci3					Counter32,
		drbPdcpSduDelayDlQci4					Counter32,
		drbPdcpSduDelayDlQci5					Counter32,
		drbPdcpSduDelayDlQci6					Counter32,
		drbPdcpSduDelayDlQci7					Counter32,
		drbPdcpSduDelayDlQci8					Counter32,
		drbPdcpSduDelayDlQci9					Counter32,
		drbPdcpSduTotalDelayDlQci1					Counter32,
		drbPdcpSduTotalDelayDlQci2					Counter32,
		drbPdcpSduTotalDelayDlQci3					Counter32,
		drbPdcpSduTotalDelayDlQci4					Counter32,
		drbPdcpSduTotalDelayDlQci5					Counter32,
		drbPdcpSduTotalDelayDlQci6					Counter32,
		drbPdcpSduTotalDelayDlQci7					Counter32,
		drbPdcpSduTotalDelayDlQci8					Counter32,
		drbPdcpSduTotalDelayDlQci9					Counter32,
		drbPdcpSduTotalNumberDlQci1					Counter32,
		drbPdcpSduTotalNumberDlQci2					Counter32,
		drbPdcpSduTotalNumberDlQci3					Counter32,
		drbPdcpSduTotalNumberDlQci4					Counter32,
		drbPdcpSduTotalNumberDlQci5					Counter32,
		drbPdcpSduTotalNumberDlQci6					Counter32,
		drbPdcpSduTotalNumberDlQci7					Counter32,
		drbPdcpSduTotalNumberDlQci8					Counter32,
		drbPdcpSduTotalNumberDlQci9					Counter32,
		pdcpUpPktDelayDlEnb					Counter32,
		pdcpUpPktDelayDlQci1Enb					Counter32,
		pdcpUpPktDelayDlQci2Enb					Counter32,
		pdcpUpPktDelayDlQci3Enb					Counter32,
		pdcpUpPktDelayDlQci4Enb					Counter32,
		pdcpUpPktDelayDlQci5Enb					Counter32,
		pdcpUpPktDelayDlQci6Enb					Counter32,
		pdcpUpPktDelayDlQci7Enb					Counter32,
		pdcpUpPktDelayDlQci8Enb					Counter32,
		pdcpUpPktDelayDlQci9Enb					Counter32
		}


	pdcpDlPacketDelayLcId		 OBJECT-TYPE
		SYNTAX					 Integer32( 0 .. 23 )
		MAX-ACCESS			 not-accessible
		STATUS					 current
		DESCRIPTION			 " -- "
		::=  { pdcpDlPacketDelayEntry  1 }


	pdcpDlPacketDelayRowStatus		 OBJECT-TYPE
		SYNTAX					 RowStatus
		MAX-ACCESS			 read-only
		STATUS					 current
		DESCRIPTION			 " -- "
		::=  { pdcpDlPacketDelayEntry  2 }


	drbPdcpSduDelayDlQci1		 OBJECT-TYPE
		SYNTAX					 Counter32
		MAX-ACCESS			 read-only
		STATUS					 current
		DESCRIPTION			 " -- "
		::=  { pdcpDlPacketDelayEntry  3 }


	drbPdcpSduDelayDlQci2		 OBJECT-TYPE
		SYNTAX					 Counter32
		MAX-ACCESS			 read-only
		STATUS					 current
		DESCRIPTION			 " -- "
		::=  { pdcpDlPacketDelayEntry  4 }


	drbPdcpSduDelayDlQci3		 OBJECT-TYPE
		SYNTAX					 Counter32
		MAX-ACCESS			 read-only
		STATUS					 current
		DESCRIPTION			 " -- "
		::=  { pdcpDlPacketDelayEntry  5 }


	drbPdcpSduDelayDlQci4		 OBJECT-TYPE
		SYNTAX					 Counter32
		MAX-ACCESS			 read-only
		STATUS					 current
		DESCRIPTION			 " -- "
		::=  { pdcpDlPacketDelayEntry  6 }


	drbPdcpSduDelayDlQci5		 OBJECT-TYPE
		SYNTAX					 Counter32
		MAX-ACCESS			 read-only
		STATUS					 current
		DESCRIPTION			 " -- "
		::=  { pdcpDlPacketDelayEntry  7 }


	drbPdcpSduDelayDlQci6		 OBJECT-TYPE
		SYNTAX					 Counter32
		MAX-ACCESS			 read-only
		STATUS					 current
		DESCRIPTION			 " -- "
		::=  { pdcpDlPacketDelayEntry  8 }


	drbPdcpSduDelayDlQci7		 OBJECT-TYPE
		SYNTAX					 Counter32
		MAX-ACCESS			 read-only
		STATUS					 current
		DESCRIPTION			 " -- "
		::=  { pdcpDlPacketDelayEntry  9 }


	drbPdcpSduDelayDlQci8		 OBJECT-TYPE
		SYNTAX					 Counter32
		MAX-ACCESS			 read-only
		STATUS					 current
		DESCRIPTION			 " -- "
		::=  { pdcpDlPacketDelayEntry  10 }


	drbPdcpSduDelayDlQci9		 OBJECT-TYPE
		SYNTAX					 Counter32
		MAX-ACCESS			 read-only
		STATUS					 current
		DESCRIPTION			 " -- "
		::=  { pdcpDlPacketDelayEntry  11 }


	drbPdcpSduTotalDelayDlQci1		 OBJECT-TYPE
		SYNTAX					 Counter32
		MAX-ACCESS			 read-only
		STATUS					 current
		DESCRIPTION			 " -- "
		::=  { pdcpDlPacketDelayEntry  12 }


	drbPdcpSduTotalDelayDlQci2		 OBJECT-TYPE
		SYNTAX					 Counter32
		MAX-ACCESS			 read-only
		STATUS					 current
		DESCRIPTION			 " -- "
		::=  { pdcpDlPacketDelayEntry  13 }


	drbPdcpSduTotalDelayDlQci3		 OBJECT-TYPE
		SYNTAX					 Counter32
		MAX-ACCESS			 read-only
		STATUS					 current
		DESCRIPTION			 " -- "
		::=  { pdcpDlPacketDelayEntry  14 }


	drbPdcpSduTotalDelayDlQci4		 OBJECT-TYPE
		SYNTAX					 Counter32
		MAX-ACCESS			 read-only
		STATUS					 current
		DESCRIPTION			 " -- "
		::=  { pdcpDlPacketDelayEntry  15 }


	drbPdcpSduTotalDelayDlQci5		 OBJECT-TYPE
		SYNTAX					 Counter32
		MAX-ACCESS			 read-only
		STATUS					 current
		DESCRIPTION			 " -- "
		::=  { pdcpDlPacketDelayEntry  16 }


	drbPdcpSduTotalDelayDlQci6		 OBJECT-TYPE
		SYNTAX					 Counter32
		MAX-ACCESS			 read-only
		STATUS					 current
		DESCRIPTION			 " -- "
		::=  { pdcpDlPacketDelayEntry  17 }


	drbPdcpSduTotalDelayDlQci7		 OBJECT-TYPE
		SYNTAX					 Counter32
		MAX-ACCESS			 read-only
		STATUS					 current
		DESCRIPTION			 " -- "
		::=  { pdcpDlPacketDelayEntry  18 }


	drbPdcpSduTotalDelayDlQci8		 OBJECT-TYPE
		SYNTAX					 Counter32
		MAX-ACCESS			 read-only
		STATUS					 current
		DESCRIPTION			 " -- "
		::=  { pdcpDlPacketDelayEntry  19 }


	drbPdcpSduTotalDelayDlQci9		 OBJECT-TYPE
		SYNTAX					 Counter32
		MAX-ACCESS			 read-only
		STATUS					 current
		DESCRIPTION			 " -- "
		::=  { pdcpDlPacketDelayEntry  20 }


	drbPdcpSduTotalNumberDlQci1		 OBJECT-TYPE
		SYNTAX					 Counter32
		MAX-ACCESS			 read-only
		STATUS					 current
		DESCRIPTION			 " -- "
		::=  { pdcpDlPacketDelayEntry  21 }


	drbPdcpSduTotalNumberDlQci2		 OBJECT-TYPE
		SYNTAX					 Counter32
		MAX-ACCESS			 read-only
		STATUS					 current
		DESCRIPTION			 " -- "
		::=  { pdcpDlPacketDelayEntry  22 }


	drbPdcpSduTotalNumberDlQci3		 OBJECT-TYPE
		SYNTAX					 Counter32
		MAX-ACCESS			 read-only
		STATUS					 current
		DESCRIPTION			 " -- "
		::=  { pdcpDlPacketDelayEntry  23 }


	drbPdcpSduTotalNumberDlQci4		 OBJECT-TYPE
		SYNTAX					 Counter32
		MAX-ACCESS			 read-only
		STATUS					 current
		DESCRIPTION			 " -- "
		::=  { pdcpDlPacketDelayEntry  24 }


	drbPdcpSduTotalNumberDlQci5		 OBJECT-TYPE
		SYNTAX					 Counter32
		MAX-ACCESS			 read-only
		STATUS					 current
		DESCRIPTION			 " -- "
		::=  { pdcpDlPacketDelayEntry  25 }


	drbPdcpSduTotalNumberDlQci6		 OBJECT-TYPE
		SYNTAX					 Counter32
		MAX-ACCESS			 read-only
		STATUS					 current
		DESCRIPTION			 " -- "
		::=  { pdcpDlPacketDelayEntry  26 }


	drbPdcpSduTotalNumberDlQci7		 OBJECT-TYPE
		SYNTAX					 Counter32
		MAX-ACCESS			 read-only
		STATUS					 current
		DESCRIPTION			 " -- "
		::=  { pdcpDlPacketDelayEntry  27 }


	drbPdcpSduTotalNumberDlQci8		 OBJECT-TYPE
		SYNTAX					 Counter32
		MAX-ACCESS			 read-only
		STATUS					 current
		DESCRIPTION			 " -- "
		::=  { pdcpDlPacketDelayEntry  28 }


	drbPdcpSduTotalNumberDlQci9		 OBJECT-TYPE
		SYNTAX					 Counter32
		MAX-ACCESS			 read-only
		STATUS					 current
		DESCRIPTION			 " -- "
		::=  { pdcpDlPacketDelayEntry  29 }


	pdcpUpPktDelayDlEnb		 OBJECT-TYPE
		SYNTAX					 Counter32
		MAX-ACCESS			 read-only
		STATUS					 current
		DESCRIPTION			 " -- "
		::=  { pdcpDlPacketDelayEntry  200 }


	pdcpUpPktDelayDlQci1Enb		 OBJECT-TYPE
		SYNTAX					 Counter32
		MAX-ACCESS			 read-only
		STATUS					 current
		DESCRIPTION			 " -- "
		::=  { pdcpDlPacketDelayEntry  201 }


	pdcpUpPktDelayDlQci2Enb		 OBJECT-TYPE
		SYNTAX					 Counter32
		MAX-ACCESS			 read-only
		STATUS					 current
		DESCRIPTION			 " -- "
		::=  { pdcpDlPacketDelayEntry  202 }


	pdcpUpPktDelayDlQci3Enb		 OBJECT-TYPE
		SYNTAX					 Counter32
		MAX-ACCESS			 read-only
		STATUS					 current
		DESCRIPTION			 " -- "
		::=  { pdcpDlPacketDelayEntry  203 }


	pdcpUpPktDelayDlQci4Enb		 OBJECT-TYPE
		SYNTAX					 Counter32
		MAX-ACCESS			 read-only
		STATUS					 current
		DESCRIPTION			 " -- "
		::=  { pdcpDlPacketDelayEntry  204 }


	pdcpUpPktDelayDlQci5Enb		 OBJECT-TYPE
		SYNTAX					 Counter32
		MAX-ACCESS			 read-only
		STATUS					 current
		DESCRIPTION			 " -- "
		::=  { pdcpDlPacketDelayEntry  205 }


	pdcpUpPktDelayDlQci6Enb		 OBJECT-TYPE
		SYNTAX					 Counter32
		MAX-ACCESS			 read-only
		STATUS					 current
		DESCRIPTION			 " -- "
		::=  { pdcpDlPacketDelayEntry  206 }


	pdcpUpPktDelayDlQci7Enb		 OBJECT-TYPE
		SYNTAX					 Counter32
		MAX-ACCESS			 read-only
		STATUS					 current
		DESCRIPTION			 " -- "
		::=  { pdcpDlPacketDelayEntry  207 }


	pdcpUpPktDelayDlQci8Enb		 OBJECT-TYPE
		SYNTAX					 Counter32
		MAX-ACCESS			 read-only
		STATUS					 current
		DESCRIPTION			 " -- "
		::=  { pdcpDlPacketDelayEntry  208 }


	pdcpUpPktDelayDlQci9Enb		 OBJECT-TYPE
		SYNTAX					 Counter32
		MAX-ACCESS			 read-only
		STATUS					 current
		DESCRIPTION			 " -- "
		::=  { pdcpDlPacketDelayEntry  209 }


	pdcpSduDlDropRatioTable		 OBJECT-TYPE
		SYNTAX					 SEQUENCE  OF	 PdcpSduDlDropRatioEntry
		MAX-ACCESS			 not-accessible
		STATUS					 current
		DESCRIPTION			 " -- "
		::=  { pdcprelatedOriginCounter  3 }


	pdcpSduDlDropRatioEntry		 OBJECT-TYPE
		SYNTAX					 PdcpSduDlDropRatioEntry
		MAX-ACCESS			 not-accessible
		STATUS					 current
		DESCRIPTION			 " -- "
		INDEX						{ pdcpSduDlDropRatioLcId }
		::=  { pdcpSduDlDropRatioTable  1 }


	PdcpSduDlDropRatioEntry		 ::=  SEQUENCE {
		pdcpSduDlDropRatioLcId					Integer32,
		pdcpSduDlDropRatioRowStatus					RowStatus,
		pdcpSduSendTotalDateLenQci1					Counter32,
		pdcpSduSendTotalDateLenQci2					Counter32,
		pdcpSduSendTotalDateLenQci3					Counter32,
		pdcpSduSendTotalDateLenQci4					Counter32,
		pdcpSduSendTotalDateLenQci5					Counter32,
		pdcpSduSendTotalDateLenQci6					Counter32,
		pdcpSduSendTotalDateLenQci7					Counter32,
		pdcpSduSendTotalDateLenQci8					Counter32,
		pdcpSduSendTotalDateLenQci9					Counter32,
		pdcpSduDropTotalDateLenQci1					Counter32,
		pdcpSduDropTotalDateLenQci2					Counter32,
		pdcpSduDropTotalDateLenQci3					Counter32,
		pdcpSduDropTotalDateLenQci4					Counter32,
		pdcpSduDropTotalDateLenQci5					Counter32,
		pdcpSduDropTotalDateLenQci6					Counter32,
		pdcpSduDropTotalDateLenQci7					Counter32,
		pdcpSduDropTotalDateLenQci8					Counter32,
		pdcpSduDropTotalDateLenQci9					Counter32
		}


	pdcpSduDlDropRatioLcId		 OBJECT-TYPE
		SYNTAX					 Integer32( 0 .. 23 )
		MAX-ACCESS			 not-accessible
		STATUS					 current
		DESCRIPTION			 " -- "
		::=  { pdcpSduDlDropRatioEntry  1 }


	pdcpSduDlDropRatioRowStatus		 OBJECT-TYPE
		SYNTAX					 RowStatus
		MAX-ACCESS			 read-only
		STATUS					 current
		DESCRIPTION			 " -- "
		::=  { pdcpSduDlDropRatioEntry  2 }


	pdcpSduSendTotalDateLenQci1		 OBJECT-TYPE
		SYNTAX					 Counter32
		MAX-ACCESS			 read-only
		STATUS					 current
		DESCRIPTION			 " -- "
		::=  { pdcpSduDlDropRatioEntry  3 }


	pdcpSduSendTotalDateLenQci2		 OBJECT-TYPE
		SYNTAX					 Counter32
		MAX-ACCESS			 read-only
		STATUS					 current
		DESCRIPTION			 " -- "
		::=  { pdcpSduDlDropRatioEntry  4 }


	pdcpSduSendTotalDateLenQci3		 OBJECT-TYPE
		SYNTAX					 Counter32
		MAX-ACCESS			 read-only
		STATUS					 current
		DESCRIPTION			 " -- "
		::=  { pdcpSduDlDropRatioEntry  5 }


	pdcpSduSendTotalDateLenQci4		 OBJECT-TYPE
		SYNTAX					 Counter32
		MAX-ACCESS			 read-only
		STATUS					 current
		DESCRIPTION			 " -- "
		::=  { pdcpSduDlDropRatioEntry  6 }


	pdcpSduSendTotalDateLenQci5		 OBJECT-TYPE
		SYNTAX					 Counter32
		MAX-ACCESS			 read-only
		STATUS					 current
		DESCRIPTION			 " -- "
		::=  { pdcpSduDlDropRatioEntry  7 }


	pdcpSduSendTotalDateLenQci6		 OBJECT-TYPE
		SYNTAX					 Counter32
		MAX-ACCESS			 read-only
		STATUS					 current
		DESCRIPTION			 " -- "
		::=  { pdcpSduDlDropRatioEntry  8 }


	pdcpSduSendTotalDateLenQci7		 OBJECT-TYPE
		SYNTAX					 Counter32
		MAX-ACCESS			 read-only
		STATUS					 current
		DESCRIPTION			 " -- "
		::=  { pdcpSduDlDropRatioEntry  9 }


	pdcpSduSendTotalDateLenQci8		 OBJECT-TYPE
		SYNTAX					 Counter32
		MAX-ACCESS			 read-only
		STATUS					 current
		DESCRIPTION			 " -- "
		::=  { pdcpSduDlDropRatioEntry  10 }


	pdcpSduSendTotalDateLenQci9		 OBJECT-TYPE
		SYNTAX					 Counter32
		MAX-ACCESS			 read-only
		STATUS					 current
		DESCRIPTION			 " -- "
		::=  { pdcpSduDlDropRatioEntry  11 }


	pdcpSduDropTotalDateLenQci1		 OBJECT-TYPE
		SYNTAX					 Counter32
		MAX-ACCESS			 read-only
		STATUS					 current
		DESCRIPTION			 " -- "
		::=  { pdcpSduDlDropRatioEntry  12 }


	pdcpSduDropTotalDateLenQci2		 OBJECT-TYPE
		SYNTAX					 Counter32
		MAX-ACCESS			 read-only
		STATUS					 current
		DESCRIPTION			 " -- "
		::=  { pdcpSduDlDropRatioEntry  13 }


	pdcpSduDropTotalDateLenQci3		 OBJECT-TYPE
		SYNTAX					 Counter32
		MAX-ACCESS			 read-only
		STATUS					 current
		DESCRIPTION			 " -- "
		::=  { pdcpSduDlDropRatioEntry  14 }


	pdcpSduDropTotalDateLenQci4		 OBJECT-TYPE
		SYNTAX					 Counter32
		MAX-ACCESS			 read-only
		STATUS					 current
		DESCRIPTION			 " -- "
		::=  { pdcpSduDlDropRatioEntry  15 }


	pdcpSduDropTotalDateLenQci5		 OBJECT-TYPE
		SYNTAX					 Counter32
		MAX-ACCESS			 read-only
		STATUS					 current
		DESCRIPTION			 " -- "
		::=  { pdcpSduDlDropRatioEntry  16 }


	pdcpSduDropTotalDateLenQci6		 OBJECT-TYPE
		SYNTAX					 Counter32
		MAX-ACCESS			 read-only
		STATUS					 current
		DESCRIPTION			 " -- "
		::=  { pdcpSduDlDropRatioEntry  17 }


	pdcpSduDropTotalDateLenQci7		 OBJECT-TYPE
		SYNTAX					 Counter32
		MAX-ACCESS			 read-only
		STATUS					 current
		DESCRIPTION			 " -- "
		::=  { pdcpSduDlDropRatioEntry  18 }


	pdcpSduDropTotalDateLenQci8		 OBJECT-TYPE
		SYNTAX					 Counter32
		MAX-ACCESS			 read-only
		STATUS					 current
		DESCRIPTION			 " -- "
		::=  { pdcpSduDlDropRatioEntry  19 }


	pdcpSduDropTotalDateLenQci9		 OBJECT-TYPE
		SYNTAX					 Counter32
		MAX-ACCESS			 read-only
		STATUS					 current
		DESCRIPTION			 " -- "
		::=  { pdcpSduDlDropRatioEntry  20 }


	pdcpUlSduAirDropRatioTable		 OBJECT-TYPE
		SYNTAX					 SEQUENCE  OF	 PdcpUlSduAirDropRatioEntry
		MAX-ACCESS			 not-accessible
		STATUS					 current
		DESCRIPTION			 " -- "
		::=  { pdcprelatedOriginCounter  4 }


	pdcpUlSduAirDropRatioEntry		 OBJECT-TYPE
		SYNTAX					 PdcpUlSduAirDropRatioEntry
		MAX-ACCESS			 not-accessible
		STATUS					 current
		DESCRIPTION			 " -- "
		INDEX						{ pdcpUlSduAirDropRatioLcId }
		::=  { pdcpUlSduAirDropRatioTable  1 }


	PdcpUlSduAirDropRatioEntry		 ::=  SEQUENCE {
		pdcpUlSduAirDropRatioLcId					Integer32,
		pdcpUlSduAirDropRatioRowStatus					RowStatus,
		pdcpUlAirSduSendTotalNumberQci1					Counter32,
		pdcpUlAirSduSendTotalNumberQci2					Counter32,
		pdcpUlAirSduSendTotalNumberQci3					Counter32,
		pdcpUlAirSduSendTotalNumberQci4					Counter32,
		pdcpUlAirSduSendTotalNumberQci5					Counter32,
		pdcpUlAirSduSendTotalNumberQci6					Counter32,
		pdcpUlAirSduSendTotalNumberQci7					Counter32,
		pdcpUlAirSduSendTotalNumberQci8					Counter32,
		pdcpUlAirSduSendTotalNumberQci9					Counter32,
		pdcpUlAirSduDropTotalNumberQci1					Counter32,
		pdcpUlAirSduDropTotalNumberQci2					Counter32,
		pdcpUlAirSduDropTotalNumberQci3					Counter32,
		pdcpUlAirSduDropTotalNumberQci4					Counter32,
		pdcpUlAirSduDropTotalNumberQci5					Counter32,
		pdcpUlAirSduDropTotalNumberQci6					Counter32,
		pdcpUlAirSduDropTotalNumberQci7					Counter32,
		pdcpUlAirSduDropTotalNumberQci8					Counter32,
		pdcpUlAirSduDropTotalNumberQci9					Counter32,
		pdcpUpPktLossRateUlEnb					Counter32,
		pdcpUpPktLossRateUlQci1Enb					Counter32,
		pdcpUpPktLossRateUlQci2Enb					Counter32,
		pdcpUpPktLossRateUlQci3Enb					Counter32,
		pdcpUpPktLossRateUlQci4Enb					Counter32,
		pdcpUpPktLossRateUlQci5Enb					Counter32,
		pdcpUpPktLossRateUlQci6Enb					Counter32,
		pdcpUpPktLossRateUlQci7Enb					Counter32,
		pdcpUpPktLossRateUlQci8Enb					Counter32,
		pdcpUpPktLossRateUlQci9Enb					Counter32
		}


	pdcpUlSduAirDropRatioLcId		 OBJECT-TYPE
		SYNTAX					 Integer32( 0 .. 23 )
		MAX-ACCESS			 not-accessible
		STATUS					 current
		DESCRIPTION			 " -- "
		::=  { pdcpUlSduAirDropRatioEntry  1 }


	pdcpUlSduAirDropRatioRowStatus		 OBJECT-TYPE
		SYNTAX					 RowStatus
		MAX-ACCESS			 read-only
		STATUS					 current
		DESCRIPTION			 " -- "
		::=  { pdcpUlSduAirDropRatioEntry  2 }


	pdcpUlAirSduSendTotalNumberQci1		 OBJECT-TYPE
		SYNTAX					 Counter32
		MAX-ACCESS			 read-only
		STATUS					 current
		DESCRIPTION			 " -- "
		::=  { pdcpUlSduAirDropRatioEntry  3 }


	pdcpUlAirSduSendTotalNumberQci2		 OBJECT-TYPE
		SYNTAX					 Counter32
		MAX-ACCESS			 read-only
		STATUS					 current
		DESCRIPTION			 " -- "
		::=  { pdcpUlSduAirDropRatioEntry  4 }


	pdcpUlAirSduSendTotalNumberQci3		 OBJECT-TYPE
		SYNTAX					 Counter32
		MAX-ACCESS			 read-only
		STATUS					 current
		DESCRIPTION			 " -- "
		::=  { pdcpUlSduAirDropRatioEntry  5 }


	pdcpUlAirSduSendTotalNumberQci4		 OBJECT-TYPE
		SYNTAX					 Counter32
		MAX-ACCESS			 read-only
		STATUS					 current
		DESCRIPTION			 " -- "
		::=  { pdcpUlSduAirDropRatioEntry  6 }


	pdcpUlAirSduSendTotalNumberQci5		 OBJECT-TYPE
		SYNTAX					 Counter32
		MAX-ACCESS			 read-only
		STATUS					 current
		DESCRIPTION			 " -- "
		::=  { pdcpUlSduAirDropRatioEntry  7 }


	pdcpUlAirSduSendTotalNumberQci6		 OBJECT-TYPE
		SYNTAX					 Counter32
		MAX-ACCESS			 read-only
		STATUS					 current
		DESCRIPTION			 " -- "
		::=  { pdcpUlSduAirDropRatioEntry  8 }


	pdcpUlAirSduSendTotalNumberQci7		 OBJECT-TYPE
		SYNTAX					 Counter32
		MAX-ACCESS			 read-only
		STATUS					 current
		DESCRIPTION			 " -- "
		::=  { pdcpUlSduAirDropRatioEntry  9 }


	pdcpUlAirSduSendTotalNumberQci8		 OBJECT-TYPE
		SYNTAX					 Counter32
		MAX-ACCESS			 read-only
		STATUS					 current
		DESCRIPTION			 " -- "
		::=  { pdcpUlSduAirDropRatioEntry  10 }


	pdcpUlAirSduSendTotalNumberQci9		 OBJECT-TYPE
		SYNTAX					 Counter32
		MAX-ACCESS			 read-only
		STATUS					 current
		DESCRIPTION			 " -- "
		::=  { pdcpUlSduAirDropRatioEntry  11 }


	pdcpUlAirSduDropTotalNumberQci1		 OBJECT-TYPE
		SYNTAX					 Counter32
		MAX-ACCESS			 read-only
		STATUS					 current
		DESCRIPTION			 " -- "
		::=  { pdcpUlSduAirDropRatioEntry  12 }


	pdcpUlAirSduDropTotalNumberQci2		 OBJECT-TYPE
		SYNTAX					 Counter32
		MAX-ACCESS			 read-only
		STATUS					 current
		DESCRIPTION			 " -- "
		::=  { pdcpUlSduAirDropRatioEntry  13 }


	pdcpUlAirSduDropTotalNumberQci3		 OBJECT-TYPE
		SYNTAX					 Counter32
		MAX-ACCESS			 read-only
		STATUS					 current
		DESCRIPTION			 " -- "
		::=  { pdcpUlSduAirDropRatioEntry  14 }


	pdcpUlAirSduDropTotalNumberQci4		 OBJECT-TYPE
		SYNTAX					 Counter32
		MAX-ACCESS			 read-only
		STATUS					 current
		DESCRIPTION			 " -- "
		::=  { pdcpUlSduAirDropRatioEntry  15 }


	pdcpUlAirSduDropTotalNumberQci5		 OBJECT-TYPE
		SYNTAX					 Counter32
		MAX-ACCESS			 read-only
		STATUS					 current
		DESCRIPTION			 " -- "
		::=  { pdcpUlSduAirDropRatioEntry  16 }


	pdcpUlAirSduDropTotalNumberQci6		 OBJECT-TYPE
		SYNTAX					 Counter32
		MAX-ACCESS			 read-only
		STATUS					 current
		DESCRIPTION			 " -- "
		::=  { pdcpUlSduAirDropRatioEntry  17 }


	pdcpUlAirSduDropTotalNumberQci7		 OBJECT-TYPE
		SYNTAX					 Counter32
		MAX-ACCESS			 read-only
		STATUS					 current
		DESCRIPTION			 " -- "
		::=  { pdcpUlSduAirDropRatioEntry  18 }


	pdcpUlAirSduDropTotalNumberQci8		 OBJECT-TYPE
		SYNTAX					 Counter32
		MAX-ACCESS			 read-only
		STATUS					 current
		DESCRIPTION			 " -- "
		::=  { pdcpUlSduAirDropRatioEntry  19 }


	pdcpUlAirSduDropTotalNumberQci9		 OBJECT-TYPE
		SYNTAX					 Counter32
		MAX-ACCESS			 read-only
		STATUS					 current
		DESCRIPTION			 " -- "
		::=  { pdcpUlSduAirDropRatioEntry  20 }


	pdcpUpPktLossRateUlEnb		 OBJECT-TYPE
		SYNTAX					 Counter32
		MAX-ACCESS			 read-only
		STATUS					 current
		DESCRIPTION			 " -- "
		::=  { pdcpUlSduAirDropRatioEntry  200 }


	pdcpUpPktLossRateUlQci1Enb		 OBJECT-TYPE
		SYNTAX					 Counter32
		MAX-ACCESS			 read-only
		STATUS					 current
		DESCRIPTION			 " -- "
		::=  { pdcpUlSduAirDropRatioEntry  201 }


	pdcpUpPktLossRateUlQci2Enb		 OBJECT-TYPE
		SYNTAX					 Counter32
		MAX-ACCESS			 read-only
		STATUS					 current
		DESCRIPTION			 " -- "
		::=  { pdcpUlSduAirDropRatioEntry  202 }


	pdcpUpPktLossRateUlQci3Enb		 OBJECT-TYPE
		SYNTAX					 Counter32
		MAX-ACCESS			 read-only
		STATUS					 current
		DESCRIPTION			 " -- "
		::=  { pdcpUlSduAirDropRatioEntry  203 }


	pdcpUpPktLossRateUlQci4Enb		 OBJECT-TYPE
		SYNTAX					 Counter32
		MAX-ACCESS			 read-only
		STATUS					 current
		DESCRIPTION			 " -- "
		::=  { pdcpUlSduAirDropRatioEntry  204 }


	pdcpUpPktLossRateUlQci5Enb		 OBJECT-TYPE
		SYNTAX					 Counter32
		MAX-ACCESS			 read-only
		STATUS					 current
		DESCRIPTION			 " -- "
		::=  { pdcpUlSduAirDropRatioEntry  205 }


	pdcpUpPktLossRateUlQci6Enb		 OBJECT-TYPE
		SYNTAX					 Counter32
		MAX-ACCESS			 read-only
		STATUS					 current
		DESCRIPTION			 " -- "
		::=  { pdcpUlSduAirDropRatioEntry  206 }


	pdcpUpPktLossRateUlQci7Enb		 OBJECT-TYPE
		SYNTAX					 Counter32
		MAX-ACCESS			 read-only
		STATUS					 current
		DESCRIPTION			 " -- "
		::=  { pdcpUlSduAirDropRatioEntry  207 }


	pdcpUpPktLossRateUlQci8Enb		 OBJECT-TYPE
		SYNTAX					 Counter32
		MAX-ACCESS			 read-only
		STATUS					 current
		DESCRIPTION			 " -- "
		::=  { pdcpUlSduAirDropRatioEntry  208 }


	pdcpUpPktLossRateUlQci9Enb		 OBJECT-TYPE
		SYNTAX					 Counter32
		MAX-ACCESS			 read-only
		STATUS					 current
		DESCRIPTION			 " -- "
		::=  { pdcpUlSduAirDropRatioEntry  209 }


	voicePakStatisticTable		 OBJECT-TYPE
		SYNTAX					 SEQUENCE  OF	 VoicePakStatisticEntry
		MAX-ACCESS			 not-accessible
		STATUS					 current
		DESCRIPTION			 " -- "
		::=  { pdcprelatedOriginCounter  5 }


	voicePakStatisticEntry		 OBJECT-TYPE
		SYNTAX					 VoicePakStatisticEntry
		MAX-ACCESS			 not-accessible
		STATUS					 current
		DESCRIPTION			 " -- "
		INDEX						{ voicePakStatisticLcId }
		::=  { voicePakStatisticTable  1 }


	VoicePakStatisticEntry		 ::=  SEQUENCE {
		voicePakStatisticLcId					Integer32,
		voicePakStatisticRowStatus					RowStatus,
		voipRtpPacketUl					Counter32,
		voipRtpPacketDl					Counter32,
		voipRtpPacketLosUl					Counter32,
		voipRtpPacketLosDl					Counter32,
		voipSilenceCallUl					Counter32,
		voipSilenceCallDl					Counter32,
		voipRohcDecompFailUl					Counter32,
		amrUlVoipPacketWb0					Counter32,
		amrUlVoipPacketWb1					Counter32,
		amrUlVoipPacketWb2					Counter32,
		amrUlVoipPacketWb3					Counter32,
		amrUlVoipPacketWb4					Counter32,
		amrUlVoipPacketWb5					Counter32,
		amrUlVoipPacketWb6					Counter32,
		amrUlVoipPacketWb7					Counter32,
		amrUlVoipPacketWb8					Counter32,
		amrUlVoipPacketWb9					Counter32,
		amrUlVoipPacketNb0					Counter32,
		amrUlVoipPacketNb1					Counter32,
		amrUlVoipPacketNb2					Counter32,
		amrUlVoipPacketNb3					Counter32,
		amrUlVoipPacketNb4					Counter32,
		amrUlVoipPacketNb5					Counter32,
		amrUlVoipPacketNb6					Counter32,
		amrUlVoipPacketNb7					Counter32,
		amrUlVoipPacketNb8					Counter32,
		amrDlVoipPacketWb0					Counter32,
		amrDlVoipPacketWb1					Counter32,
		amrDlVoipPacketWb2					Counter32,
		amrDlVoipPacketWb3					Counter32,
		amrDlVoipPacketWb4					Counter32,
		amrDlVoipPacketWb5					Counter32,
		amrDlVoipPacketWb6					Counter32,
		amrDlVoipPacketWb7					Counter32,
		amrDlVoipPacketWb8					Counter32,
		amrDlVoipPacketWb9					Counter32,
		amrDlVoipPacketNb0					Counter32,
		amrDlVoipPacketNb1					Counter32,
		amrDlVoipPacketNb2					Counter32,
		amrDlVoipPacketNb3					Counter32,
		amrDlVoipPacketNb4					Counter32,
		amrDlVoipPacketNb5					Counter32,
		amrDlVoipPacketNb6					Counter32,
		amrDlVoipPacketNb7					Counter32,
		amrDlVoipPacketNb8					Counter32,
		voipLosSilentPackerCopyUl					Counter32,
		voipLosSilentPackerCopyDl					Counter32,
		voipLosActivePackerCopyUl					Counter32,
		voipLosActivePackerCopyDl					Counter32
		}


	voicePakStatisticLcId		 OBJECT-TYPE
		SYNTAX					 Integer32( 0 .. 23 )
		MAX-ACCESS			 not-accessible
		STATUS					 current
		DESCRIPTION			 " -- "
		::=  { voicePakStatisticEntry  1 }


	voicePakStatisticRowStatus		 OBJECT-TYPE
		SYNTAX					 RowStatus
		MAX-ACCESS			 read-only
		STATUS					 current
		DESCRIPTION			 " -- "
		::=  { voicePakStatisticEntry  2 }


	voipRtpPacketUl		 OBJECT-TYPE
		SYNTAX					 Counter32
		MAX-ACCESS			 read-only
		STATUS					 current
		DESCRIPTION			 " -- "
		::=  { voicePakStatisticEntry  3 }


	voipRtpPacketDl		 OBJECT-TYPE
		SYNTAX					 Counter32
		MAX-ACCESS			 read-only
		STATUS					 current
		DESCRIPTION			 " -- "
		::=  { voicePakStatisticEntry  4 }


	voipRtpPacketLosUl		 OBJECT-TYPE
		SYNTAX					 Counter32
		MAX-ACCESS			 read-only
		STATUS					 current
		DESCRIPTION			 " -- "
		::=  { voicePakStatisticEntry  5 }


	voipRtpPacketLosDl		 OBJECT-TYPE
		SYNTAX					 Counter32
		MAX-ACCESS			 read-only
		STATUS					 current
		DESCRIPTION			 " -- "
		::=  { voicePakStatisticEntry  6 }


	voipSilenceCallUl		 OBJECT-TYPE
		SYNTAX					 Counter32
		MAX-ACCESS			 read-only
		STATUS					 current
		DESCRIPTION			 " -- "
		::=  { voicePakStatisticEntry  7 }


	voipSilenceCallDl		 OBJECT-TYPE
		SYNTAX					 Counter32
		MAX-ACCESS			 read-only
		STATUS					 current
		DESCRIPTION			 " -- "
		::=  { voicePakStatisticEntry  8 }


	voipRohcDecompFailUl		 OBJECT-TYPE
		SYNTAX					 Counter32
		MAX-ACCESS			 read-only
		STATUS					 current
		DESCRIPTION			 " -- "
		::=  { voicePakStatisticEntry  9 }


	amrUlVoipPacketWb0		 OBJECT-TYPE
		SYNTAX					 Counter32
		MAX-ACCESS			 read-only
		STATUS					 current
		DESCRIPTION			 " -- "
		::=  { voicePakStatisticEntry  10 }


	amrUlVoipPacketWb1		 OBJECT-TYPE
		SYNTAX					 Counter32
		MAX-ACCESS			 read-only
		STATUS					 current
		DESCRIPTION			 " -- "
		::=  { voicePakStatisticEntry  11 }


	amrUlVoipPacketWb2		 OBJECT-TYPE
		SYNTAX					 Counter32
		MAX-ACCESS			 read-only
		STATUS					 current
		DESCRIPTION			 " -- "
		::=  { voicePakStatisticEntry  12 }


	amrUlVoipPacketWb3		 OBJECT-TYPE
		SYNTAX					 Counter32
		MAX-ACCESS			 read-only
		STATUS					 current
		DESCRIPTION			 " -- "
		::=  { voicePakStatisticEntry  13 }


	amrUlVoipPacketWb4		 OBJECT-TYPE
		SYNTAX					 Counter32
		MAX-ACCESS			 read-only
		STATUS					 current
		DESCRIPTION			 " -- "
		::=  { voicePakStatisticEntry  14 }


	amrUlVoipPacketWb5		 OBJECT-TYPE
		SYNTAX					 Counter32
		MAX-ACCESS			 read-only
		STATUS					 current
		DESCRIPTION			 " -- "
		::=  { voicePakStatisticEntry  15 }


	amrUlVoipPacketWb6		 OBJECT-TYPE
		SYNTAX					 Counter32
		MAX-ACCESS			 read-only
		STATUS					 current
		DESCRIPTION			 " -- "
		::=  { voicePakStatisticEntry  16 }


	amrUlVoipPacketWb7		 OBJECT-TYPE
		SYNTAX					 Counter32
		MAX-ACCESS			 read-only
		STATUS					 current
		DESCRIPTION			 " -- "
		::=  { voicePakStatisticEntry  17 }


	amrUlVoipPacketWb8		 OBJECT-TYPE
		SYNTAX					 Counter32
		MAX-ACCESS			 read-only
		STATUS					 current
		DESCRIPTION			 " -- "
		::=  { voicePakStatisticEntry  18 }


	amrUlVoipPacketWb9		 OBJECT-TYPE
		SYNTAX					 Counter32
		MAX-ACCESS			 read-only
		STATUS					 current
		DESCRIPTION			 " -- "
		::=  { voicePakStatisticEntry  19 }


	amrUlVoipPacketNb0		 OBJECT-TYPE
		SYNTAX					 Counter32
		MAX-ACCESS			 read-only
		STATUS					 current
		DESCRIPTION			 " -- "
		::=  { voicePakStatisticEntry  20 }


	amrUlVoipPacketNb1		 OBJECT-TYPE
		SYNTAX					 Counter32
		MAX-ACCESS			 read-only
		STATUS					 current
		DESCRIPTION			 " -- "
		::=  { voicePakStatisticEntry  21 }


	amrUlVoipPacketNb2		 OBJECT-TYPE
		SYNTAX					 Counter32
		MAX-ACCESS			 read-only
		STATUS					 current
		DESCRIPTION			 " -- "
		::=  { voicePakStatisticEntry  22 }


	amrUlVoipPacketNb3		 OBJECT-TYPE
		SYNTAX					 Counter32
		MAX-ACCESS			 read-only
		STATUS					 current
		DESCRIPTION			 " -- "
		::=  { voicePakStatisticEntry  23 }


	amrUlVoipPacketNb4		 OBJECT-TYPE
		SYNTAX					 Counter32
		MAX-ACCESS			 read-only
		STATUS					 current
		DESCRIPTION			 " -- "
		::=  { voicePakStatisticEntry  24 }


	amrUlVoipPacketNb5		 OBJECT-TYPE
		SYNTAX					 Counter32
		MAX-ACCESS			 read-only
		STATUS					 current
		DESCRIPTION			 " -- "
		::=  { voicePakStatisticEntry  25 }


	amrUlVoipPacketNb6		 OBJECT-TYPE
		SYNTAX					 Counter32
		MAX-ACCESS			 read-only
		STATUS					 current
		DESCRIPTION			 " -- "
		::=  { voicePakStatisticEntry  26 }


	amrUlVoipPacketNb7		 OBJECT-TYPE
		SYNTAX					 Counter32
		MAX-ACCESS			 read-only
		STATUS					 current
		DESCRIPTION			 " -- "
		::=  { voicePakStatisticEntry  27 }


	amrUlVoipPacketNb8		 OBJECT-TYPE
		SYNTAX					 Counter32
		MAX-ACCESS			 read-only
		STATUS					 current
		DESCRIPTION			 " -- "
		::=  { voicePakStatisticEntry  28 }


	amrDlVoipPacketWb0		 OBJECT-TYPE
		SYNTAX					 Counter32
		MAX-ACCESS			 read-only
		STATUS					 current
		DESCRIPTION			 " -- "
		::=  { voicePakStatisticEntry  29 }


	amrDlVoipPacketWb1		 OBJECT-TYPE
		SYNTAX					 Counter32
		MAX-ACCESS			 read-only
		STATUS					 current
		DESCRIPTION			 " -- "
		::=  { voicePakStatisticEntry  30 }


	amrDlVoipPacketWb2		 OBJECT-TYPE
		SYNTAX					 Counter32
		MAX-ACCESS			 read-only
		STATUS					 current
		DESCRIPTION			 " -- "
		::=  { voicePakStatisticEntry  31 }


	amrDlVoipPacketWb3		 OBJECT-TYPE
		SYNTAX					 Counter32
		MAX-ACCESS			 read-only
		STATUS					 current
		DESCRIPTION			 " -- "
		::=  { voicePakStatisticEntry  32 }


	amrDlVoipPacketWb4		 OBJECT-TYPE
		SYNTAX					 Counter32
		MAX-ACCESS			 read-only
		STATUS					 current
		DESCRIPTION			 " -- "
		::=  { voicePakStatisticEntry  33 }


	amrDlVoipPacketWb5		 OBJECT-TYPE
		SYNTAX					 Counter32
		MAX-ACCESS			 read-only
		STATUS					 current
		DESCRIPTION			 " -- "
		::=  { voicePakStatisticEntry  34 }


	amrDlVoipPacketWb6		 OBJECT-TYPE
		SYNTAX					 Counter32
		MAX-ACCESS			 read-only
		STATUS					 current
		DESCRIPTION			 " -- "
		::=  { voicePakStatisticEntry  35 }


	amrDlVoipPacketWb7		 OBJECT-TYPE
		SYNTAX					 Counter32
		MAX-ACCESS			 read-only
		STATUS					 current
		DESCRIPTION			 " -- "
		::=  { voicePakStatisticEntry  36 }


	amrDlVoipPacketWb8		 OBJECT-TYPE
		SYNTAX					 Counter32
		MAX-ACCESS			 read-only
		STATUS					 current
		DESCRIPTION			 " -- "
		::=  { voicePakStatisticEntry  37 }


	amrDlVoipPacketWb9		 OBJECT-TYPE
		SYNTAX					 Counter32
		MAX-ACCESS			 read-only
		STATUS					 current
		DESCRIPTION			 " -- "
		::=  { voicePakStatisticEntry  38 }


	amrDlVoipPacketNb0		 OBJECT-TYPE
		SYNTAX					 Counter32
		MAX-ACCESS			 read-only
		STATUS					 current
		DESCRIPTION			 " -- "
		::=  { voicePakStatisticEntry  39 }


	amrDlVoipPacketNb1		 OBJECT-TYPE
		SYNTAX					 Counter32
		MAX-ACCESS			 read-only
		STATUS					 current
		DESCRIPTION			 " -- "
		::=  { voicePakStatisticEntry  40 }


	amrDlVoipPacketNb2		 OBJECT-TYPE
		SYNTAX					 Counter32
		MAX-ACCESS			 read-only
		STATUS					 current
		DESCRIPTION			 " -- "
		::=  { voicePakStatisticEntry  41 }


	amrDlVoipPacketNb3		 OBJECT-TYPE
		SYNTAX					 Counter32
		MAX-ACCESS			 read-only
		STATUS					 current
		DESCRIPTION			 " -- "
		::=  { voicePakStatisticEntry  42 }


	amrDlVoipPacketNb4		 OBJECT-TYPE
		SYNTAX					 Counter32
		MAX-ACCESS			 read-only
		STATUS					 current
		DESCRIPTION			 " -- "
		::=  { voicePakStatisticEntry  43 }


	amrDlVoipPacketNb5		 OBJECT-TYPE
		SYNTAX					 Counter32
		MAX-ACCESS			 read-only
		STATUS					 current
		DESCRIPTION			 " -- "
		::=  { voicePakStatisticEntry  44 }


	amrDlVoipPacketNb6		 OBJECT-TYPE
		SYNTAX					 Counter32
		MAX-ACCESS			 read-only
		STATUS					 current
		DESCRIPTION			 " -- "
		::=  { voicePakStatisticEntry  45 }


	amrDlVoipPacketNb7		 OBJECT-TYPE
		SYNTAX					 Counter32
		MAX-ACCESS			 read-only
		STATUS					 current
		DESCRIPTION			 " -- "
		::=  { voicePakStatisticEntry  46 }


	amrDlVoipPacketNb8		 OBJECT-TYPE
		SYNTAX					 Counter32
		MAX-ACCESS			 read-only
		STATUS					 current
		DESCRIPTION			 " -- "
		::=  { voicePakStatisticEntry  47 }


	voipLosSilentPackerCopyUl		 OBJECT-TYPE
		SYNTAX					 Counter32
		MAX-ACCESS			 read-only
		STATUS					 current
		DESCRIPTION			 " -- "
		::=  { voicePakStatisticEntry  48 }


	voipLosSilentPackerCopyDl		 OBJECT-TYPE
		SYNTAX					 Counter32
		MAX-ACCESS			 read-only
		STATUS					 current
		DESCRIPTION			 " -- "
		::=  { voicePakStatisticEntry  49 }


	voipLosActivePackerCopyUl		 OBJECT-TYPE
		SYNTAX					 Counter32
		MAX-ACCESS			 read-only
		STATUS					 current
		DESCRIPTION			 " -- "
		::=  { voicePakStatisticEntry  50 }


	voipLosActivePackerCopyDl		 OBJECT-TYPE
		SYNTAX					 Counter32
		MAX-ACCESS			 read-only
		STATUS					 current
		DESCRIPTION			 " -- "
		::=  { voicePakStatisticEntry  51 }


	pdcpDlSduAirDropRatioTable		 OBJECT-TYPE
		SYNTAX					 SEQUENCE  OF	 PdcpDlSduAirDropRatioEntry
		MAX-ACCESS			 not-accessible
		STATUS					 current
		DESCRIPTION			 " -- "
		::=  { pdcprelatedOriginCounter  6 }


	pdcpDlSduAirDropRatioEntry		 OBJECT-TYPE
		SYNTAX					 PdcpDlSduAirDropRatioEntry
		MAX-ACCESS			 not-accessible
		STATUS					 current
		DESCRIPTION			 " -- "
		INDEX						{ pdcpDlSduAirDropRatioLcId }
		::=  { pdcpDlSduAirDropRatioTable  1 }


	PdcpDlSduAirDropRatioEntry		 ::=  SEQUENCE {
		pdcpDlSduAirDropRatioLcId					Integer32,
		pdcpDlSduAirDropRatioRowStatus					RowStatus,
		pdcpDlAirSduSendTotalNumberQci1					Counter32,
		pdcpDlAirSduSendTotalNumberQci2					Counter32,
		pdcpDlAirSduSendTotalNumberQci3					Counter32,
		pdcpDlAirSduSendTotalNumberQci4					Counter32,
		pdcpDlAirSduSendTotalNumberQci5					Counter32,
		pdcpDlAirSduSendTotalNumberQci6					Counter32,
		pdcpDlAirSduSendTotalNumberQci7					Counter32,
		pdcpDlAirSduSendTotalNumberQci8					Counter32,
		pdcpDlAirSduSendTotalNumberQci9					Counter32,
		pdcpDlAirSduDropTotalNumberQci1					Counter32,
		pdcpDlAirSduDropTotalNumberQci2					Counter32,
		pdcpDlAirSduDropTotalNumberQci3					Counter32,
		pdcpDlAirSduDropTotalNumberQci4					Counter32,
		pdcpDlAirSduDropTotalNumberQci5					Counter32,
		pdcpDlAirSduDropTotalNumberQci6					Counter32,
		pdcpDlAirSduDropTotalNumberQci7					Counter32,
		pdcpDlAirSduDropTotalNumberQci8					Counter32,
		pdcpDlAirSduDropTotalNumberQci9					Counter32,
		pdcpUpPktLossRateDlEnb					Counter32,
		pdcpUpPktLossRateDlQci1Enb					Counter32,
		pdcpUpPktLossRateDlQci2Enb					Counter32,
		pdcpUpPktLossRateDlQci3Enb					Counter32,
		pdcpUpPktLossRateDlQci4Enb					Counter32,
		pdcpUpPktLossRateDlQci5Enb					Counter32,
		pdcpUpPktLossRateDlQci6Enb					Counter32,
		pdcpUpPktLossRateDlQci7Enb					Counter32,
		pdcpUpPktLossRateDlQci8Enb					Counter32,
		pdcpUpPktLossRateDlQci9Enb					Counter32
		}


	pdcpDlSduAirDropRatioLcId		 OBJECT-TYPE
		SYNTAX					 Integer32( 0 .. 23 )
		MAX-ACCESS			 not-accessible
		STATUS					 current
		DESCRIPTION			 " -- "
		::=  { pdcpDlSduAirDropRatioEntry  1 }


	pdcpDlSduAirDropRatioRowStatus		 OBJECT-TYPE
		SYNTAX					 RowStatus
		MAX-ACCESS			 read-only
		STATUS					 current
		DESCRIPTION			 " -- "
		::=  { pdcpDlSduAirDropRatioEntry  2 }


	pdcpDlAirSduSendTotalNumberQci1		 OBJECT-TYPE
		SYNTAX					 Counter32
		MAX-ACCESS			 read-only
		STATUS					 current
		DESCRIPTION			 " -- "
		::=  { pdcpDlSduAirDropRatioEntry  3 }


	pdcpDlAirSduSendTotalNumberQci2		 OBJECT-TYPE
		SYNTAX					 Counter32
		MAX-ACCESS			 read-only
		STATUS					 current
		DESCRIPTION			 " -- "
		::=  { pdcpDlSduAirDropRatioEntry  4 }


	pdcpDlAirSduSendTotalNumberQci3		 OBJECT-TYPE
		SYNTAX					 Counter32
		MAX-ACCESS			 read-only
		STATUS					 current
		DESCRIPTION			 " -- "
		::=  { pdcpDlSduAirDropRatioEntry  5 }


	pdcpDlAirSduSendTotalNumberQci4		 OBJECT-TYPE
		SYNTAX					 Counter32
		MAX-ACCESS			 read-only
		STATUS					 current
		DESCRIPTION			 " -- "
		::=  { pdcpDlSduAirDropRatioEntry  6 }


	pdcpDlAirSduSendTotalNumberQci5		 OBJECT-TYPE
		SYNTAX					 Counter32
		MAX-ACCESS			 read-only
		STATUS					 current
		DESCRIPTION			 " -- "
		::=  { pdcpDlSduAirDropRatioEntry  7 }


	pdcpDlAirSduSendTotalNumberQci6		 OBJECT-TYPE
		SYNTAX					 Counter32
		MAX-ACCESS			 read-only
		STATUS					 current
		DESCRIPTION			 " -- "
		::=  { pdcpDlSduAirDropRatioEntry  8 }


	pdcpDlAirSduSendTotalNumberQci7		 OBJECT-TYPE
		SYNTAX					 Counter32
		MAX-ACCESS			 read-only
		STATUS					 current
		DESCRIPTION			 " -- "
		::=  { pdcpDlSduAirDropRatioEntry  9 }


	pdcpDlAirSduSendTotalNumberQci8		 OBJECT-TYPE
		SYNTAX					 Counter32
		MAX-ACCESS			 read-only
		STATUS					 current
		DESCRIPTION			 " -- "
		::=  { pdcpDlSduAirDropRatioEntry  10 }


	pdcpDlAirSduSendTotalNumberQci9		 OBJECT-TYPE
		SYNTAX					 Counter32
		MAX-ACCESS			 read-only
		STATUS					 current
		DESCRIPTION			 " -- "
		::=  { pdcpDlSduAirDropRatioEntry  11 }


	pdcpDlAirSduDropTotalNumberQci1		 OBJECT-TYPE
		SYNTAX					 Counter32
		MAX-ACCESS			 read-only
		STATUS					 current
		DESCRIPTION			 " -- "
		::=  { pdcpDlSduAirDropRatioEntry  12 }


	pdcpDlAirSduDropTotalNumberQci2		 OBJECT-TYPE
		SYNTAX					 Counter32
		MAX-ACCESS			 read-only
		STATUS					 current
		DESCRIPTION			 " -- "
		::=  { pdcpDlSduAirDropRatioEntry  13 }


	pdcpDlAirSduDropTotalNumberQci3		 OBJECT-TYPE
		SYNTAX					 Counter32
		MAX-ACCESS			 read-only
		STATUS					 current
		DESCRIPTION			 " -- "
		::=  { pdcpDlSduAirDropRatioEntry  14 }


	pdcpDlAirSduDropTotalNumberQci4		 OBJECT-TYPE
		SYNTAX					 Counter32
		MAX-ACCESS			 read-only
		STATUS					 current
		DESCRIPTION			 " -- "
		::=  { pdcpDlSduAirDropRatioEntry  15 }


	pdcpDlAirSduDropTotalNumberQci5		 OBJECT-TYPE
		SYNTAX					 Counter32
		MAX-ACCESS			 read-only
		STATUS					 current
		DESCRIPTION			 " -- "
		::=  { pdcpDlSduAirDropRatioEntry  16 }


	pdcpDlAirSduDropTotalNumberQci6		 OBJECT-TYPE
		SYNTAX					 Counter32
		MAX-ACCESS			 read-only
		STATUS					 current
		DESCRIPTION			 " -- "
		::=  { pdcpDlSduAirDropRatioEntry  17 }


	pdcpDlAirSduDropTotalNumberQci7		 OBJECT-TYPE
		SYNTAX					 Counter32
		MAX-ACCESS			 read-only
		STATUS					 current
		DESCRIPTION			 " -- "
		::=  { pdcpDlSduAirDropRatioEntry  18 }


	pdcpDlAirSduDropTotalNumberQci8		 OBJECT-TYPE
		SYNTAX					 Counter32
		MAX-ACCESS			 read-only
		STATUS					 current
		DESCRIPTION			 " -- "
		::=  { pdcpDlSduAirDropRatioEntry  19 }


	pdcpDlAirSduDropTotalNumberQci9		 OBJECT-TYPE
		SYNTAX					 Counter32
		MAX-ACCESS			 read-only
		STATUS					 current
		DESCRIPTION			 " -- "
		::=  { pdcpDlSduAirDropRatioEntry  20 }


	pdcpUpPktLossRateDlEnb		 OBJECT-TYPE
		SYNTAX					 Counter32
		MAX-ACCESS			 read-only
		STATUS					 current
		DESCRIPTION			 " -- "
		::=  { pdcpDlSduAirDropRatioEntry  200 }


	pdcpUpPktLossRateDlQci1Enb		 OBJECT-TYPE
		SYNTAX					 Counter32
		MAX-ACCESS			 read-only
		STATUS					 current
		DESCRIPTION			 " -- "
		::=  { pdcpDlSduAirDropRatioEntry  201 }


	pdcpUpPktLossRateDlQci2Enb		 OBJECT-TYPE
		SYNTAX					 Counter32
		MAX-ACCESS			 read-only
		STATUS					 current
		DESCRIPTION			 " -- "
		::=  { pdcpDlSduAirDropRatioEntry  202 }


	pdcpUpPktLossRateDlQci3Enb		 OBJECT-TYPE
		SYNTAX					 Counter32
		MAX-ACCESS			 read-only
		STATUS					 current
		DESCRIPTION			 " -- "
		::=  { pdcpDlSduAirDropRatioEntry  203 }


	pdcpUpPktLossRateDlQci4Enb		 OBJECT-TYPE
		SYNTAX					 Counter32
		MAX-ACCESS			 read-only
		STATUS					 current
		DESCRIPTION			 " -- "
		::=  { pdcpDlSduAirDropRatioEntry  204 }


	pdcpUpPktLossRateDlQci5Enb		 OBJECT-TYPE
		SYNTAX					 Counter32
		MAX-ACCESS			 read-only
		STATUS					 current
		DESCRIPTION			 " -- "
		::=  { pdcpDlSduAirDropRatioEntry  205 }


	pdcpUpPktLossRateDlQci6Enb		 OBJECT-TYPE
		SYNTAX					 Counter32
		MAX-ACCESS			 read-only
		STATUS					 current
		DESCRIPTION			 " -- "
		::=  { pdcpDlSduAirDropRatioEntry  206 }


	pdcpUpPktLossRateDlQci7Enb		 OBJECT-TYPE
		SYNTAX					 Counter32
		MAX-ACCESS			 read-only
		STATUS					 current
		DESCRIPTION			 " -- "
		::=  { pdcpDlSduAirDropRatioEntry  207 }


	pdcpUpPktLossRateDlQci8Enb		 OBJECT-TYPE
		SYNTAX					 Counter32
		MAX-ACCESS			 read-only
		STATUS					 current
		DESCRIPTION			 " -- "
		::=  { pdcpDlSduAirDropRatioEntry  208 }


	pdcpUpPktLossRateDlQci9Enb		 OBJECT-TYPE
		SYNTAX					 Counter32
		MAX-ACCESS			 read-only
		STATUS					 current
		DESCRIPTION			 " -- "
		::=  { pdcpDlSduAirDropRatioEntry  209 }


	pdcpSduReceivedNbrTable		 OBJECT-TYPE
		SYNTAX					 SEQUENCE  OF	 PdcpSduReceivedNbrEntry
		MAX-ACCESS			 not-accessible
		STATUS					 current
		DESCRIPTION			 " -- "
		::=  { pdcprelatedOriginCounter  7 }


	pdcpSduReceivedNbrEntry		 OBJECT-TYPE
		SYNTAX					 PdcpSduReceivedNbrEntry
		MAX-ACCESS			 not-accessible
		STATUS					 current
		DESCRIPTION			 " -- "
		INDEX						{ pdcpSduReceivedNbrLcId }
		::=  { pdcpSduReceivedNbrTable  1 }


	PdcpSduReceivedNbrEntry		 ::=  SEQUENCE {
		pdcpSduReceivedNbrLcId					Integer32,
		pdcpSduReceivedNbrRowStatus					RowStatus,
		pdcpNbrUl					Counter32,
		pdcpNbrDl					Counter32
		}


	pdcpSduReceivedNbrLcId		 OBJECT-TYPE
		SYNTAX					 Integer32( 0 .. 23 )
		MAX-ACCESS			 not-accessible
		STATUS					 current
		DESCRIPTION			 " -- "
		::=  { pdcpSduReceivedNbrEntry  1 }


	pdcpSduReceivedNbrRowStatus		 OBJECT-TYPE
		SYNTAX					 RowStatus
		MAX-ACCESS			 read-only
		STATUS					 current
		DESCRIPTION			 " -- "
		::=  { pdcpSduReceivedNbrEntry  2 }


	pdcpNbrUl		 OBJECT-TYPE
		SYNTAX					 Counter32
		MAX-ACCESS			 read-only
		STATUS					 current
		DESCRIPTION			 " -- "
		::=  { pdcpSduReceivedNbrEntry  3 }


	pdcpNbrDl		 OBJECT-TYPE
		SYNTAX					 Counter32
		MAX-ACCESS			 read-only
		STATUS					 current
		DESCRIPTION			 " -- "
		::=  { pdcpSduReceivedNbrEntry  4 }


	activeRRCTable		 OBJECT-TYPE
		SYNTAX					 SEQUENCE  OF	 ActiveRRCEntry
		MAX-ACCESS			 not-accessible
		STATUS					 current
		DESCRIPTION			 " -- "
		::=  { pdcprelatedOriginCounter  8 }


	activeRRCEntry		 OBJECT-TYPE
		SYNTAX					 ActiveRRCEntry
		MAX-ACCESS			 not-accessible
		STATUS					 current
		DESCRIPTION			 " -- "
		INDEX						{ activeRRCLcId }
		::=  { activeRRCTable  1 }


	ActiveRRCEntry		 ::=  SEQUENCE {
		activeRRCLcId					Integer32,
		activeRRCRowStatus					RowStatus,
		rrcEffectiveConnMean					Counter32,
		rrcEffectiveConnMax					Counter32,
		rrcEffectiveConnSum					Counter32,
		rrcEffectiveConnSampNum					Counter32
		}


	activeRRCLcId		 OBJECT-TYPE
		SYNTAX					 Integer32( 0 .. 23 )
		MAX-ACCESS			 not-accessible
		STATUS					 current
		DESCRIPTION			 " -- "
		::=  { activeRRCEntry  1 }


	activeRRCRowStatus		 OBJECT-TYPE
		SYNTAX					 RowStatus
		MAX-ACCESS			 read-only
		STATUS					 current
		DESCRIPTION			 " -- "
		::=  { activeRRCEntry  2 }


	rrcEffectiveConnMean		 OBJECT-TYPE
		SYNTAX					 Counter32
		MAX-ACCESS			 read-only
		STATUS					 current
		DESCRIPTION			 " -- "
		::=  { activeRRCEntry  3 }


	rrcEffectiveConnMax		 OBJECT-TYPE
		SYNTAX					 Counter32
		MAX-ACCESS			 read-only
		STATUS					 current
		DESCRIPTION			 " -- "
		::=  { activeRRCEntry  4 }


	rrcEffectiveConnSum		 OBJECT-TYPE
		SYNTAX					 Counter32
		MAX-ACCESS			 read-only
		STATUS					 current
		DESCRIPTION			 " -- "
		::=  { activeRRCEntry  5 }


	rrcEffectiveConnSampNum		 OBJECT-TYPE
		SYNTAX					 Counter32
		MAX-ACCESS			 read-only
		STATUS					 current
		DESCRIPTION			 " -- "
		::=  { activeRRCEntry  6 }


	ipThroughputCapacityTable		 OBJECT-TYPE
		SYNTAX					 SEQUENCE  OF	 IpThroughputCapacityEntry
		MAX-ACCESS			 not-accessible
		STATUS					 current
		DESCRIPTION			 " -- "
		::=  { pdcprelatedOriginCounter  9 }


	ipThroughputCapacityEntry		 OBJECT-TYPE
		SYNTAX					 IpThroughputCapacityEntry
		MAX-ACCESS			 not-accessible
		STATUS					 current
		DESCRIPTION			 " -- "
		INDEX						{ ipThroughputCapacityLcId }
		::=  { ipThroughputCapacityTable  1 }


	IpThroughputCapacityEntry		 ::=  SEQUENCE {
		ipThroughputCapacityLcId					Integer32,
		ipThroughputCapacityRowStatus					RowStatus,
		pdcpIPThroughputDlQci1					Counter32,
		pdcpIPThroughputDlQci2					Counter32,
		pdcpIPThroughputDlQci3					Counter32,
		pdcpIPThroughputDlQci4					Counter32,
		pdcpIPThroughputDlQci5					Counter32,
		pdcpIPThroughputDlQci6					Counter32,
		pdcpIPThroughputDlQci7					Counter32,
		pdcpIPThroughputDlQci8					Counter32,
		pdcpIPThroughputDlQci9					Counter32,
		pdcpIPThroughputUlQci1					Counter32,
		pdcpIPThroughputUlQci2					Counter32,
		pdcpIPThroughputUlQci3					Counter32,
		pdcpIPThroughputUlQci4					Counter32,
		pdcpIPThroughputUlQci5					Counter32,
		pdcpIPThroughputUlQci6					Counter32,
		pdcpIPThroughputUlQci7					Counter32,
		pdcpIPThroughputUlQci8					Counter32,
		pdcpIPThroughputUlQci9					Counter32
		}


	ipThroughputCapacityLcId		 OBJECT-TYPE
		SYNTAX					 Integer32( 0 .. 23 )
		MAX-ACCESS			 not-accessible
		STATUS					 current
		DESCRIPTION			 " -- "
		::=  { ipThroughputCapacityEntry  1 }


	ipThroughputCapacityRowStatus		 OBJECT-TYPE
		SYNTAX					 RowStatus
		MAX-ACCESS			 read-only
		STATUS					 current
		DESCRIPTION			 " -- "
		::=  { ipThroughputCapacityEntry  2 }


	pdcpIPThroughputDlQci1		 OBJECT-TYPE
		SYNTAX					 Counter32
		MAX-ACCESS			 read-only
		STATUS					 current
		DESCRIPTION			 " -- "
		::=  { ipThroughputCapacityEntry  3 }


	pdcpIPThroughputDlQci2		 OBJECT-TYPE
		SYNTAX					 Counter32
		MAX-ACCESS			 read-only
		STATUS					 current
		DESCRIPTION			 " -- "
		::=  { ipThroughputCapacityEntry  4 }


	pdcpIPThroughputDlQci3		 OBJECT-TYPE
		SYNTAX					 Counter32
		MAX-ACCESS			 read-only
		STATUS					 current
		DESCRIPTION			 " -- "
		::=  { ipThroughputCapacityEntry  5 }


	pdcpIPThroughputDlQci4		 OBJECT-TYPE
		SYNTAX					 Counter32
		MAX-ACCESS			 read-only
		STATUS					 current
		DESCRIPTION			 " -- "
		::=  { ipThroughputCapacityEntry  6 }


	pdcpIPThroughputDlQci5		 OBJECT-TYPE
		SYNTAX					 Counter32
		MAX-ACCESS			 read-only
		STATUS					 current
		DESCRIPTION			 " -- "
		::=  { ipThroughputCapacityEntry  7 }


	pdcpIPThroughputDlQci6		 OBJECT-TYPE
		SYNTAX					 Counter32
		MAX-ACCESS			 read-only
		STATUS					 current
		DESCRIPTION			 " -- "
		::=  { ipThroughputCapacityEntry  8 }


	pdcpIPThroughputDlQci7		 OBJECT-TYPE
		SYNTAX					 Counter32
		MAX-ACCESS			 read-only
		STATUS					 current
		DESCRIPTION			 " -- "
		::=  { ipThroughputCapacityEntry  9 }


	pdcpIPThroughputDlQci8		 OBJECT-TYPE
		SYNTAX					 Counter32
		MAX-ACCESS			 read-only
		STATUS					 current
		DESCRIPTION			 " -- "
		::=  { ipThroughputCapacityEntry  10 }


	pdcpIPThroughputDlQci9		 OBJECT-TYPE
		SYNTAX					 Counter32
		MAX-ACCESS			 read-only
		STATUS					 current
		DESCRIPTION			 " -- "
		::=  { ipThroughputCapacityEntry  11 }


	pdcpIPThroughputUlQci1		 OBJECT-TYPE
		SYNTAX					 Counter32
		MAX-ACCESS			 read-only
		STATUS					 current
		DESCRIPTION			 " -- "
		::=  { ipThroughputCapacityEntry  12 }


	pdcpIPThroughputUlQci2		 OBJECT-TYPE
		SYNTAX					 Counter32
		MAX-ACCESS			 read-only
		STATUS					 current
		DESCRIPTION			 " -- "
		::=  { ipThroughputCapacityEntry  13 }


	pdcpIPThroughputUlQci3		 OBJECT-TYPE
		SYNTAX					 Counter32
		MAX-ACCESS			 read-only
		STATUS					 current
		DESCRIPTION			 " -- "
		::=  { ipThroughputCapacityEntry  14 }


	pdcpIPThroughputUlQci4		 OBJECT-TYPE
		SYNTAX					 Counter32
		MAX-ACCESS			 read-only
		STATUS					 current
		DESCRIPTION			 " -- "
		::=  { ipThroughputCapacityEntry  15 }


	pdcpIPThroughputUlQci5		 OBJECT-TYPE
		SYNTAX					 Counter32
		MAX-ACCESS			 read-only
		STATUS					 current
		DESCRIPTION			 " -- "
		::=  { ipThroughputCapacityEntry  16 }


	pdcpIPThroughputUlQci6		 OBJECT-TYPE
		SYNTAX					 Counter32
		MAX-ACCESS			 read-only
		STATUS					 current
		DESCRIPTION			 " -- "
		::=  { ipThroughputCapacityEntry  17 }


	pdcpIPThroughputUlQci7		 OBJECT-TYPE
		SYNTAX					 Counter32
		MAX-ACCESS			 read-only
		STATUS					 current
		DESCRIPTION			 " -- "
		::=  { ipThroughputCapacityEntry  18 }


	pdcpIPThroughputUlQci8		 OBJECT-TYPE
		SYNTAX					 Counter32
		MAX-ACCESS			 read-only
		STATUS					 current
		DESCRIPTION			 " -- "
		::=  { ipThroughputCapacityEntry  19 }


	pdcpIPThroughputUlQci9		 OBJECT-TYPE
		SYNTAX					 Counter32
		MAX-ACCESS			 read-only
		STATUS					 current
		DESCRIPTION			 " -- "
		::=  { ipThroughputCapacityEntry  20 }


	sessionTimeTable		 OBJECT-TYPE
		SYNTAX					 SEQUENCE  OF	 SessionTimeEntry
		MAX-ACCESS			 not-accessible
		STATUS					 current
		DESCRIPTION			 " -- "
		::=  { pdcprelatedOriginCounter  10 }


	sessionTimeEntry		 OBJECT-TYPE
		SYNTAX					 SessionTimeEntry
		MAX-ACCESS			 not-accessible
		STATUS					 current
		DESCRIPTION			 " -- "
		INDEX						{ sessionTimeLcId }
		::=  { sessionTimeTable  1 }


	SessionTimeEntry		 ::=  SEQUENCE {
		sessionTimeLcId					Integer32,
		sessionTimeRowStatus					RowStatus,
		sessiontimeue					Counter32,
		sessiontimeerabQci1					Counter32,
		sessiontimeerabQci2					Counter32,
		sessiontimeerabQci3					Counter32,
		sessiontimeerabQci4					Counter32,
		sessiontimeerabQci5					Counter32,
		sessiontimeerabQci6					Counter32,
		sessiontimeerabQci7					Counter32,
		sessiontimeerabQci8					Counter32,
		sessiontimeerabQci9					Counter32
		}


	sessionTimeLcId		 OBJECT-TYPE
		SYNTAX					 Integer32( 0 .. 23 )
		MAX-ACCESS			 not-accessible
		STATUS					 current
		DESCRIPTION			 " -- "
		::=  { sessionTimeEntry  1 }


	sessionTimeRowStatus		 OBJECT-TYPE
		SYNTAX					 RowStatus
		MAX-ACCESS			 read-only
		STATUS					 current
		DESCRIPTION			 " -- "
		::=  { sessionTimeEntry  2 }


	sessiontimeue		 OBJECT-TYPE
		SYNTAX					 Counter32
		MAX-ACCESS			 read-only
		STATUS					 current
		DESCRIPTION			 " -- "
		::=  { sessionTimeEntry  3 }


	sessiontimeerabQci1		 OBJECT-TYPE
		SYNTAX					 Counter32
		MAX-ACCESS			 read-only
		STATUS					 current
		DESCRIPTION			 " -- "
		::=  { sessionTimeEntry  4 }


	sessiontimeerabQci2		 OBJECT-TYPE
		SYNTAX					 Counter32
		MAX-ACCESS			 read-only
		STATUS					 current
		DESCRIPTION			 " -- "
		::=  { sessionTimeEntry  5 }


	sessiontimeerabQci3		 OBJECT-TYPE
		SYNTAX					 Counter32
		MAX-ACCESS			 read-only
		STATUS					 current
		DESCRIPTION			 " -- "
		::=  { sessionTimeEntry  6 }


	sessiontimeerabQci4		 OBJECT-TYPE
		SYNTAX					 Counter32
		MAX-ACCESS			 read-only
		STATUS					 current
		DESCRIPTION			 " -- "
		::=  { sessionTimeEntry  7 }


	sessiontimeerabQci5		 OBJECT-TYPE
		SYNTAX					 Counter32
		MAX-ACCESS			 read-only
		STATUS					 current
		DESCRIPTION			 " -- "
		::=  { sessionTimeEntry  8 }


	sessiontimeerabQci6		 OBJECT-TYPE
		SYNTAX					 Counter32
		MAX-ACCESS			 read-only
		STATUS					 current
		DESCRIPTION			 " -- "
		::=  { sessionTimeEntry  9 }


	sessiontimeerabQci7		 OBJECT-TYPE
		SYNTAX					 Counter32
		MAX-ACCESS			 read-only
		STATUS					 current
		DESCRIPTION			 " -- "
		::=  { sessionTimeEntry  10 }


	sessiontimeerabQci8		 OBJECT-TYPE
		SYNTAX					 Counter32
		MAX-ACCESS			 read-only
		STATUS					 current
		DESCRIPTION			 " -- "
		::=  { sessionTimeEntry  11 }


	sessiontimeerabQci9		 OBJECT-TYPE
		SYNTAX					 Counter32
		MAX-ACCESS			 read-only
		STATUS					 current
		DESCRIPTION			 " -- "
		::=  { sessionTimeEntry  12 }


	dataPlanStatisticTable		 OBJECT-TYPE
		SYNTAX					 SEQUENCE  OF	 DataPlanStatisticEntry
		MAX-ACCESS			 not-accessible
		STATUS					 current
		DESCRIPTION			 " -- "
		::=  { pdcprelatedOriginCounter  11 }


	dataPlanStatisticEntry		 OBJECT-TYPE
		SYNTAX					 DataPlanStatisticEntry
		MAX-ACCESS			 not-accessible
		STATUS					 current
		DESCRIPTION			 " -- "
		INDEX						{ dataPlanStatisticLcId }
		::=  { dataPlanStatisticTable  1 }


	DataPlanStatisticEntry		 ::=  SEQUENCE {
		dataPlanStatisticLcId					Integer32,
		dataPlanStatisticRowStatus					RowStatus,
		drbTCPSduReceivedDl					Counter32,
		drbTCPSduResentLineDisorderDl					Counter32,
		drbTCPSduResentLineDropDl					Counter32,
		drbTCPSduResentRadioDl					Counter32
		}


	dataPlanStatisticLcId		 OBJECT-TYPE
		SYNTAX					 Integer32( 0 .. 23 )
		MAX-ACCESS			 not-accessible
		STATUS					 current
		DESCRIPTION			 " -- "
		::=  { dataPlanStatisticEntry  1 }


	dataPlanStatisticRowStatus		 OBJECT-TYPE
		SYNTAX					 RowStatus
		MAX-ACCESS			 read-only
		STATUS					 current
		DESCRIPTION			 " -- "
		::=  { dataPlanStatisticEntry  2 }


	drbTCPSduReceivedDl		 OBJECT-TYPE
		SYNTAX					 Counter32
		MAX-ACCESS			 read-only
		STATUS					 current
		DESCRIPTION			 " -- "
		::=  { dataPlanStatisticEntry  3 }


	drbTCPSduResentLineDisorderDl		 OBJECT-TYPE
		SYNTAX					 Counter32
		MAX-ACCESS			 read-only
		STATUS					 current
		DESCRIPTION			 " -- "
		::=  { dataPlanStatisticEntry  4 }


	drbTCPSduResentLineDropDl		 OBJECT-TYPE
		SYNTAX					 Counter32
		MAX-ACCESS			 read-only
		STATUS					 current
		DESCRIPTION			 " -- "
		::=  { dataPlanStatisticEntry  5 }


	drbTCPSduResentRadioDl		 OBJECT-TYPE
		SYNTAX					 Counter32
		MAX-ACCESS			 read-only
		STATUS					 current
		DESCRIPTION			 " -- "
		::=  { dataPlanStatisticEntry  6 }


	pdcpRatioOfRUETable		 OBJECT-TYPE
		SYNTAX					 SEQUENCE  OF	 PdcpRatioOfRUEEntry
		MAX-ACCESS			 not-accessible
		STATUS					 current
		DESCRIPTION			 " -- "
		::=  { pdcprelatedOriginCounter  12 }


	pdcpRatioOfRUEEntry		 OBJECT-TYPE
		SYNTAX					 PdcpRatioOfRUEEntry
		MAX-ACCESS			 not-accessible
		STATUS					 current
		DESCRIPTION			 " -- "
		INDEX						{ pdcpRatioOfRUELcId }
		::=  { pdcpRatioOfRUETable  1 }


	PdcpRatioOfRUEEntry		 ::=  SEQUENCE {
		pdcpRatioOfRUELcId					Integer32,
		pdcpRatioOfRUERowStatus					RowStatus,
		ruePdcpSduBitLenDlQci251					Counter32,
		ruePdcpSduBitLenDlQci252					Counter32,
		ruePdcpSduBitLenDlQci253					Counter32,
		ruePdcpSduBitLenDlQci254					Counter32,
		ruePdcpSduBitLenUlQci251					Counter32,
		ruePdcpSduBitLenUlQci252					Counter32,
		ruePdcpSduBitLenUlQci253					Counter32,
		ruePdcpSduBitLenUlQci254					Counter32
		}


	pdcpRatioOfRUELcId		 OBJECT-TYPE
		SYNTAX					 Integer32( 0 .. 23 )
		MAX-ACCESS			 not-accessible
		STATUS					 current
		DESCRIPTION			 " -- "
		::=  { pdcpRatioOfRUEEntry  1 }


	pdcpRatioOfRUERowStatus		 OBJECT-TYPE
		SYNTAX					 RowStatus
		MAX-ACCESS			 read-only
		STATUS					 current
		DESCRIPTION			 " -- "
		::=  { pdcpRatioOfRUEEntry  2 }


	ruePdcpSduBitLenDlQci251		 OBJECT-TYPE
		SYNTAX					 Counter32
		MAX-ACCESS			 read-only
		STATUS					 current
		DESCRIPTION			 " -- "
		::=  { pdcpRatioOfRUEEntry  3 }


	ruePdcpSduBitLenDlQci252		 OBJECT-TYPE
		SYNTAX					 Counter32
		MAX-ACCESS			 read-only
		STATUS					 current
		DESCRIPTION			 " -- "
		::=  { pdcpRatioOfRUEEntry  4 }


	ruePdcpSduBitLenDlQci253		 OBJECT-TYPE
		SYNTAX					 Counter32
		MAX-ACCESS			 read-only
		STATUS					 current
		DESCRIPTION			 " -- "
		::=  { pdcpRatioOfRUEEntry  5 }


	ruePdcpSduBitLenDlQci254		 OBJECT-TYPE
		SYNTAX					 Counter32
		MAX-ACCESS			 read-only
		STATUS					 current
		DESCRIPTION			 " -- "
		::=  { pdcpRatioOfRUEEntry  6 }


	ruePdcpSduBitLenUlQci251		 OBJECT-TYPE
		SYNTAX					 Counter32
		MAX-ACCESS			 read-only
		STATUS					 current
		DESCRIPTION			 " -- "
		::=  { pdcpRatioOfRUEEntry  7 }


	ruePdcpSduBitLenUlQci252		 OBJECT-TYPE
		SYNTAX					 Counter32
		MAX-ACCESS			 read-only
		STATUS					 current
		DESCRIPTION			 " -- "
		::=  { pdcpRatioOfRUEEntry  8 }


	ruePdcpSduBitLenUlQci253		 OBJECT-TYPE
		SYNTAX					 Counter32
		MAX-ACCESS			 read-only
		STATUS					 current
		DESCRIPTION			 " -- "
		::=  { pdcpRatioOfRUEEntry  9 }


	ruePdcpSduBitLenUlQci254		 OBJECT-TYPE
		SYNTAX					 Counter32
		MAX-ACCESS			 read-only
		STATUS					 current
		DESCRIPTION			 " -- "
		::=  { pdcpRatioOfRUEEntry  10 }


	pdcpPresetPerformanceTable		 OBJECT-TYPE
		SYNTAX					 SEQUENCE  OF	 PdcpPresetPerformanceEntry
		MAX-ACCESS			 not-accessible
		STATUS					 current
		DESCRIPTION			 " -- "
		::=  { pdcprelatedOriginCounter  13 }


	pdcpPresetPerformanceEntry		 OBJECT-TYPE
		SYNTAX					 PdcpPresetPerformanceEntry
		MAX-ACCESS			 not-accessible
		STATUS					 current
		DESCRIPTION			 " -- "
		INDEX						{ pdcpPresetPerformanceLcId }
		::=  { pdcpPresetPerformanceTable  1 }


	PdcpPresetPerformanceEntry		 ::=  SEQUENCE {
		pdcpPresetPerformanceLcId					Integer32,
		pdcpPresetPerformanceRowStatus					RowStatus,
		pdcpPreset1					Counter32,
		pdcpPreset2					Counter32,
		pdcpPreset3					Counter32,
		pdcpPreset4					Counter32,
		pdcpPreset5					Counter32,
		pdcpPreset6					Counter32,
		pdcpPreset7					Counter32,
		pdcpPreset8					Counter32,
		pdcpPreset9					Counter32,
		pdcpPreset10					Counter32,
		pdcpPreset11					Counter32,
		pdcpPreset12					Counter32,
		pdcpPreset13					Counter32,
		pdcpPreset14					Counter32,
		pdcpPreset15					Counter32,
		pdcpPreset16					Counter32,
		pdcpPreset17					Counter32,
		pdcpPreset18					Counter32,
		pdcpPreset19					Counter32,
		pdcpPreset20					Counter32,
		pdcpPreset21					Counter32,
		pdcpPreset22					Counter32,
		pdcpPreset23					Counter32,
		pdcpPreset24					Counter32,
		pdcpPreset25					Counter32,
		pdcpPreset26					Counter32,
		pdcpPreset27					Counter32,
		pdcpPreset28					Counter32,
		pdcpPreset29					Counter32,
		pdcpPreset30					Counter32,
		pdcpPreset31					Counter32,
		pdcpPreset32					Counter32,
		pdcpPreset33					Counter32,
		pdcpPreset34					Counter32,
		pdcpPreset35					Counter32,
		pdcpPreset36					Counter32,
		pdcpPreset37					Counter32,
		pdcpPreset38					Counter32,
		pdcpPreset39					Counter32,
		pdcpPreset40					Counter32
		}


	pdcpPresetPerformanceLcId		 OBJECT-TYPE
		SYNTAX					 Integer32( 0 .. 23 )
		MAX-ACCESS			 not-accessible
		STATUS					 current
		DESCRIPTION			 " -- "
		::=  { pdcpPresetPerformanceEntry  1 }


	pdcpPresetPerformanceRowStatus		 OBJECT-TYPE
		SYNTAX					 RowStatus
		MAX-ACCESS			 read-only
		STATUS					 current
		DESCRIPTION			 " -- "
		::=  { pdcpPresetPerformanceEntry  2 }


	pdcpPreset1		 OBJECT-TYPE
		SYNTAX					 Counter32
		MAX-ACCESS			 read-only
		STATUS					 current
		DESCRIPTION			 " -- "
		::=  { pdcpPresetPerformanceEntry  3 }


	pdcpPreset2		 OBJECT-TYPE
		SYNTAX					 Counter32
		MAX-ACCESS			 read-only
		STATUS					 current
		DESCRIPTION			 " -- "
		::=  { pdcpPresetPerformanceEntry  4 }


	pdcpPreset3		 OBJECT-TYPE
		SYNTAX					 Counter32
		MAX-ACCESS			 read-only
		STATUS					 current
		DESCRIPTION			 " -- "
		::=  { pdcpPresetPerformanceEntry  5 }


	pdcpPreset4		 OBJECT-TYPE
		SYNTAX					 Counter32
		MAX-ACCESS			 read-only
		STATUS					 current
		DESCRIPTION			 " -- "
		::=  { pdcpPresetPerformanceEntry  6 }


	pdcpPreset5		 OBJECT-TYPE
		SYNTAX					 Counter32
		MAX-ACCESS			 read-only
		STATUS					 current
		DESCRIPTION			 " -- "
		::=  { pdcpPresetPerformanceEntry  7 }


	pdcpPreset6		 OBJECT-TYPE
		SYNTAX					 Counter32
		MAX-ACCESS			 read-only
		STATUS					 current
		DESCRIPTION			 " -- "
		::=  { pdcpPresetPerformanceEntry  8 }


	pdcpPreset7		 OBJECT-TYPE
		SYNTAX					 Counter32
		MAX-ACCESS			 read-only
		STATUS					 current
		DESCRIPTION			 " -- "
		::=  { pdcpPresetPerformanceEntry  9 }


	pdcpPreset8		 OBJECT-TYPE
		SYNTAX					 Counter32
		MAX-ACCESS			 read-only
		STATUS					 current
		DESCRIPTION			 " -- "
		::=  { pdcpPresetPerformanceEntry  10 }


	pdcpPreset9		 OBJECT-TYPE
		SYNTAX					 Counter32
		MAX-ACCESS			 read-only
		STATUS					 current
		DESCRIPTION			 " -- "
		::=  { pdcpPresetPerformanceEntry  11 }


	pdcpPreset10		 OBJECT-TYPE
		SYNTAX					 Counter32
		MAX-ACCESS			 read-only
		STATUS					 current
		DESCRIPTION			 " -- "
		::=  { pdcpPresetPerformanceEntry  12 }


	pdcpPreset11		 OBJECT-TYPE
		SYNTAX					 Counter32
		MAX-ACCESS			 read-only
		STATUS					 current
		DESCRIPTION			 " -- "
		::=  { pdcpPresetPerformanceEntry  13 }


	pdcpPreset12		 OBJECT-TYPE
		SYNTAX					 Counter32
		MAX-ACCESS			 read-only
		STATUS					 current
		DESCRIPTION			 " -- "
		::=  { pdcpPresetPerformanceEntry  14 }


	pdcpPreset13		 OBJECT-TYPE
		SYNTAX					 Counter32
		MAX-ACCESS			 read-only
		STATUS					 current
		DESCRIPTION			 " -- "
		::=  { pdcpPresetPerformanceEntry  15 }


	pdcpPreset14		 OBJECT-TYPE
		SYNTAX					 Counter32
		MAX-ACCESS			 read-only
		STATUS					 current
		DESCRIPTION			 " -- "
		::=  { pdcpPresetPerformanceEntry  16 }


	pdcpPreset15		 OBJECT-TYPE
		SYNTAX					 Counter32
		MAX-ACCESS			 read-only
		STATUS					 current
		DESCRIPTION			 " -- "
		::=  { pdcpPresetPerformanceEntry  17 }


	pdcpPreset16		 OBJECT-TYPE
		SYNTAX					 Counter32
		MAX-ACCESS			 read-only
		STATUS					 current
		DESCRIPTION			 " -- "
		::=  { pdcpPresetPerformanceEntry  18 }


	pdcpPreset17		 OBJECT-TYPE
		SYNTAX					 Counter32
		MAX-ACCESS			 read-only
		STATUS					 current
		DESCRIPTION			 " -- "
		::=  { pdcpPresetPerformanceEntry  19 }


	pdcpPreset18		 OBJECT-TYPE
		SYNTAX					 Counter32
		MAX-ACCESS			 read-only
		STATUS					 current
		DESCRIPTION			 " -- "
		::=  { pdcpPresetPerformanceEntry  20 }


	pdcpPreset19		 OBJECT-TYPE
		SYNTAX					 Counter32
		MAX-ACCESS			 read-only
		STATUS					 current
		DESCRIPTION			 " -- "
		::=  { pdcpPresetPerformanceEntry  21 }


	pdcpPreset20		 OBJECT-TYPE
		SYNTAX					 Counter32
		MAX-ACCESS			 read-only
		STATUS					 current
		DESCRIPTION			 " -- "
		::=  { pdcpPresetPerformanceEntry  22 }


	pdcpPreset21		 OBJECT-TYPE
		SYNTAX					 Counter32
		MAX-ACCESS			 read-only
		STATUS					 current
		DESCRIPTION			 " -- "
		::=  { pdcpPresetPerformanceEntry  23 }


	pdcpPreset22		 OBJECT-TYPE
		SYNTAX					 Counter32
		MAX-ACCESS			 read-only
		STATUS					 current
		DESCRIPTION			 " -- "
		::=  { pdcpPresetPerformanceEntry  24 }


	pdcpPreset23		 OBJECT-TYPE
		SYNTAX					 Counter32
		MAX-ACCESS			 read-only
		STATUS					 current
		DESCRIPTION			 " -- "
		::=  { pdcpPresetPerformanceEntry  25 }


	pdcpPreset24		 OBJECT-TYPE
		SYNTAX					 Counter32
		MAX-ACCESS			 read-only
		STATUS					 current
		DESCRIPTION			 " -- "
		::=  { pdcpPresetPerformanceEntry  26 }


	pdcpPreset25		 OBJECT-TYPE
		SYNTAX					 Counter32
		MAX-ACCESS			 read-only
		STATUS					 current
		DESCRIPTION			 " -- "
		::=  { pdcpPresetPerformanceEntry  27 }


	pdcpPreset26		 OBJECT-TYPE
		SYNTAX					 Counter32
		MAX-ACCESS			 read-only
		STATUS					 current
		DESCRIPTION			 " -- "
		::=  { pdcpPresetPerformanceEntry  28 }


	pdcpPreset27		 OBJECT-TYPE
		SYNTAX					 Counter32
		MAX-ACCESS			 read-only
		STATUS					 current
		DESCRIPTION			 " -- "
		::=  { pdcpPresetPerformanceEntry  29 }


	pdcpPreset28		 OBJECT-TYPE
		SYNTAX					 Counter32
		MAX-ACCESS			 read-only
		STATUS					 current
		DESCRIPTION			 " -- "
		::=  { pdcpPresetPerformanceEntry  30 }


	pdcpPreset29		 OBJECT-TYPE
		SYNTAX					 Counter32
		MAX-ACCESS			 read-only
		STATUS					 current
		DESCRIPTION			 " -- "
		::=  { pdcpPresetPerformanceEntry  31 }


	pdcpPreset30		 OBJECT-TYPE
		SYNTAX					 Counter32
		MAX-ACCESS			 read-only
		STATUS					 current
		DESCRIPTION			 " -- "
		::=  { pdcpPresetPerformanceEntry  32 }


	pdcpPreset31		 OBJECT-TYPE
		SYNTAX					 Counter32
		MAX-ACCESS			 read-only
		STATUS					 current
		DESCRIPTION			 " -- "
		::=  { pdcpPresetPerformanceEntry  33 }


	pdcpPreset32		 OBJECT-TYPE
		SYNTAX					 Counter32
		MAX-ACCESS			 read-only
		STATUS					 current
		DESCRIPTION			 " -- "
		::=  { pdcpPresetPerformanceEntry  34 }


	pdcpPreset33		 OBJECT-TYPE
		SYNTAX					 Counter32
		MAX-ACCESS			 read-only
		STATUS					 current
		DESCRIPTION			 " -- "
		::=  { pdcpPresetPerformanceEntry  35 }


	pdcpPreset34		 OBJECT-TYPE
		SYNTAX					 Counter32
		MAX-ACCESS			 read-only
		STATUS					 current
		DESCRIPTION			 " -- "
		::=  { pdcpPresetPerformanceEntry  36 }


	pdcpPreset35		 OBJECT-TYPE
		SYNTAX					 Counter32
		MAX-ACCESS			 read-only
		STATUS					 current
		DESCRIPTION			 " -- "
		::=  { pdcpPresetPerformanceEntry  37 }


	pdcpPreset36		 OBJECT-TYPE
		SYNTAX					 Counter32
		MAX-ACCESS			 read-only
		STATUS					 current
		DESCRIPTION			 " -- "
		::=  { pdcpPresetPerformanceEntry  38 }


	pdcpPreset37		 OBJECT-TYPE
		SYNTAX					 Counter32
		MAX-ACCESS			 read-only
		STATUS					 current
		DESCRIPTION			 " -- "
		::=  { pdcpPresetPerformanceEntry  39 }


	pdcpPreset38		 OBJECT-TYPE
		SYNTAX					 Counter32
		MAX-ACCESS			 read-only
		STATUS					 current
		DESCRIPTION			 " -- "
		::=  { pdcpPresetPerformanceEntry  40 }


	pdcpPreset39		 OBJECT-TYPE
		SYNTAX					 Counter32
		MAX-ACCESS			 read-only
		STATUS					 current
		DESCRIPTION			 " -- "
		::=  { pdcpPresetPerformanceEntry  41 }


	pdcpPreset40		 OBJECT-TYPE
		SYNTAX					 Counter32
		MAX-ACCESS			 read-only
		STATUS					 current
		DESCRIPTION			 " -- "
		::=  { pdcpPresetPerformanceEntry  42 }


	videoPerfOfPdcpTable		 OBJECT-TYPE
		SYNTAX					 SEQUENCE  OF	 VideoPerfOfPdcpEntry
		MAX-ACCESS			 not-accessible
		STATUS					 current
		DESCRIPTION			 " -- "
		::=  { pdcprelatedOriginCounter  14 }


	videoPerfOfPdcpEntry		 OBJECT-TYPE
		SYNTAX					 VideoPerfOfPdcpEntry
		MAX-ACCESS			 not-accessible
		STATUS					 current
		DESCRIPTION			 " -- "
		INDEX						{ videoPerfOfPdcpLcId }
		::=  { videoPerfOfPdcpTable  1 }


	VideoPerfOfPdcpEntry		 ::=  SEQUENCE {
		videoPerfOfPdcpLcId					Integer32,
		videoPerfOfPdcpRowStatus					RowStatus,
		pdcpUlPakChaRecogSuc					Counter32,
		pdcpVideoRecogSucMax					Counter32,
		pdcpVideoRecogSucAvg					Counter32,
		pdcpVideoThroughput					Counter32,
		pdcpVideoMatchTencent					Counter32,
		pdcpVideoMatchIqiyi					Counter32,
		pdcpVideoMatchYouku					Counter32,
		pdcpVideoMatchLetv					Counter32,
		pdcpVideoMatchMigu					Counter32,
		pdcpVideoMatchKuaiShou					Counter32,
		pdcpVideoMatchMgtv					Counter32,
		pdcpVideoPreset1					Counter32,
		pdcpVideoPreset2					Counter32,
		pdcpVideoPreset3					Counter32,
		pdcpVideoPreset4					Counter32,
		pdcpVideoPreset5					Counter32,
		pdcpVideoPreset6					Counter32,
		pdcpVideoPreset7					Counter32,
		pdcpVideoPreset8					Counter32,
		pdcpVideoPreset9					Counter32,
		pdcpVideoPreset10					Counter32
		}


	videoPerfOfPdcpLcId		 OBJECT-TYPE
		SYNTAX					 Integer32( 0 .. 23 )
		MAX-ACCESS			 not-accessible
		STATUS					 current
		DESCRIPTION			 " -- "
		::=  { videoPerfOfPdcpEntry  1 }


	videoPerfOfPdcpRowStatus		 OBJECT-TYPE
		SYNTAX					 RowStatus
		MAX-ACCESS			 read-only
		STATUS					 current
		DESCRIPTION			 " -- "
		::=  { videoPerfOfPdcpEntry  2 }


	pdcpUlPakChaRecogSuc		 OBJECT-TYPE
		SYNTAX					 Counter32
		MAX-ACCESS			 read-only
		STATUS					 current
		DESCRIPTION			 " -- "
		::=  { videoPerfOfPdcpEntry  3 }


	pdcpVideoRecogSucMax		 OBJECT-TYPE
		SYNTAX					 Counter32
		MAX-ACCESS			 read-only
		STATUS					 current
		DESCRIPTION			 " -- "
		::=  { videoPerfOfPdcpEntry  4 }


	pdcpVideoRecogSucAvg		 OBJECT-TYPE
		SYNTAX					 Counter32
		MAX-ACCESS			 read-only
		STATUS					 current
		DESCRIPTION			 " -- "
		::=  { videoPerfOfPdcpEntry  5 }


	pdcpVideoThroughput		 OBJECT-TYPE
		SYNTAX					 Counter32
		MAX-ACCESS			 read-only
		STATUS					 current
		DESCRIPTION			 " -- "
		::=  { videoPerfOfPdcpEntry  6 }


	pdcpVideoMatchTencent		 OBJECT-TYPE
		SYNTAX					 Counter32
		MAX-ACCESS			 read-only
		STATUS					 current
		DESCRIPTION			 " -- "
		::=  { videoPerfOfPdcpEntry  7 }


	pdcpVideoMatchIqiyi		 OBJECT-TYPE
		SYNTAX					 Counter32
		MAX-ACCESS			 read-only
		STATUS					 current
		DESCRIPTION			 " -- "
		::=  { videoPerfOfPdcpEntry  8 }


	pdcpVideoMatchYouku		 OBJECT-TYPE
		SYNTAX					 Counter32
		MAX-ACCESS			 read-only
		STATUS					 current
		DESCRIPTION			 " -- "
		::=  { videoPerfOfPdcpEntry  9 }


	pdcpVideoMatchLetv		 OBJECT-TYPE
		SYNTAX					 Counter32
		MAX-ACCESS			 read-only
		STATUS					 current
		DESCRIPTION			 " -- "
		::=  { videoPerfOfPdcpEntry  10 }


	pdcpVideoMatchMigu		 OBJECT-TYPE
		SYNTAX					 Counter32
		MAX-ACCESS			 read-only
		STATUS					 current
		DESCRIPTION			 " -- "
		::=  { videoPerfOfPdcpEntry  11 }


	pdcpVideoMatchKuaiShou		 OBJECT-TYPE
		SYNTAX					 Counter32
		MAX-ACCESS			 read-only
		STATUS					 current
		DESCRIPTION			 " -- "
		::=  { videoPerfOfPdcpEntry  12 }


	pdcpVideoMatchMgtv		 OBJECT-TYPE
		SYNTAX					 Counter32
		MAX-ACCESS			 read-only
		STATUS					 current
		DESCRIPTION			 " -- "
		::=  { videoPerfOfPdcpEntry  13 }


	pdcpVideoPreset1		 OBJECT-TYPE
		SYNTAX					 Counter32
		MAX-ACCESS			 read-only
		STATUS					 current
		DESCRIPTION			 " -- "
		::=  { videoPerfOfPdcpEntry  14 }


	pdcpVideoPreset2		 OBJECT-TYPE
		SYNTAX					 Counter32
		MAX-ACCESS			 read-only
		STATUS					 current
		DESCRIPTION			 " -- "
		::=  { videoPerfOfPdcpEntry  15 }


	pdcpVideoPreset3		 OBJECT-TYPE
		SYNTAX					 Counter32
		MAX-ACCESS			 read-only
		STATUS					 current
		DESCRIPTION			 " -- "
		::=  { videoPerfOfPdcpEntry  16 }


	pdcpVideoPreset4		 OBJECT-TYPE
		SYNTAX					 Counter32
		MAX-ACCESS			 read-only
		STATUS					 current
		DESCRIPTION			 " -- "
		::=  { videoPerfOfPdcpEntry  17 }


	pdcpVideoPreset5		 OBJECT-TYPE
		SYNTAX					 Counter32
		MAX-ACCESS			 read-only
		STATUS					 current
		DESCRIPTION			 " -- "
		::=  { videoPerfOfPdcpEntry  18 }


	pdcpVideoPreset6		 OBJECT-TYPE
		SYNTAX					 Counter32
		MAX-ACCESS			 read-only
		STATUS					 current
		DESCRIPTION			 " -- "
		::=  { videoPerfOfPdcpEntry  19 }


	pdcpVideoPreset7		 OBJECT-TYPE
		SYNTAX					 Counter32
		MAX-ACCESS			 read-only
		STATUS					 current
		DESCRIPTION			 " -- "
		::=  { videoPerfOfPdcpEntry  20 }


	pdcpVideoPreset8		 OBJECT-TYPE
		SYNTAX					 Counter32
		MAX-ACCESS			 read-only
		STATUS					 current
		DESCRIPTION			 " -- "
		::=  { videoPerfOfPdcpEntry  21 }


	pdcpVideoPreset9		 OBJECT-TYPE
		SYNTAX					 Counter32
		MAX-ACCESS			 read-only
		STATUS					 current
		DESCRIPTION			 " -- "
		::=  { videoPerfOfPdcpEntry  22 }


	pdcpVideoPreset10		 OBJECT-TYPE
		SYNTAX					 Counter32
		MAX-ACCESS			 read-only
		STATUS					 current
		DESCRIPTION			 " -- "
		::=  { videoPerfOfPdcpEntry  23 }


	plrelatedOriginCounter		 OBJECT IDENTIFIER
		::=  { pmOriginCounterGrpInfo  5 }


	plPreambeRevNumTable		 OBJECT-TYPE
		SYNTAX					 SEQUENCE  OF	 PlPreambeRevNumEntry
		MAX-ACCESS			 not-accessible
		STATUS					 current
		DESCRIPTION			 " -- "
		::=  { plrelatedOriginCounter  1 }


	plPreambeRevNumEntry		 OBJECT-TYPE
		SYNTAX					 PlPreambeRevNumEntry
		MAX-ACCESS			 not-accessible
		STATUS					 current
		DESCRIPTION			 " -- "
		INDEX						{ plPreambeRevNumLcId }
		::=  { plPreambeRevNumTable  1 }


	PlPreambeRevNumEntry		 ::=  SEQUENCE {
		plPreambeRevNumLcId					Integer32,
		plPreambeRevNumRowStatus					RowStatus,
		rruPreambleDTotal					Counter32,
		rruPreambleATotal					Counter32,
		rruPreambleBTotal					Counter32,
		rruPreambleContentionTimesGroupA					Counter32,
		rruPreambleContentionTimesGroupB					Counter32
		}


	plPreambeRevNumLcId		 OBJECT-TYPE
		SYNTAX					 Integer32( 0 .. 23 )
		MAX-ACCESS			 not-accessible
		STATUS					 current
		DESCRIPTION			 " -- "
		::=  { plPreambeRevNumEntry  1 }


	plPreambeRevNumRowStatus		 OBJECT-TYPE
		SYNTAX					 RowStatus
		MAX-ACCESS			 read-only
		STATUS					 current
		DESCRIPTION			 " -- "
		::=  { plPreambeRevNumEntry  2 }


	rruPreambleDTotal		 OBJECT-TYPE
		SYNTAX					 Counter32
		MAX-ACCESS			 read-only
		STATUS					 current
		DESCRIPTION			 " -- "
		::=  { plPreambeRevNumEntry  3 }


	rruPreambleATotal		 OBJECT-TYPE
		SYNTAX					 Counter32
		MAX-ACCESS			 read-only
		STATUS					 current
		DESCRIPTION			 " -- "
		::=  { plPreambeRevNumEntry  4 }


	rruPreambleBTotal		 OBJECT-TYPE
		SYNTAX					 Counter32
		MAX-ACCESS			 read-only
		STATUS					 current
		DESCRIPTION			 " -- "
		::=  { plPreambeRevNumEntry  5 }


	rruPreambleContentionTimesGroupA		 OBJECT-TYPE
		SYNTAX					 Counter32
		MAX-ACCESS			 read-only
		STATUS					 current
		DESCRIPTION			 " -- "
		::=  { plPreambeRevNumEntry  6 }


	rruPreambleContentionTimesGroupB		 OBJECT-TYPE
		SYNTAX					 Counter32
		MAX-ACCESS			 read-only
		STATUS					 current
		DESCRIPTION			 " -- "
		::=  { plPreambeRevNumEntry  7 }


	plrssiTable		 OBJECT-TYPE
		SYNTAX					 SEQUENCE  OF	 PlrssiEntry
		MAX-ACCESS			 not-accessible
		STATUS					 current
		DESCRIPTION			 " -- "
		::=  { plrelatedOriginCounter  2 }


	plrssiEntry		 OBJECT-TYPE
		SYNTAX					 PlrssiEntry
		MAX-ACCESS			 not-accessible
		STATUS					 current
		DESCRIPTION			 " -- "
		INDEX						{ plrssiLcId }
		::=  { plrssiTable  1 }


	PlrssiEntry		 ::=  SEQUENCE {
		plrssiLcId					Integer32,
		plrssiRowStatus					RowStatus,
		plReceivePowerMax					Integer32,
		plReceivePowerMin					Integer32,
		plReceivePowerAvg					Integer32,
		plRssiAvgC1					Integer32,
		plRssiAvgC2					Integer32,
		plRssiAvgC3					Integer32,
		plRssiAvgC4					Integer32,
		plRssiAvgC5					Integer32,
		plRssiAvgC6					Integer32,
		plRssiAvgC7					Integer32,
		plRssiAvgC8					Integer32,
		plRssiAvgC9					Integer32,
		plRssiAvgC10					Integer32,
		plRssiAvgC11					Integer32,
		plRssiAvgC12					Integer32,
		plRssiAvgC13					Integer32,
		plRssiAvgC14					Integer32,
		plRssiAvgC15					Integer32,
		plRssiAvgC16					Integer32,
		plRssiAvgC17					Integer32,
		plRssiAvgC18					Integer32,
		plRssiAvgC19					Integer32,
		plRssiAvgC20					Integer32,
		plRssiAvgC21					Integer32,
		plRssiAvgC22					Integer32,
		plRssiAvgC23					Integer32,
		plRssiAvgC24					Integer32
		}


	plrssiLcId		 OBJECT-TYPE
		SYNTAX					 Integer32( 0 .. 23 )
		MAX-ACCESS			 not-accessible
		STATUS					 current
		DESCRIPTION			 " -- "
		::=  { plrssiEntry  1 }


	plrssiRowStatus		 OBJECT-TYPE
		SYNTAX					 RowStatus
		MAX-ACCESS			 read-only
		STATUS					 current
		DESCRIPTION			 " -- "
		::=  { plrssiEntry  2 }


	plReceivePowerMax		 OBJECT-TYPE
		SYNTAX					 Integer32( -2147483648 .. 2147483647 )
		MAX-ACCESS			 read-only
		STATUS					 current
		DESCRIPTION			 " -- "
		::=  { plrssiEntry  3 }


	plReceivePowerMin		 OBJECT-TYPE
		SYNTAX					 Integer32( -2147483648 .. 2147483647 )
		MAX-ACCESS			 read-only
		STATUS					 current
		DESCRIPTION			 " -- "
		::=  { plrssiEntry  4 }


	plReceivePowerAvg		 OBJECT-TYPE
		SYNTAX					 Integer32( -2147483648 .. 2147483647 )
		MAX-ACCESS			 read-only
		STATUS					 current
		DESCRIPTION			 " -- "
		::=  { plrssiEntry  5 }


	plRssiAvgC1		 OBJECT-TYPE
		SYNTAX					 Integer32( -2147483648 .. 2147483647 )
		MAX-ACCESS			 read-only
		STATUS					 current
		DESCRIPTION			 " -- "
		::=  { plrssiEntry  6 }


	plRssiAvgC2		 OBJECT-TYPE
		SYNTAX					 Integer32( -2147483648 .. 2147483647 )
		MAX-ACCESS			 read-only
		STATUS					 current
		DESCRIPTION			 " -- "
		::=  { plrssiEntry  7 }


	plRssiAvgC3		 OBJECT-TYPE
		SYNTAX					 Integer32( -2147483648 .. 2147483647 )
		MAX-ACCESS			 read-only
		STATUS					 current
		DESCRIPTION			 " -- "
		::=  { plrssiEntry  8 }


	plRssiAvgC4		 OBJECT-TYPE
		SYNTAX					 Integer32( -2147483648 .. 2147483647 )
		MAX-ACCESS			 read-only
		STATUS					 current
		DESCRIPTION			 " -- "
		::=  { plrssiEntry  9 }


	plRssiAvgC5		 OBJECT-TYPE
		SYNTAX					 Integer32( -2147483648 .. 2147483647 )
		MAX-ACCESS			 read-only
		STATUS					 current
		DESCRIPTION			 " -- "
		::=  { plrssiEntry  10 }


	plRssiAvgC6		 OBJECT-TYPE
		SYNTAX					 Integer32( -2147483648 .. 2147483647 )
		MAX-ACCESS			 read-only
		STATUS					 current
		DESCRIPTION			 " -- "
		::=  { plrssiEntry  11 }


	plRssiAvgC7		 OBJECT-TYPE
		SYNTAX					 Integer32( -2147483648 .. 2147483647 )
		MAX-ACCESS			 read-only
		STATUS					 current
		DESCRIPTION			 " -- "
		::=  { plrssiEntry  12 }


	plRssiAvgC8		 OBJECT-TYPE
		SYNTAX					 Integer32( -2147483648 .. 2147483647 )
		MAX-ACCESS			 read-only
		STATUS					 current
		DESCRIPTION			 " -- "
		::=  { plrssiEntry  13 }


	plRssiAvgC9		 OBJECT-TYPE
		SYNTAX					 Integer32( -2147483648 .. 2147483647 )
		MAX-ACCESS			 read-only
		STATUS					 current
		DESCRIPTION			 " -- "
		::=  { plrssiEntry  14 }


	plRssiAvgC10		 OBJECT-TYPE
		SYNTAX					 Integer32( -2147483648 .. 2147483647 )
		MAX-ACCESS			 read-only
		STATUS					 current
		DESCRIPTION			 " -- "
		::=  { plrssiEntry  15 }


	plRssiAvgC11		 OBJECT-TYPE
		SYNTAX					 Integer32( -2147483648 .. 2147483647 )
		MAX-ACCESS			 read-only
		STATUS					 current
		DESCRIPTION			 " -- "
		::=  { plrssiEntry  16 }


	plRssiAvgC12		 OBJECT-TYPE
		SYNTAX					 Integer32( -2147483648 .. 2147483647 )
		MAX-ACCESS			 read-only
		STATUS					 current
		DESCRIPTION			 " -- "
		::=  { plrssiEntry  17 }


	plRssiAvgC13		 OBJECT-TYPE
		SYNTAX					 Integer32( -2147483648 .. 2147483647 )
		MAX-ACCESS			 read-only
		STATUS					 current
		DESCRIPTION			 " -- "
		::=  { plrssiEntry  18 }


	plRssiAvgC14		 OBJECT-TYPE
		SYNTAX					 Integer32( -2147483648 .. 2147483647 )
		MAX-ACCESS			 read-only
		STATUS					 current
		DESCRIPTION			 " -- "
		::=  { plrssiEntry  19 }


	plRssiAvgC15		 OBJECT-TYPE
		SYNTAX					 Integer32( -2147483648 .. 2147483647 )
		MAX-ACCESS			 read-only
		STATUS					 current
		DESCRIPTION			 " -- "
		::=  { plrssiEntry  20 }


	plRssiAvgC16		 OBJECT-TYPE
		SYNTAX					 Integer32( -2147483648 .. 2147483647 )
		MAX-ACCESS			 read-only
		STATUS					 current
		DESCRIPTION			 " -- "
		::=  { plrssiEntry  21 }


	plRssiAvgC17		 OBJECT-TYPE
		SYNTAX					 Integer32( -2147483648 .. 2147483647 )
		MAX-ACCESS			 read-only
		STATUS					 current
		DESCRIPTION			 " -- "
		::=  { plrssiEntry  22 }


	plRssiAvgC18		 OBJECT-TYPE
		SYNTAX					 Integer32( -2147483648 .. 2147483647 )
		MAX-ACCESS			 read-only
		STATUS					 current
		DESCRIPTION			 " -- "
		::=  { plrssiEntry  23 }


	plRssiAvgC19		 OBJECT-TYPE
		SYNTAX					 Integer32( -2147483648 .. 2147483647 )
		MAX-ACCESS			 read-only
		STATUS					 current
		DESCRIPTION			 " -- "
		::=  { plrssiEntry  24 }


	plRssiAvgC20		 OBJECT-TYPE
		SYNTAX					 Integer32( -2147483648 .. 2147483647 )
		MAX-ACCESS			 read-only
		STATUS					 current
		DESCRIPTION			 " -- "
		::=  { plrssiEntry  25 }


	plRssiAvgC21		 OBJECT-TYPE
		SYNTAX					 Integer32( -2147483648 .. 2147483647 )
		MAX-ACCESS			 read-only
		STATUS					 current
		DESCRIPTION			 " -- "
		::=  { plrssiEntry  26 }


	plRssiAvgC22		 OBJECT-TYPE
		SYNTAX					 Integer32( -2147483648 .. 2147483647 )
		MAX-ACCESS			 read-only
		STATUS					 current
		DESCRIPTION			 " -- "
		::=  { plrssiEntry  27 }


	plRssiAvgC23		 OBJECT-TYPE
		SYNTAX					 Integer32( -2147483648 .. 2147483647 )
		MAX-ACCESS			 read-only
		STATUS					 current
		DESCRIPTION			 " -- "
		::=  { plrssiEntry  28 }


	plRssiAvgC24		 OBJECT-TYPE
		SYNTAX					 Integer32( -2147483648 .. 2147483647 )
		MAX-ACCESS			 read-only
		STATUS					 current
		DESCRIPTION			 " -- "
		::=  { plrssiEntry  29 }


	plPreamblePwrTable		 OBJECT-TYPE
		SYNTAX					 SEQUENCE  OF	 PlPreamblePwrEntry
		MAX-ACCESS			 not-accessible
		STATUS					 current
		DESCRIPTION			 " -- "
		::=  { plrelatedOriginCounter  3 }


	plPreamblePwrEntry		 OBJECT-TYPE
		SYNTAX					 PlPreamblePwrEntry
		MAX-ACCESS			 not-accessible
		STATUS					 current
		DESCRIPTION			 " -- "
		INDEX						{ plPreamblePwrLcId }
		::=  { plPreamblePwrTable  1 }


	PlPreamblePwrEntry		 ::=  SEQUENCE {
		plPreamblePwrLcId					Integer32,
		plPreamblePwrRowStatus					RowStatus,
		plPreamblePwrHighNum					Counter32,
		plPreamblePwrNormNum					Counter32
		}


	plPreamblePwrLcId		 OBJECT-TYPE
		SYNTAX					 Integer32( 0 .. 23 )
		MAX-ACCESS			 not-accessible
		STATUS					 current
		DESCRIPTION			 " -- "
		::=  { plPreamblePwrEntry  1 }


	plPreamblePwrRowStatus		 OBJECT-TYPE
		SYNTAX					 RowStatus
		MAX-ACCESS			 read-only
		STATUS					 current
		DESCRIPTION			 " -- "
		::=  { plPreamblePwrEntry  2 }


	plPreamblePwrHighNum		 OBJECT-TYPE
		SYNTAX					 Counter32
		MAX-ACCESS			 read-only
		STATUS					 current
		DESCRIPTION			 " -- "
		::=  { plPreamblePwrEntry  3 }


	plPreamblePwrNormNum		 OBJECT-TYPE
		SYNTAX					 Counter32
		MAX-ACCESS			 read-only
		STATUS					 current
		DESCRIPTION			 " -- "
		::=  { plPreamblePwrEntry  4 }


	sfn1avgripTable		 OBJECT-TYPE
		SYNTAX					 SEQUENCE  OF	 Sfn1avgripEntry
		MAX-ACCESS			 not-accessible
		STATUS					 current
		DESCRIPTION			 " -- "
		::=  { plrelatedOriginCounter  4 }


	sfn1avgripEntry		 OBJECT-TYPE
		SYNTAX					 Sfn1avgripEntry
		MAX-ACCESS			 not-accessible
		STATUS					 current
		DESCRIPTION			 " -- "
		INDEX						{ sfn1avgripLcId }
		::=  { sfn1avgripTable  1 }


	Sfn1avgripEntry		 ::=  SEQUENCE {
		sfn1avgripLcId					Integer32,
		sfn1avgripRowStatus					RowStatus,
		plsfn1Prb00RIPAvg					Integer32,
		plsfn1Prb01RIPAvg					Integer32,
		plsfn1Prb02RIPAvg					Integer32,
		plsfn1Prb03RIPAvg					Integer32,
		plsfn1Prb04RIPAvg					Integer32,
		plsfn1Prb05RIPAvg					Integer32,
		plsfn1Prb06RIPAvg					Integer32,
		plsfn1Prb07RIPAvg					Integer32,
		plsfn1Prb08RIPAvg					Integer32,
		plsfn1Prb09RIPAvg					Integer32,
		plsfn1Prb10RIPAvg					Integer32,
		plsfn1Prb11RIPAvg					Integer32,
		plsfn1Prb12RIPAvg					Integer32,
		plsfn1Prb13RIPAvg					Integer32,
		plsfn1Prb14RIPAvg					Integer32,
		plsfn1Prb15RIPAvg					Integer32,
		plsfn1Prb16RIPAvg					Integer32,
		plsfn1Prb17RIPAvg					Integer32,
		plsfn1Prb18RIPAvg					Integer32,
		plsfn1Prb19RIPAvg					Integer32,
		plsfn1Prb20RIPAvg					Integer32,
		plsfn1Prb21RIPAvg					Integer32,
		plsfn1Prb22RIPAvg					Integer32,
		plsfn1Prb23RIPAvg					Integer32,
		plsfn1Prb24RIPAvg					Integer32,
		plsfn1Prb25RIPAvg					Integer32,
		plsfn1Prb26RIPAvg					Integer32,
		plsfn1Prb27RIPAvg					Integer32,
		plsfn1Prb28RIPAvg					Integer32,
		plsfn1Prb29RIPAvg					Integer32,
		plsfn1Prb30RIPAvg					Integer32,
		plsfn1Prb31RIPAvg					Integer32,
		plsfn1Prb32RIPAvg					Integer32,
		plsfn1Prb33RIPAvg					Integer32,
		plsfn1Prb34RIPAvg					Integer32,
		plsfn1Prb35RIPAvg					Integer32,
		plsfn1Prb36RIPAvg					Integer32,
		plsfn1Prb37RIPAvg					Integer32,
		plsfn1Prb38RIPAvg					Integer32,
		plsfn1Prb39RIPAvg					Integer32,
		plsfn1Prb40RIPAvg					Integer32,
		plsfn1Prb41RIPAvg					Integer32,
		plsfn1Prb42RIPAvg					Integer32,
		plsfn1Prb43RIPAvg					Integer32,
		plsfn1Prb44RIPAvg					Integer32,
		plsfn1Prb45RIPAvg					Integer32,
		plsfn1Prb46RIPAvg					Integer32,
		plsfn1Prb47RIPAvg					Integer32,
		plsfn1Prb48RIPAvg					Integer32,
		plsfn1Prb49RIPAvg					Integer32,
		plsfn1Prb50RIPAvg					Integer32,
		plsfn1Prb51RIPAvg					Integer32,
		plsfn1Prb52RIPAvg					Integer32,
		plsfn1Prb53RIPAvg					Integer32,
		plsfn1Prb54RIPAvg					Integer32,
		plsfn1Prb55RIPAvg					Integer32,
		plsfn1Prb56RIPAvg					Integer32,
		plsfn1Prb57RIPAvg					Integer32,
		plsfn1Prb58RIPAvg					Integer32,
		plsfn1Prb59RIPAvg					Integer32,
		plsfn1Prb60RIPAvg					Integer32,
		plsfn1Prb61RIPAvg					Integer32,
		plsfn1Prb62RIPAvg					Integer32,
		plsfn1Prb63RIPAvg					Integer32,
		plsfn1Prb64RIPAvg					Integer32,
		plsfn1Prb65RIPAvg					Integer32,
		plsfn1Prb66RIPAvg					Integer32,
		plsfn1Prb67RIPAvg					Integer32,
		plsfn1Prb68RIPAvg					Integer32,
		plsfn1Prb69RIPAvg					Integer32,
		plsfn1Prb70RIPAvg					Integer32,
		plsfn1Prb71RIPAvg					Integer32,
		plsfn1Prb72RIPAvg					Integer32,
		plsfn1Prb73RIPAvg					Integer32,
		plsfn1Prb74RIPAvg					Integer32,
		plsfn1Prb75RIPAvg					Integer32,
		plsfn1Prb76RIPAvg					Integer32,
		plsfn1Prb77RIPAvg					Integer32,
		plsfn1Prb78RIPAvg					Integer32,
		plsfn1Prb79RIPAvg					Integer32,
		plsfn1Prb80RIPAvg					Integer32,
		plsfn1Prb81RIPAvg					Integer32,
		plsfn1Prb82RIPAvg					Integer32,
		plsfn1Prb83RIPAvg					Integer32,
		plsfn1Prb84RIPAvg					Integer32,
		plsfn1Prb85RIPAvg					Integer32,
		plsfn1Prb86RIPAvg					Integer32,
		plsfn1Prb87RIPAvg					Integer32,
		plsfn1Prb88RIPAvg					Integer32,
		plsfn1Prb89RIPAvg					Integer32,
		plsfn1Prb90RIPAvg					Integer32,
		plsfn1Prb91RIPAvg					Integer32,
		plsfn1Prb92RIPAvg					Integer32,
		plsfn1Prb93RIPAvg					Integer32,
		plsfn1Prb94RIPAvg					Integer32,
		plsfn1Prb95RIPAvg					Integer32,
		plsfn1Prb96RIPAvg					Integer32,
		plsfn1Prb97RIPAvg					Integer32,
		plsfn1Prb98RIPAvg					Integer32,
		plsfn1Prb99RIPAvg					Integer32
		}


	sfn1avgripLcId		 OBJECT-TYPE
		SYNTAX					 Integer32( 0 .. 23 )
		MAX-ACCESS			 not-accessible
		STATUS					 current
		DESCRIPTION			 " -- "
		::=  { sfn1avgripEntry  1 }


	sfn1avgripRowStatus		 OBJECT-TYPE
		SYNTAX					 RowStatus
		MAX-ACCESS			 read-only
		STATUS					 current
		DESCRIPTION			 " -- "
		::=  { sfn1avgripEntry  2 }


	plsfn1Prb00RIPAvg		 OBJECT-TYPE
		SYNTAX					 Integer32( -2147483648 .. 2147483647 )
		MAX-ACCESS			 read-only
		STATUS					 current
		DESCRIPTION			 " -- "
		::=  { sfn1avgripEntry  3 }


	plsfn1Prb01RIPAvg		 OBJECT-TYPE
		SYNTAX					 Integer32( -2147483648 .. 2147483647 )
		MAX-ACCESS			 read-only
		STATUS					 current
		DESCRIPTION			 " -- "
		::=  { sfn1avgripEntry  4 }


	plsfn1Prb02RIPAvg		 OBJECT-TYPE
		SYNTAX					 Integer32( -2147483648 .. 2147483647 )
		MAX-ACCESS			 read-only
		STATUS					 current
		DESCRIPTION			 " -- "
		::=  { sfn1avgripEntry  5 }


	plsfn1Prb03RIPAvg		 OBJECT-TYPE
		SYNTAX					 Integer32( -2147483648 .. 2147483647 )
		MAX-ACCESS			 read-only
		STATUS					 current
		DESCRIPTION			 " -- "
		::=  { sfn1avgripEntry  6 }


	plsfn1Prb04RIPAvg		 OBJECT-TYPE
		SYNTAX					 Integer32( -2147483648 .. 2147483647 )
		MAX-ACCESS			 read-only
		STATUS					 current
		DESCRIPTION			 " -- "
		::=  { sfn1avgripEntry  7 }


	plsfn1Prb05RIPAvg		 OBJECT-TYPE
		SYNTAX					 Integer32( -2147483648 .. 2147483647 )
		MAX-ACCESS			 read-only
		STATUS					 current
		DESCRIPTION			 " -- "
		::=  { sfn1avgripEntry  8 }


	plsfn1Prb06RIPAvg		 OBJECT-TYPE
		SYNTAX					 Integer32( -2147483648 .. 2147483647 )
		MAX-ACCESS			 read-only
		STATUS					 current
		DESCRIPTION			 " -- "
		::=  { sfn1avgripEntry  9 }


	plsfn1Prb07RIPAvg		 OBJECT-TYPE
		SYNTAX					 Integer32( -2147483648 .. 2147483647 )
		MAX-ACCESS			 read-only
		STATUS					 current
		DESCRIPTION			 " -- "
		::=  { sfn1avgripEntry  10 }


	plsfn1Prb08RIPAvg		 OBJECT-TYPE
		SYNTAX					 Integer32( -2147483648 .. 2147483647 )
		MAX-ACCESS			 read-only
		STATUS					 current
		DESCRIPTION			 " -- "
		::=  { sfn1avgripEntry  11 }


	plsfn1Prb09RIPAvg		 OBJECT-TYPE
		SYNTAX					 Integer32( -2147483648 .. 2147483647 )
		MAX-ACCESS			 read-only
		STATUS					 current
		DESCRIPTION			 " -- "
		::=  { sfn1avgripEntry  12 }


	plsfn1Prb10RIPAvg		 OBJECT-TYPE
		SYNTAX					 Integer32( -2147483648 .. 2147483647 )
		MAX-ACCESS			 read-only
		STATUS					 current
		DESCRIPTION			 " -- "
		::=  { sfn1avgripEntry  13 }


	plsfn1Prb11RIPAvg		 OBJECT-TYPE
		SYNTAX					 Integer32( -2147483648 .. 2147483647 )
		MAX-ACCESS			 read-only
		STATUS					 current
		DESCRIPTION			 " -- "
		::=  { sfn1avgripEntry  14 }


	plsfn1Prb12RIPAvg		 OBJECT-TYPE
		SYNTAX					 Integer32( -2147483648 .. 2147483647 )
		MAX-ACCESS			 read-only
		STATUS					 current
		DESCRIPTION			 " -- "
		::=  { sfn1avgripEntry  15 }


	plsfn1Prb13RIPAvg		 OBJECT-TYPE
		SYNTAX					 Integer32( -2147483648 .. 2147483647 )
		MAX-ACCESS			 read-only
		STATUS					 current
		DESCRIPTION			 " -- "
		::=  { sfn1avgripEntry  16 }


	plsfn1Prb14RIPAvg		 OBJECT-TYPE
		SYNTAX					 Integer32( -2147483648 .. 2147483647 )
		MAX-ACCESS			 read-only
		STATUS					 current
		DESCRIPTION			 " -- "
		::=  { sfn1avgripEntry  17 }


	plsfn1Prb15RIPAvg		 OBJECT-TYPE
		SYNTAX					 Integer32( -2147483648 .. 2147483647 )
		MAX-ACCESS			 read-only
		STATUS					 current
		DESCRIPTION			 " -- "
		::=  { sfn1avgripEntry  18 }


	plsfn1Prb16RIPAvg		 OBJECT-TYPE
		SYNTAX					 Integer32( -2147483648 .. 2147483647 )
		MAX-ACCESS			 read-only
		STATUS					 current
		DESCRIPTION			 " -- "
		::=  { sfn1avgripEntry  19 }


	plsfn1Prb17RIPAvg		 OBJECT-TYPE
		SYNTAX					 Integer32( -2147483648 .. 2147483647 )
		MAX-ACCESS			 read-only
		STATUS					 current
		DESCRIPTION			 " -- "
		::=  { sfn1avgripEntry  20 }


	plsfn1Prb18RIPAvg		 OBJECT-TYPE
		SYNTAX					 Integer32( -2147483648 .. 2147483647 )
		MAX-ACCESS			 read-only
		STATUS					 current
		DESCRIPTION			 " -- "
		::=  { sfn1avgripEntry  21 }


	plsfn1Prb19RIPAvg		 OBJECT-TYPE
		SYNTAX					 Integer32( -2147483648 .. 2147483647 )
		MAX-ACCESS			 read-only
		STATUS					 current
		DESCRIPTION			 " -- "
		::=  { sfn1avgripEntry  22 }


	plsfn1Prb20RIPAvg		 OBJECT-TYPE
		SYNTAX					 Integer32( -2147483648 .. 2147483647 )
		MAX-ACCESS			 read-only
		STATUS					 current
		DESCRIPTION			 " -- "
		::=  { sfn1avgripEntry  23 }


	plsfn1Prb21RIPAvg		 OBJECT-TYPE
		SYNTAX					 Integer32( -2147483648 .. 2147483647 )
		MAX-ACCESS			 read-only
		STATUS					 current
		DESCRIPTION			 " -- "
		::=  { sfn1avgripEntry  24 }


	plsfn1Prb22RIPAvg		 OBJECT-TYPE
		SYNTAX					 Integer32( -2147483648 .. 2147483647 )
		MAX-ACCESS			 read-only
		STATUS					 current
		DESCRIPTION			 " -- "
		::=  { sfn1avgripEntry  25 }


	plsfn1Prb23RIPAvg		 OBJECT-TYPE
		SYNTAX					 Integer32( -2147483648 .. 2147483647 )
		MAX-ACCESS			 read-only
		STATUS					 current
		DESCRIPTION			 " -- "
		::=  { sfn1avgripEntry  26 }


	plsfn1Prb24RIPAvg		 OBJECT-TYPE
		SYNTAX					 Integer32( -2147483648 .. 2147483647 )
		MAX-ACCESS			 read-only
		STATUS					 current
		DESCRIPTION			 " -- "
		::=  { sfn1avgripEntry  27 }


	plsfn1Prb25RIPAvg		 OBJECT-TYPE
		SYNTAX					 Integer32( -2147483648 .. 2147483647 )
		MAX-ACCESS			 read-only
		STATUS					 current
		DESCRIPTION			 " -- "
		::=  { sfn1avgripEntry  28 }


	plsfn1Prb26RIPAvg		 OBJECT-TYPE
		SYNTAX					 Integer32( -2147483648 .. 2147483647 )
		MAX-ACCESS			 read-only
		STATUS					 current
		DESCRIPTION			 " -- "
		::=  { sfn1avgripEntry  29 }


	plsfn1Prb27RIPAvg		 OBJECT-TYPE
		SYNTAX					 Integer32( -2147483648 .. 2147483647 )
		MAX-ACCESS			 read-only
		STATUS					 current
		DESCRIPTION			 " -- "
		::=  { sfn1avgripEntry  30 }


	plsfn1Prb28RIPAvg		 OBJECT-TYPE
		SYNTAX					 Integer32( -2147483648 .. 2147483647 )
		MAX-ACCESS			 read-only
		STATUS					 current
		DESCRIPTION			 " -- "
		::=  { sfn1avgripEntry  31 }


	plsfn1Prb29RIPAvg		 OBJECT-TYPE
		SYNTAX					 Integer32( -2147483648 .. 2147483647 )
		MAX-ACCESS			 read-only
		STATUS					 current
		DESCRIPTION			 " -- "
		::=  { sfn1avgripEntry  32 }


	plsfn1Prb30RIPAvg		 OBJECT-TYPE
		SYNTAX					 Integer32( -2147483648 .. 2147483647 )
		MAX-ACCESS			 read-only
		STATUS					 current
		DESCRIPTION			 " -- "
		::=  { sfn1avgripEntry  33 }


	plsfn1Prb31RIPAvg		 OBJECT-TYPE
		SYNTAX					 Integer32( -2147483648 .. 2147483647 )
		MAX-ACCESS			 read-only
		STATUS					 current
		DESCRIPTION			 " -- "
		::=  { sfn1avgripEntry  34 }


	plsfn1Prb32RIPAvg		 OBJECT-TYPE
		SYNTAX					 Integer32( -2147483648 .. 2147483647 )
		MAX-ACCESS			 read-only
		STATUS					 current
		DESCRIPTION			 " -- "
		::=  { sfn1avgripEntry  35 }


	plsfn1Prb33RIPAvg		 OBJECT-TYPE
		SYNTAX					 Integer32( -2147483648 .. 2147483647 )
		MAX-ACCESS			 read-only
		STATUS					 current
		DESCRIPTION			 " -- "
		::=  { sfn1avgripEntry  36 }


	plsfn1Prb34RIPAvg		 OBJECT-TYPE
		SYNTAX					 Integer32( -2147483648 .. 2147483647 )
		MAX-ACCESS			 read-only
		STATUS					 current
		DESCRIPTION			 " -- "
		::=  { sfn1avgripEntry  37 }


	plsfn1Prb35RIPAvg		 OBJECT-TYPE
		SYNTAX					 Integer32( -2147483648 .. 2147483647 )
		MAX-ACCESS			 read-only
		STATUS					 current
		DESCRIPTION			 " -- "
		::=  { sfn1avgripEntry  38 }


	plsfn1Prb36RIPAvg		 OBJECT-TYPE
		SYNTAX					 Integer32( -2147483648 .. 2147483647 )
		MAX-ACCESS			 read-only
		STATUS					 current
		DESCRIPTION			 " -- "
		::=  { sfn1avgripEntry  39 }


	plsfn1Prb37RIPAvg		 OBJECT-TYPE
		SYNTAX					 Integer32( -2147483648 .. 2147483647 )
		MAX-ACCESS			 read-only
		STATUS					 current
		DESCRIPTION			 " -- "
		::=  { sfn1avgripEntry  40 }


	plsfn1Prb38RIPAvg		 OBJECT-TYPE
		SYNTAX					 Integer32( -2147483648 .. 2147483647 )
		MAX-ACCESS			 read-only
		STATUS					 current
		DESCRIPTION			 " -- "
		::=  { sfn1avgripEntry  41 }


	plsfn1Prb39RIPAvg		 OBJECT-TYPE
		SYNTAX					 Integer32( -2147483648 .. 2147483647 )
		MAX-ACCESS			 read-only
		STATUS					 current
		DESCRIPTION			 " -- "
		::=  { sfn1avgripEntry  42 }


	plsfn1Prb40RIPAvg		 OBJECT-TYPE
		SYNTAX					 Integer32( -2147483648 .. 2147483647 )
		MAX-ACCESS			 read-only
		STATUS					 current
		DESCRIPTION			 " -- "
		::=  { sfn1avgripEntry  43 }


	plsfn1Prb41RIPAvg		 OBJECT-TYPE
		SYNTAX					 Integer32( -2147483648 .. 2147483647 )
		MAX-ACCESS			 read-only
		STATUS					 current
		DESCRIPTION			 " -- "
		::=  { sfn1avgripEntry  44 }


	plsfn1Prb42RIPAvg		 OBJECT-TYPE
		SYNTAX					 Integer32( -2147483648 .. 2147483647 )
		MAX-ACCESS			 read-only
		STATUS					 current
		DESCRIPTION			 " -- "
		::=  { sfn1avgripEntry  45 }


	plsfn1Prb43RIPAvg		 OBJECT-TYPE
		SYNTAX					 Integer32( -2147483648 .. 2147483647 )
		MAX-ACCESS			 read-only
		STATUS					 current
		DESCRIPTION			 " -- "
		::=  { sfn1avgripEntry  46 }


	plsfn1Prb44RIPAvg		 OBJECT-TYPE
		SYNTAX					 Integer32( -2147483648 .. 2147483647 )
		MAX-ACCESS			 read-only
		STATUS					 current
		DESCRIPTION			 " -- "
		::=  { sfn1avgripEntry  47 }


	plsfn1Prb45RIPAvg		 OBJECT-TYPE
		SYNTAX					 Integer32( -2147483648 .. 2147483647 )
		MAX-ACCESS			 read-only
		STATUS					 current
		DESCRIPTION			 " -- "
		::=  { sfn1avgripEntry  48 }


	plsfn1Prb46RIPAvg		 OBJECT-TYPE
		SYNTAX					 Integer32( -2147483648 .. 2147483647 )
		MAX-ACCESS			 read-only
		STATUS					 current
		DESCRIPTION			 " -- "
		::=  { sfn1avgripEntry  49 }


	plsfn1Prb47RIPAvg		 OBJECT-TYPE
		SYNTAX					 Integer32( -2147483648 .. 2147483647 )
		MAX-ACCESS			 read-only
		STATUS					 current
		DESCRIPTION			 " -- "
		::=  { sfn1avgripEntry  50 }


	plsfn1Prb48RIPAvg		 OBJECT-TYPE
		SYNTAX					 Integer32( -2147483648 .. 2147483647 )
		MAX-ACCESS			 read-only
		STATUS					 current
		DESCRIPTION			 " -- "
		::=  { sfn1avgripEntry  51 }


	plsfn1Prb49RIPAvg		 OBJECT-TYPE
		SYNTAX					 Integer32( -2147483648 .. 2147483647 )
		MAX-ACCESS			 read-only
		STATUS					 current
		DESCRIPTION			 " -- "
		::=  { sfn1avgripEntry  52 }


	plsfn1Prb50RIPAvg		 OBJECT-TYPE
		SYNTAX					 Integer32( -2147483648 .. 2147483647 )
		MAX-ACCESS			 read-only
		STATUS					 current
		DESCRIPTION			 " -- "
		::=  { sfn1avgripEntry  53 }


	plsfn1Prb51RIPAvg		 OBJECT-TYPE
		SYNTAX					 Integer32( -2147483648 .. 2147483647 )
		MAX-ACCESS			 read-only
		STATUS					 current
		DESCRIPTION			 " -- "
		::=  { sfn1avgripEntry  54 }


	plsfn1Prb52RIPAvg		 OBJECT-TYPE
		SYNTAX					 Integer32( -2147483648 .. 2147483647 )
		MAX-ACCESS			 read-only
		STATUS					 current
		DESCRIPTION			 " -- "
		::=  { sfn1avgripEntry  55 }


	plsfn1Prb53RIPAvg		 OBJECT-TYPE
		SYNTAX					 Integer32( -2147483648 .. 2147483647 )
		MAX-ACCESS			 read-only
		STATUS					 current
		DESCRIPTION			 " -- "
		::=  { sfn1avgripEntry  56 }


	plsfn1Prb54RIPAvg		 OBJECT-TYPE
		SYNTAX					 Integer32( -2147483648 .. 2147483647 )
		MAX-ACCESS			 read-only
		STATUS					 current
		DESCRIPTION			 " -- "
		::=  { sfn1avgripEntry  57 }


	plsfn1Prb55RIPAvg		 OBJECT-TYPE
		SYNTAX					 Integer32( -2147483648 .. 2147483647 )
		MAX-ACCESS			 read-only
		STATUS					 current
		DESCRIPTION			 " -- "
		::=  { sfn1avgripEntry  58 }


	plsfn1Prb56RIPAvg		 OBJECT-TYPE
		SYNTAX					 Integer32( -2147483648 .. 2147483647 )
		MAX-ACCESS			 read-only
		STATUS					 current
		DESCRIPTION			 " -- "
		::=  { sfn1avgripEntry  59 }


	plsfn1Prb57RIPAvg		 OBJECT-TYPE
		SYNTAX					 Integer32( -2147483648 .. 2147483647 )
		MAX-ACCESS			 read-only
		STATUS					 current
		DESCRIPTION			 " -- "
		::=  { sfn1avgripEntry  60 }


	plsfn1Prb58RIPAvg		 OBJECT-TYPE
		SYNTAX					 Integer32( -2147483648 .. 2147483647 )
		MAX-ACCESS			 read-only
		STATUS					 current
		DESCRIPTION			 " -- "
		::=  { sfn1avgripEntry  61 }


	plsfn1Prb59RIPAvg		 OBJECT-TYPE
		SYNTAX					 Integer32( -2147483648 .. 2147483647 )
		MAX-ACCESS			 read-only
		STATUS					 current
		DESCRIPTION			 " -- "
		::=  { sfn1avgripEntry  62 }


	plsfn1Prb60RIPAvg		 OBJECT-TYPE
		SYNTAX					 Integer32( -2147483648 .. 2147483647 )
		MAX-ACCESS			 read-only
		STATUS					 current
		DESCRIPTION			 " -- "
		::=  { sfn1avgripEntry  63 }


	plsfn1Prb61RIPAvg		 OBJECT-TYPE
		SYNTAX					 Integer32( -2147483648 .. 2147483647 )
		MAX-ACCESS			 read-only
		STATUS					 current
		DESCRIPTION			 " -- "
		::=  { sfn1avgripEntry  64 }


	plsfn1Prb62RIPAvg		 OBJECT-TYPE
		SYNTAX					 Integer32( -2147483648 .. 2147483647 )
		MAX-ACCESS			 read-only
		STATUS					 current
		DESCRIPTION			 " -- "
		::=  { sfn1avgripEntry  65 }


	plsfn1Prb63RIPAvg		 OBJECT-TYPE
		SYNTAX					 Integer32( -2147483648 .. 2147483647 )
		MAX-ACCESS			 read-only
		STATUS					 current
		DESCRIPTION			 " -- "
		::=  { sfn1avgripEntry  66 }


	plsfn1Prb64RIPAvg		 OBJECT-TYPE
		SYNTAX					 Integer32( -2147483648 .. 2147483647 )
		MAX-ACCESS			 read-only
		STATUS					 current
		DESCRIPTION			 " -- "
		::=  { sfn1avgripEntry  67 }


	plsfn1Prb65RIPAvg		 OBJECT-TYPE
		SYNTAX					 Integer32( -2147483648 .. 2147483647 )
		MAX-ACCESS			 read-only
		STATUS					 current
		DESCRIPTION			 " -- "
		::=  { sfn1avgripEntry  68 }


	plsfn1Prb66RIPAvg		 OBJECT-TYPE
		SYNTAX					 Integer32( -2147483648 .. 2147483647 )
		MAX-ACCESS			 read-only
		STATUS					 current
		DESCRIPTION			 " -- "
		::=  { sfn1avgripEntry  69 }


	plsfn1Prb67RIPAvg		 OBJECT-TYPE
		SYNTAX					 Integer32( -2147483648 .. 2147483647 )
		MAX-ACCESS			 read-only
		STATUS					 current
		DESCRIPTION			 " -- "
		::=  { sfn1avgripEntry  70 }


	plsfn1Prb68RIPAvg		 OBJECT-TYPE
		SYNTAX					 Integer32( -2147483648 .. 2147483647 )
		MAX-ACCESS			 read-only
		STATUS					 current
		DESCRIPTION			 " -- "
		::=  { sfn1avgripEntry  71 }


	plsfn1Prb69RIPAvg		 OBJECT-TYPE
		SYNTAX					 Integer32( -2147483648 .. 2147483647 )
		MAX-ACCESS			 read-only
		STATUS					 current
		DESCRIPTION			 " -- "
		::=  { sfn1avgripEntry  72 }


	plsfn1Prb70RIPAvg		 OBJECT-TYPE
		SYNTAX					 Integer32( -2147483648 .. 2147483647 )
		MAX-ACCESS			 read-only
		STATUS					 current
		DESCRIPTION			 " -- "
		::=  { sfn1avgripEntry  73 }


	plsfn1Prb71RIPAvg		 OBJECT-TYPE
		SYNTAX					 Integer32( -2147483648 .. 2147483647 )
		MAX-ACCESS			 read-only
		STATUS					 current
		DESCRIPTION			 " -- "
		::=  { sfn1avgripEntry  74 }


	plsfn1Prb72RIPAvg		 OBJECT-TYPE
		SYNTAX					 Integer32( -2147483648 .. 2147483647 )
		MAX-ACCESS			 read-only
		STATUS					 current
		DESCRIPTION			 " -- "
		::=  { sfn1avgripEntry  75 }


	plsfn1Prb73RIPAvg		 OBJECT-TYPE
		SYNTAX					 Integer32( -2147483648 .. 2147483647 )
		MAX-ACCESS			 read-only
		STATUS					 current
		DESCRIPTION			 " -- "
		::=  { sfn1avgripEntry  76 }


	plsfn1Prb74RIPAvg		 OBJECT-TYPE
		SYNTAX					 Integer32( -2147483648 .. 2147483647 )
		MAX-ACCESS			 read-only
		STATUS					 current
		DESCRIPTION			 " -- "
		::=  { sfn1avgripEntry  77 }


	plsfn1Prb75RIPAvg		 OBJECT-TYPE
		SYNTAX					 Integer32( -2147483648 .. 2147483647 )
		MAX-ACCESS			 read-only
		STATUS					 current
		DESCRIPTION			 " -- "
		::=  { sfn1avgripEntry  78 }


	plsfn1Prb76RIPAvg		 OBJECT-TYPE
		SYNTAX					 Integer32( -2147483648 .. 2147483647 )
		MAX-ACCESS			 read-only
		STATUS					 current
		DESCRIPTION			 " -- "
		::=  { sfn1avgripEntry  79 }


	plsfn1Prb77RIPAvg		 OBJECT-TYPE
		SYNTAX					 Integer32( -2147483648 .. 2147483647 )
		MAX-ACCESS			 read-only
		STATUS					 current
		DESCRIPTION			 " -- "
		::=  { sfn1avgripEntry  80 }


	plsfn1Prb78RIPAvg		 OBJECT-TYPE
		SYNTAX					 Integer32( -2147483648 .. 2147483647 )
		MAX-ACCESS			 read-only
		STATUS					 current
		DESCRIPTION			 " -- "
		::=  { sfn1avgripEntry  81 }


	plsfn1Prb79RIPAvg		 OBJECT-TYPE
		SYNTAX					 Integer32( -2147483648 .. 2147483647 )
		MAX-ACCESS			 read-only
		STATUS					 current
		DESCRIPTION			 " -- "
		::=  { sfn1avgripEntry  82 }


	plsfn1Prb80RIPAvg		 OBJECT-TYPE
		SYNTAX					 Integer32( -2147483648 .. 2147483647 )
		MAX-ACCESS			 read-only
		STATUS					 current
		DESCRIPTION			 " -- "
		::=  { sfn1avgripEntry  83 }


	plsfn1Prb81RIPAvg		 OBJECT-TYPE
		SYNTAX					 Integer32( -2147483648 .. 2147483647 )
		MAX-ACCESS			 read-only
		STATUS					 current
		DESCRIPTION			 " -- "
		::=  { sfn1avgripEntry  84 }


	plsfn1Prb82RIPAvg		 OBJECT-TYPE
		SYNTAX					 Integer32( -2147483648 .. 2147483647 )
		MAX-ACCESS			 read-only
		STATUS					 current
		DESCRIPTION			 " -- "
		::=  { sfn1avgripEntry  85 }


	plsfn1Prb83RIPAvg		 OBJECT-TYPE
		SYNTAX					 Integer32( -2147483648 .. 2147483647 )
		MAX-ACCESS			 read-only
		STATUS					 current
		DESCRIPTION			 " -- "
		::=  { sfn1avgripEntry  86 }


	plsfn1Prb84RIPAvg		 OBJECT-TYPE
		SYNTAX					 Integer32( -2147483648 .. 2147483647 )
		MAX-ACCESS			 read-only
		STATUS					 current
		DESCRIPTION			 " -- "
		::=  { sfn1avgripEntry  87 }


	plsfn1Prb85RIPAvg		 OBJECT-TYPE
		SYNTAX					 Integer32( -2147483648 .. 2147483647 )
		MAX-ACCESS			 read-only
		STATUS					 current
		DESCRIPTION			 " -- "
		::=  { sfn1avgripEntry  88 }


	plsfn1Prb86RIPAvg		 OBJECT-TYPE
		SYNTAX					 Integer32( -2147483648 .. 2147483647 )
		MAX-ACCESS			 read-only
		STATUS					 current
		DESCRIPTION			 " -- "
		::=  { sfn1avgripEntry  89 }


	plsfn1Prb87RIPAvg		 OBJECT-TYPE
		SYNTAX					 Integer32( -2147483648 .. 2147483647 )
		MAX-ACCESS			 read-only
		STATUS					 current
		DESCRIPTION			 " -- "
		::=  { sfn1avgripEntry  90 }


	plsfn1Prb88RIPAvg		 OBJECT-TYPE
		SYNTAX					 Integer32( -2147483648 .. 2147483647 )
		MAX-ACCESS			 read-only
		STATUS					 current
		DESCRIPTION			 " -- "
		::=  { sfn1avgripEntry  91 }


	plsfn1Prb89RIPAvg		 OBJECT-TYPE
		SYNTAX					 Integer32( -2147483648 .. 2147483647 )
		MAX-ACCESS			 read-only
		STATUS					 current
		DESCRIPTION			 " -- "
		::=  { sfn1avgripEntry  92 }


	plsfn1Prb90RIPAvg		 OBJECT-TYPE
		SYNTAX					 Integer32( -2147483648 .. 2147483647 )
		MAX-ACCESS			 read-only
		STATUS					 current
		DESCRIPTION			 " -- "
		::=  { sfn1avgripEntry  93 }


	plsfn1Prb91RIPAvg		 OBJECT-TYPE
		SYNTAX					 Integer32( -2147483648 .. 2147483647 )
		MAX-ACCESS			 read-only
		STATUS					 current
		DESCRIPTION			 " -- "
		::=  { sfn1avgripEntry  94 }


	plsfn1Prb92RIPAvg		 OBJECT-TYPE
		SYNTAX					 Integer32( -2147483648 .. 2147483647 )
		MAX-ACCESS			 read-only
		STATUS					 current
		DESCRIPTION			 " -- "
		::=  { sfn1avgripEntry  95 }


	plsfn1Prb93RIPAvg		 OBJECT-TYPE
		SYNTAX					 Integer32( -2147483648 .. 2147483647 )
		MAX-ACCESS			 read-only
		STATUS					 current
		DESCRIPTION			 " -- "
		::=  { sfn1avgripEntry  96 }


	plsfn1Prb94RIPAvg		 OBJECT-TYPE
		SYNTAX					 Integer32( -2147483648 .. 2147483647 )
		MAX-ACCESS			 read-only
		STATUS					 current
		DESCRIPTION			 " -- "
		::=  { sfn1avgripEntry  97 }


	plsfn1Prb95RIPAvg		 OBJECT-TYPE
		SYNTAX					 Integer32( -2147483648 .. 2147483647 )
		MAX-ACCESS			 read-only
		STATUS					 current
		DESCRIPTION			 " -- "
		::=  { sfn1avgripEntry  98 }


	plsfn1Prb96RIPAvg		 OBJECT-TYPE
		SYNTAX					 Integer32( -2147483648 .. 2147483647 )
		MAX-ACCESS			 read-only
		STATUS					 current
		DESCRIPTION			 " -- "
		::=  { sfn1avgripEntry  99 }


	plsfn1Prb97RIPAvg		 OBJECT-TYPE
		SYNTAX					 Integer32( -2147483648 .. 2147483647 )
		MAX-ACCESS			 read-only
		STATUS					 current
		DESCRIPTION			 " -- "
		::=  { sfn1avgripEntry  100 }


	plsfn1Prb98RIPAvg		 OBJECT-TYPE
		SYNTAX					 Integer32( -2147483648 .. 2147483647 )
		MAX-ACCESS			 read-only
		STATUS					 current
		DESCRIPTION			 " -- "
		::=  { sfn1avgripEntry  101 }


	plsfn1Prb99RIPAvg		 OBJECT-TYPE
		SYNTAX					 Integer32( -2147483648 .. 2147483647 )
		MAX-ACCESS			 read-only
		STATUS					 current
		DESCRIPTION			 " -- "
		::=  { sfn1avgripEntry  102 }


	sfn0avgripTable		 OBJECT-TYPE
		SYNTAX					 SEQUENCE  OF	 Sfn0avgripEntry
		MAX-ACCESS			 not-accessible
		STATUS					 current
		DESCRIPTION			 " -- "
		::=  { plrelatedOriginCounter  5 }


	sfn0avgripEntry		 OBJECT-TYPE
		SYNTAX					 Sfn0avgripEntry
		MAX-ACCESS			 not-accessible
		STATUS					 current
		DESCRIPTION			 " -- "
		INDEX						{ sfn0avgripLcId }
		::=  { sfn0avgripTable  1 }


	Sfn0avgripEntry		 ::=  SEQUENCE {
		sfn0avgripLcId					Integer32,
		sfn0avgripRowStatus					RowStatus,
		plsfn0Prb00RIPAvg					Integer32,
		plsfn0Prb01RIPAvg					Integer32,
		plsfn0Prb02RIPAvg					Integer32,
		plsfn0Prb03RIPAvg					Integer32,
		plsfn0Prb04RIPAvg					Integer32,
		plsfn0Prb05RIPAvg					Integer32,
		plsfn0Prb06RIPAvg					Integer32,
		plsfn0Prb07RIPAvg					Integer32,
		plsfn0Prb08RIPAvg					Integer32,
		plsfn0Prb09RIPAvg					Integer32,
		plsfn0Prb10RIPAvg					Integer32,
		plsfn0Prb11RIPAvg					Integer32,
		plsfn0Prb12RIPAvg					Integer32,
		plsfn0Prb13RIPAvg					Integer32,
		plsfn0Prb14RIPAvg					Integer32,
		plsfn0Prb15RIPAvg					Integer32,
		plsfn0Prb16RIPAvg					Integer32,
		plsfn0Prb17RIPAvg					Integer32,
		plsfn0Prb18RIPAvg					Integer32,
		plsfn0Prb19RIPAvg					Integer32,
		plsfn0Prb20RIPAvg					Integer32,
		plsfn0Prb21RIPAvg					Integer32,
		plsfn0Prb22RIPAvg					Integer32,
		plsfn0Prb23RIPAvg					Integer32,
		plsfn0Prb24RIPAvg					Integer32,
		plsfn0Prb25RIPAvg					Integer32,
		plsfn0Prb26RIPAvg					Integer32,
		plsfn0Prb27RIPAvg					Integer32,
		plsfn0Prb28RIPAvg					Integer32,
		plsfn0Prb29RIPAvg					Integer32,
		plsfn0Prb30RIPAvg					Integer32,
		plsfn0Prb31RIPAvg					Integer32,
		plsfn0Prb32RIPAvg					Integer32,
		plsfn0Prb33RIPAvg					Integer32,
		plsfn0Prb34RIPAvg					Integer32,
		plsfn0Prb35RIPAvg					Integer32,
		plsfn0Prb36RIPAvg					Integer32,
		plsfn0Prb37RIPAvg					Integer32,
		plsfn0Prb38RIPAvg					Integer32,
		plsfn0Prb39RIPAvg					Integer32,
		plsfn0Prb40RIPAvg					Integer32,
		plsfn0Prb41RIPAvg					Integer32,
		plsfn0Prb42RIPAvg					Integer32,
		plsfn0Prb43RIPAvg					Integer32,
		plsfn0Prb44RIPAvg					Integer32,
		plsfn0Prb45RIPAvg					Integer32,
		plsfn0Prb46RIPAvg					Integer32,
		plsfn0Prb47RIPAvg					Integer32,
		plsfn0Prb48RIPAvg					Integer32,
		plsfn0Prb49RIPAvg					Integer32,
		plsfn0Prb50RIPAvg					Integer32,
		plsfn0Prb51RIPAvg					Integer32,
		plsfn0Prb52RIPAvg					Integer32,
		plsfn0Prb53RIPAvg					Integer32,
		plsfn0Prb54RIPAvg					Integer32,
		plsfn0Prb55RIPAvg					Integer32,
		plsfn0Prb56RIPAvg					Integer32,
		plsfn0Prb57RIPAvg					Integer32,
		plsfn0Prb58RIPAvg					Integer32,
		plsfn0Prb59RIPAvg					Integer32,
		plsfn0Prb60RIPAvg					Integer32,
		plsfn0Prb61RIPAvg					Integer32,
		plsfn0Prb62RIPAvg					Integer32,
		plsfn0Prb63RIPAvg					Integer32,
		plsfn0Prb64RIPAvg					Integer32,
		plsfn0Prb65RIPAvg					Integer32,
		plsfn0Prb66RIPAvg					Integer32,
		plsfn0Prb67RIPAvg					Integer32,
		plsfn0Prb68RIPAvg					Integer32,
		plsfn0Prb69RIPAvg					Integer32,
		plsfn0Prb70RIPAvg					Integer32,
		plsfn0Prb71RIPAvg					Integer32,
		plsfn0Prb72RIPAvg					Integer32,
		plsfn0Prb73RIPAvg					Integer32,
		plsfn0Prb74RIPAvg					Integer32,
		plsfn0Prb75RIPAvg					Integer32,
		plsfn0Prb76RIPAvg					Integer32,
		plsfn0Prb77RIPAvg					Integer32,
		plsfn0Prb78RIPAvg					Integer32,
		plsfn0Prb79RIPAvg					Integer32,
		plsfn0Prb80RIPAvg					Integer32,
		plsfn0Prb81RIPAvg					Integer32,
		plsfn0Prb82RIPAvg					Integer32,
		plsfn0Prb83RIPAvg					Integer32,
		plsfn0Prb84RIPAvg					Integer32,
		plsfn0Prb85RIPAvg					Integer32,
		plsfn0Prb86RIPAvg					Integer32,
		plsfn0Prb87RIPAvg					Integer32,
		plsfn0Prb88RIPAvg					Integer32,
		plsfn0Prb89RIPAvg					Integer32,
		plsfn0Prb90RIPAvg					Integer32,
		plsfn0Prb91RIPAvg					Integer32,
		plsfn0Prb92RIPAvg					Integer32,
		plsfn0Prb93RIPAvg					Integer32,
		plsfn0Prb94RIPAvg					Integer32,
		plsfn0Prb95RIPAvg					Integer32,
		plsfn0Prb96RIPAvg					Integer32,
		plsfn0Prb97RIPAvg					Integer32,
		plsfn0Prb98RIPAvg					Integer32,
		plsfn0Prb99RIPAvg					Integer32
		}


	sfn0avgripLcId		 OBJECT-TYPE
		SYNTAX					 Integer32( 0 .. 23 )
		MAX-ACCESS			 not-accessible
		STATUS					 current
		DESCRIPTION			 " -- "
		::=  { sfn0avgripEntry  1 }


	sfn0avgripRowStatus		 OBJECT-TYPE
		SYNTAX					 RowStatus
		MAX-ACCESS			 read-only
		STATUS					 current
		DESCRIPTION			 " -- "
		::=  { sfn0avgripEntry  2 }


	plsfn0Prb00RIPAvg		 OBJECT-TYPE
		SYNTAX					 Integer32( -2147483648 .. 2147483647 )
		MAX-ACCESS			 read-only
		STATUS					 current
		DESCRIPTION			 " -- "
		::=  { sfn0avgripEntry  3 }


	plsfn0Prb01RIPAvg		 OBJECT-TYPE
		SYNTAX					 Integer32( -2147483648 .. 2147483647 )
		MAX-ACCESS			 read-only
		STATUS					 current
		DESCRIPTION			 " -- "
		::=  { sfn0avgripEntry  4 }


	plsfn0Prb02RIPAvg		 OBJECT-TYPE
		SYNTAX					 Integer32( -2147483648 .. 2147483647 )
		MAX-ACCESS			 read-only
		STATUS					 current
		DESCRIPTION			 " -- "
		::=  { sfn0avgripEntry  5 }


	plsfn0Prb03RIPAvg		 OBJECT-TYPE
		SYNTAX					 Integer32( -2147483648 .. 2147483647 )
		MAX-ACCESS			 read-only
		STATUS					 current
		DESCRIPTION			 " -- "
		::=  { sfn0avgripEntry  6 }


	plsfn0Prb04RIPAvg		 OBJECT-TYPE
		SYNTAX					 Integer32( -2147483648 .. 2147483647 )
		MAX-ACCESS			 read-only
		STATUS					 current
		DESCRIPTION			 " -- "
		::=  { sfn0avgripEntry  7 }


	plsfn0Prb05RIPAvg		 OBJECT-TYPE
		SYNTAX					 Integer32( -2147483648 .. 2147483647 )
		MAX-ACCESS			 read-only
		STATUS					 current
		DESCRIPTION			 " -- "
		::=  { sfn0avgripEntry  8 }


	plsfn0Prb06RIPAvg		 OBJECT-TYPE
		SYNTAX					 Integer32( -2147483648 .. 2147483647 )
		MAX-ACCESS			 read-only
		STATUS					 current
		DESCRIPTION			 " -- "
		::=  { sfn0avgripEntry  9 }


	plsfn0Prb07RIPAvg		 OBJECT-TYPE
		SYNTAX					 Integer32( -2147483648 .. 2147483647 )
		MAX-ACCESS			 read-only
		STATUS					 current
		DESCRIPTION			 " -- "
		::=  { sfn0avgripEntry  10 }


	plsfn0Prb08RIPAvg		 OBJECT-TYPE
		SYNTAX					 Integer32( -2147483648 .. 2147483647 )
		MAX-ACCESS			 read-only
		STATUS					 current
		DESCRIPTION			 " -- "
		::=  { sfn0avgripEntry  11 }


	plsfn0Prb09RIPAvg		 OBJECT-TYPE
		SYNTAX					 Integer32( -2147483648 .. 2147483647 )
		MAX-ACCESS			 read-only
		STATUS					 current
		DESCRIPTION			 " -- "
		::=  { sfn0avgripEntry  12 }


	plsfn0Prb10RIPAvg		 OBJECT-TYPE
		SYNTAX					 Integer32( -2147483648 .. 2147483647 )
		MAX-ACCESS			 read-only
		STATUS					 current
		DESCRIPTION			 " -- "
		::=  { sfn0avgripEntry  13 }


	plsfn0Prb11RIPAvg		 OBJECT-TYPE
		SYNTAX					 Integer32( -2147483648 .. 2147483647 )
		MAX-ACCESS			 read-only
		STATUS					 current
		DESCRIPTION			 " -- "
		::=  { sfn0avgripEntry  14 }


	plsfn0Prb12RIPAvg		 OBJECT-TYPE
		SYNTAX					 Integer32( -2147483648 .. 2147483647 )
		MAX-ACCESS			 read-only
		STATUS					 current
		DESCRIPTION			 " -- "
		::=  { sfn0avgripEntry  15 }


	plsfn0Prb13RIPAvg		 OBJECT-TYPE
		SYNTAX					 Integer32( -2147483648 .. 2147483647 )
		MAX-ACCESS			 read-only
		STATUS					 current
		DESCRIPTION			 " -- "
		::=  { sfn0avgripEntry  16 }


	plsfn0Prb14RIPAvg		 OBJECT-TYPE
		SYNTAX					 Integer32( -2147483648 .. 2147483647 )
		MAX-ACCESS			 read-only
		STATUS					 current
		DESCRIPTION			 " -- "
		::=  { sfn0avgripEntry  17 }


	plsfn0Prb15RIPAvg		 OBJECT-TYPE
		SYNTAX					 Integer32( -2147483648 .. 2147483647 )
		MAX-ACCESS			 read-only
		STATUS					 current
		DESCRIPTION			 " -- "
		::=  { sfn0avgripEntry  18 }


	plsfn0Prb16RIPAvg		 OBJECT-TYPE
		SYNTAX					 Integer32( -2147483648 .. 2147483647 )
		MAX-ACCESS			 read-only
		STATUS					 current
		DESCRIPTION			 " -- "
		::=  { sfn0avgripEntry  19 }


	plsfn0Prb17RIPAvg		 OBJECT-TYPE
		SYNTAX					 Integer32( -2147483648 .. 2147483647 )
		MAX-ACCESS			 read-only
		STATUS					 current
		DESCRIPTION			 " -- "
		::=  { sfn0avgripEntry  20 }


	plsfn0Prb18RIPAvg		 OBJECT-TYPE
		SYNTAX					 Integer32( -2147483648 .. 2147483647 )
		MAX-ACCESS			 read-only
		STATUS					 current
		DESCRIPTION			 " -- "
		::=  { sfn0avgripEntry  21 }


	plsfn0Prb19RIPAvg		 OBJECT-TYPE
		SYNTAX					 Integer32( -2147483648 .. 2147483647 )
		MAX-ACCESS			 read-only
		STATUS					 current
		DESCRIPTION			 " -- "
		::=  { sfn0avgripEntry  22 }


	plsfn0Prb20RIPAvg		 OBJECT-TYPE
		SYNTAX					 Integer32( -2147483648 .. 2147483647 )
		MAX-ACCESS			 read-only
		STATUS					 current
		DESCRIPTION			 " -- "
		::=  { sfn0avgripEntry  23 }


	plsfn0Prb21RIPAvg		 OBJECT-TYPE
		SYNTAX					 Integer32( -2147483648 .. 2147483647 )
		MAX-ACCESS			 read-only
		STATUS					 current
		DESCRIPTION			 " -- "
		::=  { sfn0avgripEntry  24 }


	plsfn0Prb22RIPAvg		 OBJECT-TYPE
		SYNTAX					 Integer32( -2147483648 .. 2147483647 )
		MAX-ACCESS			 read-only
		STATUS					 current
		DESCRIPTION			 " -- "
		::=  { sfn0avgripEntry  25 }


	plsfn0Prb23RIPAvg		 OBJECT-TYPE
		SYNTAX					 Integer32( -2147483648 .. 2147483647 )
		MAX-ACCESS			 read-only
		STATUS					 current
		DESCRIPTION			 " -- "
		::=  { sfn0avgripEntry  26 }


	plsfn0Prb24RIPAvg		 OBJECT-TYPE
		SYNTAX					 Integer32( -2147483648 .. 2147483647 )
		MAX-ACCESS			 read-only
		STATUS					 current
		DESCRIPTION			 " -- "
		::=  { sfn0avgripEntry  27 }


	plsfn0Prb25RIPAvg		 OBJECT-TYPE
		SYNTAX					 Integer32( -2147483648 .. 2147483647 )
		MAX-ACCESS			 read-only
		STATUS					 current
		DESCRIPTION			 " -- "
		::=  { sfn0avgripEntry  28 }


	plsfn0Prb26RIPAvg		 OBJECT-TYPE
		SYNTAX					 Integer32( -2147483648 .. 2147483647 )
		MAX-ACCESS			 read-only
		STATUS					 current
		DESCRIPTION			 " -- "
		::=  { sfn0avgripEntry  29 }


	plsfn0Prb27RIPAvg		 OBJECT-TYPE
		SYNTAX					 Integer32( -2147483648 .. 2147483647 )
		MAX-ACCESS			 read-only
		STATUS					 current
		DESCRIPTION			 " -- "
		::=  { sfn0avgripEntry  30 }


	plsfn0Prb28RIPAvg		 OBJECT-TYPE
		SYNTAX					 Integer32( -2147483648 .. 2147483647 )
		MAX-ACCESS			 read-only
		STATUS					 current
		DESCRIPTION			 " -- "
		::=  { sfn0avgripEntry  31 }


	plsfn0Prb29RIPAvg		 OBJECT-TYPE
		SYNTAX					 Integer32( -2147483648 .. 2147483647 )
		MAX-ACCESS			 read-only
		STATUS					 current
		DESCRIPTION			 " -- "
		::=  { sfn0avgripEntry  32 }


	plsfn0Prb30RIPAvg		 OBJECT-TYPE
		SYNTAX					 Integer32( -2147483648 .. 2147483647 )
		MAX-ACCESS			 read-only
		STATUS					 current
		DESCRIPTION			 " -- "
		::=  { sfn0avgripEntry  33 }


	plsfn0Prb31RIPAvg		 OBJECT-TYPE
		SYNTAX					 Integer32( -2147483648 .. 2147483647 )
		MAX-ACCESS			 read-only
		STATUS					 current
		DESCRIPTION			 " -- "
		::=  { sfn0avgripEntry  34 }


	plsfn0Prb32RIPAvg		 OBJECT-TYPE
		SYNTAX					 Integer32( -2147483648 .. 2147483647 )
		MAX-ACCESS			 read-only
		STATUS					 current
		DESCRIPTION			 " -- "
		::=  { sfn0avgripEntry  35 }


	plsfn0Prb33RIPAvg		 OBJECT-TYPE
		SYNTAX					 Integer32( -2147483648 .. 2147483647 )
		MAX-ACCESS			 read-only
		STATUS					 current
		DESCRIPTION			 " -- "
		::=  { sfn0avgripEntry  36 }


	plsfn0Prb34RIPAvg		 OBJECT-TYPE
		SYNTAX					 Integer32( -2147483648 .. 2147483647 )
		MAX-ACCESS			 read-only
		STATUS					 current
		DESCRIPTION			 " -- "
		::=  { sfn0avgripEntry  37 }


	plsfn0Prb35RIPAvg		 OBJECT-TYPE
		SYNTAX					 Integer32( -2147483648 .. 2147483647 )
		MAX-ACCESS			 read-only
		STATUS					 current
		DESCRIPTION			 " -- "
		::=  { sfn0avgripEntry  38 }


	plsfn0Prb36RIPAvg		 OBJECT-TYPE
		SYNTAX					 Integer32( -2147483648 .. 2147483647 )
		MAX-ACCESS			 read-only
		STATUS					 current
		DESCRIPTION			 " -- "
		::=  { sfn0avgripEntry  39 }


	plsfn0Prb37RIPAvg		 OBJECT-TYPE
		SYNTAX					 Integer32( -2147483648 .. 2147483647 )
		MAX-ACCESS			 read-only
		STATUS					 current
		DESCRIPTION			 " -- "
		::=  { sfn0avgripEntry  40 }


	plsfn0Prb38RIPAvg		 OBJECT-TYPE
		SYNTAX					 Integer32( -2147483648 .. 2147483647 )
		MAX-ACCESS			 read-only
		STATUS					 current
		DESCRIPTION			 " -- "
		::=  { sfn0avgripEntry  41 }


	plsfn0Prb39RIPAvg		 OBJECT-TYPE
		SYNTAX					 Integer32( -2147483648 .. 2147483647 )
		MAX-ACCESS			 read-only
		STATUS					 current
		DESCRIPTION			 " -- "
		::=  { sfn0avgripEntry  42 }


	plsfn0Prb40RIPAvg		 OBJECT-TYPE
		SYNTAX					 Integer32( -2147483648 .. 2147483647 )
		MAX-ACCESS			 read-only
		STATUS					 current
		DESCRIPTION			 " -- "
		::=  { sfn0avgripEntry  43 }


	plsfn0Prb41RIPAvg		 OBJECT-TYPE
		SYNTAX					 Integer32( -2147483648 .. 2147483647 )
		MAX-ACCESS			 read-only
		STATUS					 current
		DESCRIPTION			 " -- "
		::=  { sfn0avgripEntry  44 }


	plsfn0Prb42RIPAvg		 OBJECT-TYPE
		SYNTAX					 Integer32( -2147483648 .. 2147483647 )
		MAX-ACCESS			 read-only
		STATUS					 current
		DESCRIPTION			 " -- "
		::=  { sfn0avgripEntry  45 }


	plsfn0Prb43RIPAvg		 OBJECT-TYPE
		SYNTAX					 Integer32( -2147483648 .. 2147483647 )
		MAX-ACCESS			 read-only
		STATUS					 current
		DESCRIPTION			 " -- "
		::=  { sfn0avgripEntry  46 }


	plsfn0Prb44RIPAvg		 OBJECT-TYPE
		SYNTAX					 Integer32( -2147483648 .. 2147483647 )
		MAX-ACCESS			 read-only
		STATUS					 current
		DESCRIPTION			 " -- "
		::=  { sfn0avgripEntry  47 }


	plsfn0Prb45RIPAvg		 OBJECT-TYPE
		SYNTAX					 Integer32( -2147483648 .. 2147483647 )
		MAX-ACCESS			 read-only
		STATUS					 current
		DESCRIPTION			 " -- "
		::=  { sfn0avgripEntry  48 }


	plsfn0Prb46RIPAvg		 OBJECT-TYPE
		SYNTAX					 Integer32( -2147483648 .. 2147483647 )
		MAX-ACCESS			 read-only
		STATUS					 current
		DESCRIPTION			 " -- "
		::=  { sfn0avgripEntry  49 }


	plsfn0Prb47RIPAvg		 OBJECT-TYPE
		SYNTAX					 Integer32( -2147483648 .. 2147483647 )
		MAX-ACCESS			 read-only
		STATUS					 current
		DESCRIPTION			 " -- "
		::=  { sfn0avgripEntry  50 }


	plsfn0Prb48RIPAvg		 OBJECT-TYPE
		SYNTAX					 Integer32( -2147483648 .. 2147483647 )
		MAX-ACCESS			 read-only
		STATUS					 current
		DESCRIPTION			 " -- "
		::=  { sfn0avgripEntry  51 }


	plsfn0Prb49RIPAvg		 OBJECT-TYPE
		SYNTAX					 Integer32( -2147483648 .. 2147483647 )
		MAX-ACCESS			 read-only
		STATUS					 current
		DESCRIPTION			 " -- "
		::=  { sfn0avgripEntry  52 }


	plsfn0Prb50RIPAvg		 OBJECT-TYPE
		SYNTAX					 Integer32( -2147483648 .. 2147483647 )
		MAX-ACCESS			 read-only
		STATUS					 current
		DESCRIPTION			 " -- "
		::=  { sfn0avgripEntry  53 }


	plsfn0Prb51RIPAvg		 OBJECT-TYPE
		SYNTAX					 Integer32( -2147483648 .. 2147483647 )
		MAX-ACCESS			 read-only
		STATUS					 current
		DESCRIPTION			 " -- "
		::=  { sfn0avgripEntry  54 }


	plsfn0Prb52RIPAvg		 OBJECT-TYPE
		SYNTAX					 Integer32( -2147483648 .. 2147483647 )
		MAX-ACCESS			 read-only
		STATUS					 current
		DESCRIPTION			 " -- "
		::=  { sfn0avgripEntry  55 }


	plsfn0Prb53RIPAvg		 OBJECT-TYPE
		SYNTAX					 Integer32( -2147483648 .. 2147483647 )
		MAX-ACCESS			 read-only
		STATUS					 current
		DESCRIPTION			 " -- "
		::=  { sfn0avgripEntry  56 }


	plsfn0Prb54RIPAvg		 OBJECT-TYPE
		SYNTAX					 Integer32( -2147483648 .. 2147483647 )
		MAX-ACCESS			 read-only
		STATUS					 current
		DESCRIPTION			 " -- "
		::=  { sfn0avgripEntry  57 }


	plsfn0Prb55RIPAvg		 OBJECT-TYPE
		SYNTAX					 Integer32( -2147483648 .. 2147483647 )
		MAX-ACCESS			 read-only
		STATUS					 current
		DESCRIPTION			 " -- "
		::=  { sfn0avgripEntry  58 }


	plsfn0Prb56RIPAvg		 OBJECT-TYPE
		SYNTAX					 Integer32( -2147483648 .. 2147483647 )
		MAX-ACCESS			 read-only
		STATUS					 current
		DESCRIPTION			 " -- "
		::=  { sfn0avgripEntry  59 }


	plsfn0Prb57RIPAvg		 OBJECT-TYPE
		SYNTAX					 Integer32( -2147483648 .. 2147483647 )
		MAX-ACCESS			 read-only
		STATUS					 current
		DESCRIPTION			 " -- "
		::=  { sfn0avgripEntry  60 }


	plsfn0Prb58RIPAvg		 OBJECT-TYPE
		SYNTAX					 Integer32( -2147483648 .. 2147483647 )
		MAX-ACCESS			 read-only
		STATUS					 current
		DESCRIPTION			 " -- "
		::=  { sfn0avgripEntry  61 }


	plsfn0Prb59RIPAvg		 OBJECT-TYPE
		SYNTAX					 Integer32( -2147483648 .. 2147483647 )
		MAX-ACCESS			 read-only
		STATUS					 current
		DESCRIPTION			 " -- "
		::=  { sfn0avgripEntry  62 }


	plsfn0Prb60RIPAvg		 OBJECT-TYPE
		SYNTAX					 Integer32( -2147483648 .. 2147483647 )
		MAX-ACCESS			 read-only
		STATUS					 current
		DESCRIPTION			 " -- "
		::=  { sfn0avgripEntry  63 }


	plsfn0Prb61RIPAvg		 OBJECT-TYPE
		SYNTAX					 Integer32( -2147483648 .. 2147483647 )
		MAX-ACCESS			 read-only
		STATUS					 current
		DESCRIPTION			 " -- "
		::=  { sfn0avgripEntry  64 }


	plsfn0Prb62RIPAvg		 OBJECT-TYPE
		SYNTAX					 Integer32( -2147483648 .. 2147483647 )
		MAX-ACCESS			 read-only
		STATUS					 current
		DESCRIPTION			 " -- "
		::=  { sfn0avgripEntry  65 }


	plsfn0Prb63RIPAvg		 OBJECT-TYPE
		SYNTAX					 Integer32( -2147483648 .. 2147483647 )
		MAX-ACCESS			 read-only
		STATUS					 current
		DESCRIPTION			 " -- "
		::=  { sfn0avgripEntry  66 }


	plsfn0Prb64RIPAvg		 OBJECT-TYPE
		SYNTAX					 Integer32( -2147483648 .. 2147483647 )
		MAX-ACCESS			 read-only
		STATUS					 current
		DESCRIPTION			 " -- "
		::=  { sfn0avgripEntry  67 }


	plsfn0Prb65RIPAvg		 OBJECT-TYPE
		SYNTAX					 Integer32( -2147483648 .. 2147483647 )
		MAX-ACCESS			 read-only
		STATUS					 current
		DESCRIPTION			 " -- "
		::=  { sfn0avgripEntry  68 }


	plsfn0Prb66RIPAvg		 OBJECT-TYPE
		SYNTAX					 Integer32( -2147483648 .. 2147483647 )
		MAX-ACCESS			 read-only
		STATUS					 current
		DESCRIPTION			 " -- "
		::=  { sfn0avgripEntry  69 }


	plsfn0Prb67RIPAvg		 OBJECT-TYPE
		SYNTAX					 Integer32( -2147483648 .. 2147483647 )
		MAX-ACCESS			 read-only
		STATUS					 current
		DESCRIPTION			 " -- "
		::=  { sfn0avgripEntry  70 }


	plsfn0Prb68RIPAvg		 OBJECT-TYPE
		SYNTAX					 Integer32( -2147483648 .. 2147483647 )
		MAX-ACCESS			 read-only
		STATUS					 current
		DESCRIPTION			 " -- "
		::=  { sfn0avgripEntry  71 }


	plsfn0Prb69RIPAvg		 OBJECT-TYPE
		SYNTAX					 Integer32( -2147483648 .. 2147483647 )
		MAX-ACCESS			 read-only
		STATUS					 current
		DESCRIPTION			 " -- "
		::=  { sfn0avgripEntry  72 }


	plsfn0Prb70RIPAvg		 OBJECT-TYPE
		SYNTAX					 Integer32( -2147483648 .. 2147483647 )
		MAX-ACCESS			 read-only
		STATUS					 current
		DESCRIPTION			 " -- "
		::=  { sfn0avgripEntry  73 }


	plsfn0Prb71RIPAvg		 OBJECT-TYPE
		SYNTAX					 Integer32( -2147483648 .. 2147483647 )
		MAX-ACCESS			 read-only
		STATUS					 current
		DESCRIPTION			 " -- "
		::=  { sfn0avgripEntry  74 }


	plsfn0Prb72RIPAvg		 OBJECT-TYPE
		SYNTAX					 Integer32( -2147483648 .. 2147483647 )
		MAX-ACCESS			 read-only
		STATUS					 current
		DESCRIPTION			 " -- "
		::=  { sfn0avgripEntry  75 }


	plsfn0Prb73RIPAvg		 OBJECT-TYPE
		SYNTAX					 Integer32( -2147483648 .. 2147483647 )
		MAX-ACCESS			 read-only
		STATUS					 current
		DESCRIPTION			 " -- "
		::=  { sfn0avgripEntry  76 }


	plsfn0Prb74RIPAvg		 OBJECT-TYPE
		SYNTAX					 Integer32( -2147483648 .. 2147483647 )
		MAX-ACCESS			 read-only
		STATUS					 current
		DESCRIPTION			 " -- "
		::=  { sfn0avgripEntry  77 }


	plsfn0Prb75RIPAvg		 OBJECT-TYPE
		SYNTAX					 Integer32( -2147483648 .. 2147483647 )
		MAX-ACCESS			 read-only
		STATUS					 current
		DESCRIPTION			 " -- "
		::=  { sfn0avgripEntry  78 }


	plsfn0Prb76RIPAvg		 OBJECT-TYPE
		SYNTAX					 Integer32( -2147483648 .. 2147483647 )
		MAX-ACCESS			 read-only
		STATUS					 current
		DESCRIPTION			 " -- "
		::=  { sfn0avgripEntry  79 }


	plsfn0Prb77RIPAvg		 OBJECT-TYPE
		SYNTAX					 Integer32( -2147483648 .. 2147483647 )
		MAX-ACCESS			 read-only
		STATUS					 current
		DESCRIPTION			 " -- "
		::=  { sfn0avgripEntry  80 }


	plsfn0Prb78RIPAvg		 OBJECT-TYPE
		SYNTAX					 Integer32( -2147483648 .. 2147483647 )
		MAX-ACCESS			 read-only
		STATUS					 current
		DESCRIPTION			 " -- "
		::=  { sfn0avgripEntry  81 }


	plsfn0Prb79RIPAvg		 OBJECT-TYPE
		SYNTAX					 Integer32( -2147483648 .. 2147483647 )
		MAX-ACCESS			 read-only
		STATUS					 current
		DESCRIPTION			 " -- "
		::=  { sfn0avgripEntry  82 }


	plsfn0Prb80RIPAvg		 OBJECT-TYPE
		SYNTAX					 Integer32( -2147483648 .. 2147483647 )
		MAX-ACCESS			 read-only
		STATUS					 current
		DESCRIPTION			 " -- "
		::=  { sfn0avgripEntry  83 }


	plsfn0Prb81RIPAvg		 OBJECT-TYPE
		SYNTAX					 Integer32( -2147483648 .. 2147483647 )
		MAX-ACCESS			 read-only
		STATUS					 current
		DESCRIPTION			 " -- "
		::=  { sfn0avgripEntry  84 }


	plsfn0Prb82RIPAvg		 OBJECT-TYPE
		SYNTAX					 Integer32( -2147483648 .. 2147483647 )
		MAX-ACCESS			 read-only
		STATUS					 current
		DESCRIPTION			 " -- "
		::=  { sfn0avgripEntry  85 }


	plsfn0Prb83RIPAvg		 OBJECT-TYPE
		SYNTAX					 Integer32( -2147483648 .. 2147483647 )
		MAX-ACCESS			 read-only
		STATUS					 current
		DESCRIPTION			 " -- "
		::=  { sfn0avgripEntry  86 }


	plsfn0Prb84RIPAvg		 OBJECT-TYPE
		SYNTAX					 Integer32( -2147483648 .. 2147483647 )
		MAX-ACCESS			 read-only
		STATUS					 current
		DESCRIPTION			 " -- "
		::=  { sfn0avgripEntry  87 }


	plsfn0Prb85RIPAvg		 OBJECT-TYPE
		SYNTAX					 Integer32( -2147483648 .. 2147483647 )
		MAX-ACCESS			 read-only
		STATUS					 current
		DESCRIPTION			 " -- "
		::=  { sfn0avgripEntry  88 }


	plsfn0Prb86RIPAvg		 OBJECT-TYPE
		SYNTAX					 Integer32( -2147483648 .. 2147483647 )
		MAX-ACCESS			 read-only
		STATUS					 current
		DESCRIPTION			 " -- "
		::=  { sfn0avgripEntry  89 }


	plsfn0Prb87RIPAvg		 OBJECT-TYPE
		SYNTAX					 Integer32( -2147483648 .. 2147483647 )
		MAX-ACCESS			 read-only
		STATUS					 current
		DESCRIPTION			 " -- "
		::=  { sfn0avgripEntry  90 }


	plsfn0Prb88RIPAvg		 OBJECT-TYPE
		SYNTAX					 Integer32( -2147483648 .. 2147483647 )
		MAX-ACCESS			 read-only
		STATUS					 current
		DESCRIPTION			 " -- "
		::=  { sfn0avgripEntry  91 }


	plsfn0Prb89RIPAvg		 OBJECT-TYPE
		SYNTAX					 Integer32( -2147483648 .. 2147483647 )
		MAX-ACCESS			 read-only
		STATUS					 current
		DESCRIPTION			 " -- "
		::=  { sfn0avgripEntry  92 }


	plsfn0Prb90RIPAvg		 OBJECT-TYPE
		SYNTAX					 Integer32( -2147483648 .. 2147483647 )
		MAX-ACCESS			 read-only
		STATUS					 current
		DESCRIPTION			 " -- "
		::=  { sfn0avgripEntry  93 }


	plsfn0Prb91RIPAvg		 OBJECT-TYPE
		SYNTAX					 Integer32( -2147483648 .. 2147483647 )
		MAX-ACCESS			 read-only
		STATUS					 current
		DESCRIPTION			 " -- "
		::=  { sfn0avgripEntry  94 }


	plsfn0Prb92RIPAvg		 OBJECT-TYPE
		SYNTAX					 Integer32( -2147483648 .. 2147483647 )
		MAX-ACCESS			 read-only
		STATUS					 current
		DESCRIPTION			 " -- "
		::=  { sfn0avgripEntry  95 }


	plsfn0Prb93RIPAvg		 OBJECT-TYPE
		SYNTAX					 Integer32( -2147483648 .. 2147483647 )
		MAX-ACCESS			 read-only
		STATUS					 current
		DESCRIPTION			 " -- "
		::=  { sfn0avgripEntry  96 }


	plsfn0Prb94RIPAvg		 OBJECT-TYPE
		SYNTAX					 Integer32( -2147483648 .. 2147483647 )
		MAX-ACCESS			 read-only
		STATUS					 current
		DESCRIPTION			 " -- "
		::=  { sfn0avgripEntry  97 }


	plsfn0Prb95RIPAvg		 OBJECT-TYPE
		SYNTAX					 Integer32( -2147483648 .. 2147483647 )
		MAX-ACCESS			 read-only
		STATUS					 current
		DESCRIPTION			 " -- "
		::=  { sfn0avgripEntry  98 }


	plsfn0Prb96RIPAvg		 OBJECT-TYPE
		SYNTAX					 Integer32( -2147483648 .. 2147483647 )
		MAX-ACCESS			 read-only
		STATUS					 current
		DESCRIPTION			 " -- "
		::=  { sfn0avgripEntry  99 }


	plsfn0Prb97RIPAvg		 OBJECT-TYPE
		SYNTAX					 Integer32( -2147483648 .. 2147483647 )
		MAX-ACCESS			 read-only
		STATUS					 current
		DESCRIPTION			 " -- "
		::=  { sfn0avgripEntry  100 }


	plsfn0Prb98RIPAvg		 OBJECT-TYPE
		SYNTAX					 Integer32( -2147483648 .. 2147483647 )
		MAX-ACCESS			 read-only
		STATUS					 current
		DESCRIPTION			 " -- "
		::=  { sfn0avgripEntry  101 }


	plsfn0Prb99RIPAvg		 OBJECT-TYPE
		SYNTAX					 Integer32( -2147483648 .. 2147483647 )
		MAX-ACCESS			 read-only
		STATUS					 current
		DESCRIPTION			 " -- "
		::=  { sfn0avgripEntry  102 }


	sfn2avgripTable		 OBJECT-TYPE
		SYNTAX					 SEQUENCE  OF	 Sfn2avgripEntry
		MAX-ACCESS			 not-accessible
		STATUS					 current
		DESCRIPTION			 " -- "
		::=  { plrelatedOriginCounter  6 }


	sfn2avgripEntry		 OBJECT-TYPE
		SYNTAX					 Sfn2avgripEntry
		MAX-ACCESS			 not-accessible
		STATUS					 current
		DESCRIPTION			 " -- "
		INDEX						{ sfn2avgripLcId }
		::=  { sfn2avgripTable  1 }


	Sfn2avgripEntry		 ::=  SEQUENCE {
		sfn2avgripLcId					Integer32,
		sfn2avgripRowStatus					RowStatus,
		plsfn2Prb00RIPAvg					Integer32,
		plsfn2Prb01RIPAvg					Integer32,
		plsfn2Prb02RIPAvg					Integer32,
		plsfn2Prb03RIPAvg					Integer32,
		plsfn2Prb04RIPAvg					Integer32,
		plsfn2Prb05RIPAvg					Integer32,
		plsfn2Prb06RIPAvg					Integer32,
		plsfn2Prb07RIPAvg					Integer32,
		plsfn2Prb08RIPAvg					Integer32,
		plsfn2Prb09RIPAvg					Integer32,
		plsfn2Prb10RIPAvg					Integer32,
		plsfn2Prb11RIPAvg					Integer32,
		plsfn2Prb12RIPAvg					Integer32,
		plsfn2Prb13RIPAvg					Integer32,
		plsfn2Prb14RIPAvg					Integer32,
		plsfn2Prb15RIPAvg					Integer32,
		plsfn2Prb16RIPAvg					Integer32,
		plsfn2Prb17RIPAvg					Integer32,
		plsfn2Prb18RIPAvg					Integer32,
		plsfn2Prb19RIPAvg					Integer32,
		plsfn2Prb20RIPAvg					Integer32,
		plsfn2Prb21RIPAvg					Integer32,
		plsfn2Prb22RIPAvg					Integer32,
		plsfn2Prb23RIPAvg					Integer32,
		plsfn2Prb24RIPAvg					Integer32,
		plsfn2Prb25RIPAvg					Integer32,
		plsfn2Prb26RIPAvg					Integer32,
		plsfn2Prb27RIPAvg					Integer32,
		plsfn2Prb28RIPAvg					Integer32,
		plsfn2Prb29RIPAvg					Integer32,
		plsfn2Prb30RIPAvg					Integer32,
		plsfn2Prb31RIPAvg					Integer32,
		plsfn2Prb32RIPAvg					Integer32,
		plsfn2Prb33RIPAvg					Integer32,
		plsfn2Prb34RIPAvg					Integer32,
		plsfn2Prb35RIPAvg					Integer32,
		plsfn2Prb36RIPAvg					Integer32,
		plsfn2Prb37RIPAvg					Integer32,
		plsfn2Prb38RIPAvg					Integer32,
		plsfn2Prb39RIPAvg					Integer32,
		plsfn2Prb40RIPAvg					Integer32,
		plsfn2Prb41RIPAvg					Integer32,
		plsfn2Prb42RIPAvg					Integer32,
		plsfn2Prb43RIPAvg					Integer32,
		plsfn2Prb44RIPAvg					Integer32,
		plsfn2Prb45RIPAvg					Integer32,
		plsfn2Prb46RIPAvg					Integer32,
		plsfn2Prb47RIPAvg					Integer32,
		plsfn2Prb48RIPAvg					Integer32,
		plsfn2Prb49RIPAvg					Integer32,
		plsfn2Prb50RIPAvg					Integer32,
		plsfn2Prb51RIPAvg					Integer32,
		plsfn2Prb52RIPAvg					Integer32,
		plsfn2Prb53RIPAvg					Integer32,
		plsfn2Prb54RIPAvg					Integer32,
		plsfn2Prb55RIPAvg					Integer32,
		plsfn2Prb56RIPAvg					Integer32,
		plsfn2Prb57RIPAvg					Integer32,
		plsfn2Prb58RIPAvg					Integer32,
		plsfn2Prb59RIPAvg					Integer32,
		plsfn2Prb60RIPAvg					Integer32,
		plsfn2Prb61RIPAvg					Integer32,
		plsfn2Prb62RIPAvg					Integer32,
		plsfn2Prb63RIPAvg					Integer32,
		plsfn2Prb64RIPAvg					Integer32,
		plsfn2Prb65RIPAvg					Integer32,
		plsfn2Prb66RIPAvg					Integer32,
		plsfn2Prb67RIPAvg					Integer32,
		plsfn2Prb68RIPAvg					Integer32,
		plsfn2Prb69RIPAvg					Integer32,
		plsfn2Prb70RIPAvg					Integer32,
		plsfn2Prb71RIPAvg					Integer32,
		plsfn2Prb72RIPAvg					Integer32,
		plsfn2Prb73RIPAvg					Integer32,
		plsfn2Prb74RIPAvg					Integer32,
		plsfn2Prb75RIPAvg					Integer32,
		plsfn2Prb76RIPAvg					Integer32,
		plsfn2Prb77RIPAvg					Integer32,
		plsfn2Prb78RIPAvg					Integer32,
		plsfn2Prb79RIPAvg					Integer32,
		plsfn2Prb80RIPAvg					Integer32,
		plsfn2Prb81RIPAvg					Integer32,
		plsfn2Prb82RIPAvg					Integer32,
		plsfn2Prb83RIPAvg					Integer32,
		plsfn2Prb84RIPAvg					Integer32,
		plsfn2Prb85RIPAvg					Integer32,
		plsfn2Prb86RIPAvg					Integer32,
		plsfn2Prb87RIPAvg					Integer32,
		plsfn2Prb88RIPAvg					Integer32,
		plsfn2Prb89RIPAvg					Integer32,
		plsfn2Prb90RIPAvg					Integer32,
		plsfn2Prb91RIPAvg					Integer32,
		plsfn2Prb92RIPAvg					Integer32,
		plsfn2Prb93RIPAvg					Integer32,
		plsfn2Prb94RIPAvg					Integer32,
		plsfn2Prb95RIPAvg					Integer32,
		plsfn2Prb96RIPAvg					Integer32,
		plsfn2Prb97RIPAvg					Integer32,
		plsfn2Prb98RIPAvg					Integer32,
		plsfn2Prb99RIPAvg					Integer32
		}


	sfn2avgripLcId		 OBJECT-TYPE
		SYNTAX					 Integer32( 0 .. 23 )
		MAX-ACCESS			 not-accessible
		STATUS					 current
		DESCRIPTION			 " -- "
		::=  { sfn2avgripEntry  1 }


	sfn2avgripRowStatus		 OBJECT-TYPE
		SYNTAX					 RowStatus
		MAX-ACCESS			 read-only
		STATUS					 current
		DESCRIPTION			 " -- "
		::=  { sfn2avgripEntry  2 }


	plsfn2Prb00RIPAvg		 OBJECT-TYPE
		SYNTAX					 Integer32( -2147483648 .. 2147483647 )
		MAX-ACCESS			 read-only
		STATUS					 current
		DESCRIPTION			 " -- "
		::=  { sfn2avgripEntry  3 }


	plsfn2Prb01RIPAvg		 OBJECT-TYPE
		SYNTAX					 Integer32( -2147483648 .. 2147483647 )
		MAX-ACCESS			 read-only
		STATUS					 current
		DESCRIPTION			 " -- "
		::=  { sfn2avgripEntry  4 }


	plsfn2Prb02RIPAvg		 OBJECT-TYPE
		SYNTAX					 Integer32( -2147483648 .. 2147483647 )
		MAX-ACCESS			 read-only
		STATUS					 current
		DESCRIPTION			 " -- "
		::=  { sfn2avgripEntry  5 }


	plsfn2Prb03RIPAvg		 OBJECT-TYPE
		SYNTAX					 Integer32( -2147483648 .. 2147483647 )
		MAX-ACCESS			 read-only
		STATUS					 current
		DESCRIPTION			 " -- "
		::=  { sfn2avgripEntry  6 }


	plsfn2Prb04RIPAvg		 OBJECT-TYPE
		SYNTAX					 Integer32( -2147483648 .. 2147483647 )
		MAX-ACCESS			 read-only
		STATUS					 current
		DESCRIPTION			 " -- "
		::=  { sfn2avgripEntry  7 }


	plsfn2Prb05RIPAvg		 OBJECT-TYPE
		SYNTAX					 Integer32( -2147483648 .. 2147483647 )
		MAX-ACCESS			 read-only
		STATUS					 current
		DESCRIPTION			 " -- "
		::=  { sfn2avgripEntry  8 }


	plsfn2Prb06RIPAvg		 OBJECT-TYPE
		SYNTAX					 Integer32( -2147483648 .. 2147483647 )
		MAX-ACCESS			 read-only
		STATUS					 current
		DESCRIPTION			 " -- "
		::=  { sfn2avgripEntry  9 }


	plsfn2Prb07RIPAvg		 OBJECT-TYPE
		SYNTAX					 Integer32( -2147483648 .. 2147483647 )
		MAX-ACCESS			 read-only
		STATUS					 current
		DESCRIPTION			 " -- "
		::=  { sfn2avgripEntry  10 }


	plsfn2Prb08RIPAvg		 OBJECT-TYPE
		SYNTAX					 Integer32( -2147483648 .. 2147483647 )
		MAX-ACCESS			 read-only
		STATUS					 current
		DESCRIPTION			 " -- "
		::=  { sfn2avgripEntry  11 }


	plsfn2Prb09RIPAvg		 OBJECT-TYPE
		SYNTAX					 Integer32( -2147483648 .. 2147483647 )
		MAX-ACCESS			 read-only
		STATUS					 current
		DESCRIPTION			 " -- "
		::=  { sfn2avgripEntry  12 }


	plsfn2Prb10RIPAvg		 OBJECT-TYPE
		SYNTAX					 Integer32( -2147483648 .. 2147483647 )
		MAX-ACCESS			 read-only
		STATUS					 current
		DESCRIPTION			 " -- "
		::=  { sfn2avgripEntry  13 }


	plsfn2Prb11RIPAvg		 OBJECT-TYPE
		SYNTAX					 Integer32( -2147483648 .. 2147483647 )
		MAX-ACCESS			 read-only
		STATUS					 current
		DESCRIPTION			 " -- "
		::=  { sfn2avgripEntry  14 }


	plsfn2Prb12RIPAvg		 OBJECT-TYPE
		SYNTAX					 Integer32( -2147483648 .. 2147483647 )
		MAX-ACCESS			 read-only
		STATUS					 current
		DESCRIPTION			 " -- "
		::=  { sfn2avgripEntry  15 }


	plsfn2Prb13RIPAvg		 OBJECT-TYPE
		SYNTAX					 Integer32( -2147483648 .. 2147483647 )
		MAX-ACCESS			 read-only
		STATUS					 current
		DESCRIPTION			 " -- "
		::=  { sfn2avgripEntry  16 }


	plsfn2Prb14RIPAvg		 OBJECT-TYPE
		SYNTAX					 Integer32( -2147483648 .. 2147483647 )
		MAX-ACCESS			 read-only
		STATUS					 current
		DESCRIPTION			 " -- "
		::=  { sfn2avgripEntry  17 }


	plsfn2Prb15RIPAvg		 OBJECT-TYPE
		SYNTAX					 Integer32( -2147483648 .. 2147483647 )
		MAX-ACCESS			 read-only
		STATUS					 current
		DESCRIPTION			 " -- "
		::=  { sfn2avgripEntry  18 }


	plsfn2Prb16RIPAvg		 OBJECT-TYPE
		SYNTAX					 Integer32( -2147483648 .. 2147483647 )
		MAX-ACCESS			 read-only
		STATUS					 current
		DESCRIPTION			 " -- "
		::=  { sfn2avgripEntry  19 }


	plsfn2Prb17RIPAvg		 OBJECT-TYPE
		SYNTAX					 Integer32( -2147483648 .. 2147483647 )
		MAX-ACCESS			 read-only
		STATUS					 current
		DESCRIPTION			 " -- "
		::=  { sfn2avgripEntry  20 }


	plsfn2Prb18RIPAvg		 OBJECT-TYPE
		SYNTAX					 Integer32( -2147483648 .. 2147483647 )
		MAX-ACCESS			 read-only
		STATUS					 current
		DESCRIPTION			 " -- "
		::=  { sfn2avgripEntry  21 }


	plsfn2Prb19RIPAvg		 OBJECT-TYPE
		SYNTAX					 Integer32( -2147483648 .. 2147483647 )
		MAX-ACCESS			 read-only
		STATUS					 current
		DESCRIPTION			 " -- "
		::=  { sfn2avgripEntry  22 }


	plsfn2Prb20RIPAvg		 OBJECT-TYPE
		SYNTAX					 Integer32( -2147483648 .. 2147483647 )
		MAX-ACCESS			 read-only
		STATUS					 current
		DESCRIPTION			 " -- "
		::=  { sfn2avgripEntry  23 }


	plsfn2Prb21RIPAvg		 OBJECT-TYPE
		SYNTAX					 Integer32( -2147483648 .. 2147483647 )
		MAX-ACCESS			 read-only
		STATUS					 current
		DESCRIPTION			 " -- "
		::=  { sfn2avgripEntry  24 }


	plsfn2Prb22RIPAvg		 OBJECT-TYPE
		SYNTAX					 Integer32( -2147483648 .. 2147483647 )
		MAX-ACCESS			 read-only
		STATUS					 current
		DESCRIPTION			 " -- "
		::=  { sfn2avgripEntry  25 }


	plsfn2Prb23RIPAvg		 OBJECT-TYPE
		SYNTAX					 Integer32( -2147483648 .. 2147483647 )
		MAX-ACCESS			 read-only
		STATUS					 current
		DESCRIPTION			 " -- "
		::=  { sfn2avgripEntry  26 }


	plsfn2Prb24RIPAvg		 OBJECT-TYPE
		SYNTAX					 Integer32( -2147483648 .. 2147483647 )
		MAX-ACCESS			 read-only
		STATUS					 current
		DESCRIPTION			 " -- "
		::=  { sfn2avgripEntry  27 }


	plsfn2Prb25RIPAvg		 OBJECT-TYPE
		SYNTAX					 Integer32( -2147483648 .. 2147483647 )
		MAX-ACCESS			 read-only
		STATUS					 current
		DESCRIPTION			 " -- "
		::=  { sfn2avgripEntry  28 }


	plsfn2Prb26RIPAvg		 OBJECT-TYPE
		SYNTAX					 Integer32( -2147483648 .. 2147483647 )
		MAX-ACCESS			 read-only
		STATUS					 current
		DESCRIPTION			 " -- "
		::=  { sfn2avgripEntry  29 }


	plsfn2Prb27RIPAvg		 OBJECT-TYPE
		SYNTAX					 Integer32( -2147483648 .. 2147483647 )
		MAX-ACCESS			 read-only
		STATUS					 current
		DESCRIPTION			 " -- "
		::=  { sfn2avgripEntry  30 }


	plsfn2Prb28RIPAvg		 OBJECT-TYPE
		SYNTAX					 Integer32( -2147483648 .. 2147483647 )
		MAX-ACCESS			 read-only
		STATUS					 current
		DESCRIPTION			 " -- "
		::=  { sfn2avgripEntry  31 }


	plsfn2Prb29RIPAvg		 OBJECT-TYPE
		SYNTAX					 Integer32( -2147483648 .. 2147483647 )
		MAX-ACCESS			 read-only
		STATUS					 current
		DESCRIPTION			 " -- "
		::=  { sfn2avgripEntry  32 }


	plsfn2Prb30RIPAvg		 OBJECT-TYPE
		SYNTAX					 Integer32( -2147483648 .. 2147483647 )
		MAX-ACCESS			 read-only
		STATUS					 current
		DESCRIPTION			 " -- "
		::=  { sfn2avgripEntry  33 }


	plsfn2Prb31RIPAvg		 OBJECT-TYPE
		SYNTAX					 Integer32( -2147483648 .. 2147483647 )
		MAX-ACCESS			 read-only
		STATUS					 current
		DESCRIPTION			 " -- "
		::=  { sfn2avgripEntry  34 }


	plsfn2Prb32RIPAvg		 OBJECT-TYPE
		SYNTAX					 Integer32( -2147483648 .. 2147483647 )
		MAX-ACCESS			 read-only
		STATUS					 current
		DESCRIPTION			 " -- "
		::=  { sfn2avgripEntry  35 }


	plsfn2Prb33RIPAvg		 OBJECT-TYPE
		SYNTAX					 Integer32( -2147483648 .. 2147483647 )
		MAX-ACCESS			 read-only
		STATUS					 current
		DESCRIPTION			 " -- "
		::=  { sfn2avgripEntry  36 }


	plsfn2Prb34RIPAvg		 OBJECT-TYPE
		SYNTAX					 Integer32( -2147483648 .. 2147483647 )
		MAX-ACCESS			 read-only
		STATUS					 current
		DESCRIPTION			 " -- "
		::=  { sfn2avgripEntry  37 }


	plsfn2Prb35RIPAvg		 OBJECT-TYPE
		SYNTAX					 Integer32( -2147483648 .. 2147483647 )
		MAX-ACCESS			 read-only
		STATUS					 current
		DESCRIPTION			 " -- "
		::=  { sfn2avgripEntry  38 }


	plsfn2Prb36RIPAvg		 OBJECT-TYPE
		SYNTAX					 Integer32( -2147483648 .. 2147483647 )
		MAX-ACCESS			 read-only
		STATUS					 current
		DESCRIPTION			 " -- "
		::=  { sfn2avgripEntry  39 }


	plsfn2Prb37RIPAvg		 OBJECT-TYPE
		SYNTAX					 Integer32( -2147483648 .. 2147483647 )
		MAX-ACCESS			 read-only
		STATUS					 current
		DESCRIPTION			 " -- "
		::=  { sfn2avgripEntry  40 }


	plsfn2Prb38RIPAvg		 OBJECT-TYPE
		SYNTAX					 Integer32( -2147483648 .. 2147483647 )
		MAX-ACCESS			 read-only
		STATUS					 current
		DESCRIPTION			 " -- "
		::=  { sfn2avgripEntry  41 }


	plsfn2Prb39RIPAvg		 OBJECT-TYPE
		SYNTAX					 Integer32( -2147483648 .. 2147483647 )
		MAX-ACCESS			 read-only
		STATUS					 current
		DESCRIPTION			 " -- "
		::=  { sfn2avgripEntry  42 }


	plsfn2Prb40RIPAvg		 OBJECT-TYPE
		SYNTAX					 Integer32( -2147483648 .. 2147483647 )
		MAX-ACCESS			 read-only
		STATUS					 current
		DESCRIPTION			 " -- "
		::=  { sfn2avgripEntry  43 }


	plsfn2Prb41RIPAvg		 OBJECT-TYPE
		SYNTAX					 Integer32( -2147483648 .. 2147483647 )
		MAX-ACCESS			 read-only
		STATUS					 current
		DESCRIPTION			 " -- "
		::=  { sfn2avgripEntry  44 }


	plsfn2Prb42RIPAvg		 OBJECT-TYPE
		SYNTAX					 Integer32( -2147483648 .. 2147483647 )
		MAX-ACCESS			 read-only
		STATUS					 current
		DESCRIPTION			 " -- "
		::=  { sfn2avgripEntry  45 }


	plsfn2Prb43RIPAvg		 OBJECT-TYPE
		SYNTAX					 Integer32( -2147483648 .. 2147483647 )
		MAX-ACCESS			 read-only
		STATUS					 current
		DESCRIPTION			 " -- "
		::=  { sfn2avgripEntry  46 }


	plsfn2Prb44RIPAvg		 OBJECT-TYPE
		SYNTAX					 Integer32( -2147483648 .. 2147483647 )
		MAX-ACCESS			 read-only
		STATUS					 current
		DESCRIPTION			 " -- "
		::=  { sfn2avgripEntry  47 }


	plsfn2Prb45RIPAvg		 OBJECT-TYPE
		SYNTAX					 Integer32( -2147483648 .. 2147483647 )
		MAX-ACCESS			 read-only
		STATUS					 current
		DESCRIPTION			 " -- "
		::=  { sfn2avgripEntry  48 }


	plsfn2Prb46RIPAvg		 OBJECT-TYPE
		SYNTAX					 Integer32( -2147483648 .. 2147483647 )
		MAX-ACCESS			 read-only
		STATUS					 current
		DESCRIPTION			 " -- "
		::=  { sfn2avgripEntry  49 }


	plsfn2Prb47RIPAvg		 OBJECT-TYPE
		SYNTAX					 Integer32( -2147483648 .. 2147483647 )
		MAX-ACCESS			 read-only
		STATUS					 current
		DESCRIPTION			 " -- "
		::=  { sfn2avgripEntry  50 }


	plsfn2Prb48RIPAvg		 OBJECT-TYPE
		SYNTAX					 Integer32( -2147483648 .. 2147483647 )
		MAX-ACCESS			 read-only
		STATUS					 current
		DESCRIPTION			 " -- "
		::=  { sfn2avgripEntry  51 }


	plsfn2Prb49RIPAvg		 OBJECT-TYPE
		SYNTAX					 Integer32( -2147483648 .. 2147483647 )
		MAX-ACCESS			 read-only
		STATUS					 current
		DESCRIPTION			 " -- "
		::=  { sfn2avgripEntry  52 }


	plsfn2Prb50RIPAvg		 OBJECT-TYPE
		SYNTAX					 Integer32( -2147483648 .. 2147483647 )
		MAX-ACCESS			 read-only
		STATUS					 current
		DESCRIPTION			 " -- "
		::=  { sfn2avgripEntry  53 }


	plsfn2Prb51RIPAvg		 OBJECT-TYPE
		SYNTAX					 Integer32( -2147483648 .. 2147483647 )
		MAX-ACCESS			 read-only
		STATUS					 current
		DESCRIPTION			 " -- "
		::=  { sfn2avgripEntry  54 }


	plsfn2Prb52RIPAvg		 OBJECT-TYPE
		SYNTAX					 Integer32( -2147483648 .. 2147483647 )
		MAX-ACCESS			 read-only
		STATUS					 current
		DESCRIPTION			 " -- "
		::=  { sfn2avgripEntry  55 }


	plsfn2Prb53RIPAvg		 OBJECT-TYPE
		SYNTAX					 Integer32( -2147483648 .. 2147483647 )
		MAX-ACCESS			 read-only
		STATUS					 current
		DESCRIPTION			 " -- "
		::=  { sfn2avgripEntry  56 }


	plsfn2Prb54RIPAvg		 OBJECT-TYPE
		SYNTAX					 Integer32( -2147483648 .. 2147483647 )
		MAX-ACCESS			 read-only
		STATUS					 current
		DESCRIPTION			 " -- "
		::=  { sfn2avgripEntry  57 }


	plsfn2Prb55RIPAvg		 OBJECT-TYPE
		SYNTAX					 Integer32( -2147483648 .. 2147483647 )
		MAX-ACCESS			 read-only
		STATUS					 current
		DESCRIPTION			 " -- "
		::=  { sfn2avgripEntry  58 }


	plsfn2Prb56RIPAvg		 OBJECT-TYPE
		SYNTAX					 Integer32( -2147483648 .. 2147483647 )
		MAX-ACCESS			 read-only
		STATUS					 current
		DESCRIPTION			 " -- "
		::=  { sfn2avgripEntry  59 }


	plsfn2Prb57RIPAvg		 OBJECT-TYPE
		SYNTAX					 Integer32( -2147483648 .. 2147483647 )
		MAX-ACCESS			 read-only
		STATUS					 current
		DESCRIPTION			 " -- "
		::=  { sfn2avgripEntry  60 }


	plsfn2Prb58RIPAvg		 OBJECT-TYPE
		SYNTAX					 Integer32( -2147483648 .. 2147483647 )
		MAX-ACCESS			 read-only
		STATUS					 current
		DESCRIPTION			 " -- "
		::=  { sfn2avgripEntry  61 }


	plsfn2Prb59RIPAvg		 OBJECT-TYPE
		SYNTAX					 Integer32( -2147483648 .. 2147483647 )
		MAX-ACCESS			 read-only
		STATUS					 current
		DESCRIPTION			 " -- "
		::=  { sfn2avgripEntry  62 }


	plsfn2Prb60RIPAvg		 OBJECT-TYPE
		SYNTAX					 Integer32( -2147483648 .. 2147483647 )
		MAX-ACCESS			 read-only
		STATUS					 current
		DESCRIPTION			 " -- "
		::=  { sfn2avgripEntry  63 }


	plsfn2Prb61RIPAvg		 OBJECT-TYPE
		SYNTAX					 Integer32( -2147483648 .. 2147483647 )
		MAX-ACCESS			 read-only
		STATUS					 current
		DESCRIPTION			 " -- "
		::=  { sfn2avgripEntry  64 }


	plsfn2Prb62RIPAvg		 OBJECT-TYPE
		SYNTAX					 Integer32( -2147483648 .. 2147483647 )
		MAX-ACCESS			 read-only
		STATUS					 current
		DESCRIPTION			 " -- "
		::=  { sfn2avgripEntry  65 }


	plsfn2Prb63RIPAvg		 OBJECT-TYPE
		SYNTAX					 Integer32( -2147483648 .. 2147483647 )
		MAX-ACCESS			 read-only
		STATUS					 current
		DESCRIPTION			 " -- "
		::=  { sfn2avgripEntry  66 }


	plsfn2Prb64RIPAvg		 OBJECT-TYPE
		SYNTAX					 Integer32( -2147483648 .. 2147483647 )
		MAX-ACCESS			 read-only
		STATUS					 current
		DESCRIPTION			 " -- "
		::=  { sfn2avgripEntry  67 }


	plsfn2Prb65RIPAvg		 OBJECT-TYPE
		SYNTAX					 Integer32( -2147483648 .. 2147483647 )
		MAX-ACCESS			 read-only
		STATUS					 current
		DESCRIPTION			 " -- "
		::=  { sfn2avgripEntry  68 }


	plsfn2Prb66RIPAvg		 OBJECT-TYPE
		SYNTAX					 Integer32( -2147483648 .. 2147483647 )
		MAX-ACCESS			 read-only
		STATUS					 current
		DESCRIPTION			 " -- "
		::=  { sfn2avgripEntry  69 }


	plsfn2Prb67RIPAvg		 OBJECT-TYPE
		SYNTAX					 Integer32( -2147483648 .. 2147483647 )
		MAX-ACCESS			 read-only
		STATUS					 current
		DESCRIPTION			 " -- "
		::=  { sfn2avgripEntry  70 }


	plsfn2Prb68RIPAvg		 OBJECT-TYPE
		SYNTAX					 Integer32( -2147483648 .. 2147483647 )
		MAX-ACCESS			 read-only
		STATUS					 current
		DESCRIPTION			 " -- "
		::=  { sfn2avgripEntry  71 }


	plsfn2Prb69RIPAvg		 OBJECT-TYPE
		SYNTAX					 Integer32( -2147483648 .. 2147483647 )
		MAX-ACCESS			 read-only
		STATUS					 current
		DESCRIPTION			 " -- "
		::=  { sfn2avgripEntry  72 }


	plsfn2Prb70RIPAvg		 OBJECT-TYPE
		SYNTAX					 Integer32( -2147483648 .. 2147483647 )
		MAX-ACCESS			 read-only
		STATUS					 current
		DESCRIPTION			 " -- "
		::=  { sfn2avgripEntry  73 }


	plsfn2Prb71RIPAvg		 OBJECT-TYPE
		SYNTAX					 Integer32( -2147483648 .. 2147483647 )
		MAX-ACCESS			 read-only
		STATUS					 current
		DESCRIPTION			 " -- "
		::=  { sfn2avgripEntry  74 }


	plsfn2Prb72RIPAvg		 OBJECT-TYPE
		SYNTAX					 Integer32( -2147483648 .. 2147483647 )
		MAX-ACCESS			 read-only
		STATUS					 current
		DESCRIPTION			 " -- "
		::=  { sfn2avgripEntry  75 }


	plsfn2Prb73RIPAvg		 OBJECT-TYPE
		SYNTAX					 Integer32( -2147483648 .. 2147483647 )
		MAX-ACCESS			 read-only
		STATUS					 current
		DESCRIPTION			 " -- "
		::=  { sfn2avgripEntry  76 }


	plsfn2Prb74RIPAvg		 OBJECT-TYPE
		SYNTAX					 Integer32( -2147483648 .. 2147483647 )
		MAX-ACCESS			 read-only
		STATUS					 current
		DESCRIPTION			 " -- "
		::=  { sfn2avgripEntry  77 }


	plsfn2Prb75RIPAvg		 OBJECT-TYPE
		SYNTAX					 Integer32( -2147483648 .. 2147483647 )
		MAX-ACCESS			 read-only
		STATUS					 current
		DESCRIPTION			 " -- "
		::=  { sfn2avgripEntry  78 }


	plsfn2Prb76RIPAvg		 OBJECT-TYPE
		SYNTAX					 Integer32( -2147483648 .. 2147483647 )
		MAX-ACCESS			 read-only
		STATUS					 current
		DESCRIPTION			 " -- "
		::=  { sfn2avgripEntry  79 }


	plsfn2Prb77RIPAvg		 OBJECT-TYPE
		SYNTAX					 Integer32( -2147483648 .. 2147483647 )
		MAX-ACCESS			 read-only
		STATUS					 current
		DESCRIPTION			 " -- "
		::=  { sfn2avgripEntry  80 }


	plsfn2Prb78RIPAvg		 OBJECT-TYPE
		SYNTAX					 Integer32( -2147483648 .. 2147483647 )
		MAX-ACCESS			 read-only
		STATUS					 current
		DESCRIPTION			 " -- "
		::=  { sfn2avgripEntry  81 }


	plsfn2Prb79RIPAvg		 OBJECT-TYPE
		SYNTAX					 Integer32( -2147483648 .. 2147483647 )
		MAX-ACCESS			 read-only
		STATUS					 current
		DESCRIPTION			 " -- "
		::=  { sfn2avgripEntry  82 }


	plsfn2Prb80RIPAvg		 OBJECT-TYPE
		SYNTAX					 Integer32( -2147483648 .. 2147483647 )
		MAX-ACCESS			 read-only
		STATUS					 current
		DESCRIPTION			 " -- "
		::=  { sfn2avgripEntry  83 }


	plsfn2Prb81RIPAvg		 OBJECT-TYPE
		SYNTAX					 Integer32( -2147483648 .. 2147483647 )
		MAX-ACCESS			 read-only
		STATUS					 current
		DESCRIPTION			 " -- "
		::=  { sfn2avgripEntry  84 }


	plsfn2Prb82RIPAvg		 OBJECT-TYPE
		SYNTAX					 Integer32( -2147483648 .. 2147483647 )
		MAX-ACCESS			 read-only
		STATUS					 current
		DESCRIPTION			 " -- "
		::=  { sfn2avgripEntry  85 }


	plsfn2Prb83RIPAvg		 OBJECT-TYPE
		SYNTAX					 Integer32( -2147483648 .. 2147483647 )
		MAX-ACCESS			 read-only
		STATUS					 current
		DESCRIPTION			 " -- "
		::=  { sfn2avgripEntry  86 }


	plsfn2Prb84RIPAvg		 OBJECT-TYPE
		SYNTAX					 Integer32( -2147483648 .. 2147483647 )
		MAX-ACCESS			 read-only
		STATUS					 current
		DESCRIPTION			 " -- "
		::=  { sfn2avgripEntry  87 }


	plsfn2Prb85RIPAvg		 OBJECT-TYPE
		SYNTAX					 Integer32( -2147483648 .. 2147483647 )
		MAX-ACCESS			 read-only
		STATUS					 current
		DESCRIPTION			 " -- "
		::=  { sfn2avgripEntry  88 }


	plsfn2Prb86RIPAvg		 OBJECT-TYPE
		SYNTAX					 Integer32( -2147483648 .. 2147483647 )
		MAX-ACCESS			 read-only
		STATUS					 current
		DESCRIPTION			 " -- "
		::=  { sfn2avgripEntry  89 }


	plsfn2Prb87RIPAvg		 OBJECT-TYPE
		SYNTAX					 Integer32( -2147483648 .. 2147483647 )
		MAX-ACCESS			 read-only
		STATUS					 current
		DESCRIPTION			 " -- "
		::=  { sfn2avgripEntry  90 }


	plsfn2Prb88RIPAvg		 OBJECT-TYPE
		SYNTAX					 Integer32( -2147483648 .. 2147483647 )
		MAX-ACCESS			 read-only
		STATUS					 current
		DESCRIPTION			 " -- "
		::=  { sfn2avgripEntry  91 }


	plsfn2Prb89RIPAvg		 OBJECT-TYPE
		SYNTAX					 Integer32( -2147483648 .. 2147483647 )
		MAX-ACCESS			 read-only
		STATUS					 current
		DESCRIPTION			 " -- "
		::=  { sfn2avgripEntry  92 }


	plsfn2Prb90RIPAvg		 OBJECT-TYPE
		SYNTAX					 Integer32( -2147483648 .. 2147483647 )
		MAX-ACCESS			 read-only
		STATUS					 current
		DESCRIPTION			 " -- "
		::=  { sfn2avgripEntry  93 }


	plsfn2Prb91RIPAvg		 OBJECT-TYPE
		SYNTAX					 Integer32( -2147483648 .. 2147483647 )
		MAX-ACCESS			 read-only
		STATUS					 current
		DESCRIPTION			 " -- "
		::=  { sfn2avgripEntry  94 }


	plsfn2Prb92RIPAvg		 OBJECT-TYPE
		SYNTAX					 Integer32( -2147483648 .. 2147483647 )
		MAX-ACCESS			 read-only
		STATUS					 current
		DESCRIPTION			 " -- "
		::=  { sfn2avgripEntry  95 }


	plsfn2Prb93RIPAvg		 OBJECT-TYPE
		SYNTAX					 Integer32( -2147483648 .. 2147483647 )
		MAX-ACCESS			 read-only
		STATUS					 current
		DESCRIPTION			 " -- "
		::=  { sfn2avgripEntry  96 }


	plsfn2Prb94RIPAvg		 OBJECT-TYPE
		SYNTAX					 Integer32( -2147483648 .. 2147483647 )
		MAX-ACCESS			 read-only
		STATUS					 current
		DESCRIPTION			 " -- "
		::=  { sfn2avgripEntry  97 }


	plsfn2Prb95RIPAvg		 OBJECT-TYPE
		SYNTAX					 Integer32( -2147483648 .. 2147483647 )
		MAX-ACCESS			 read-only
		STATUS					 current
		DESCRIPTION			 " -- "
		::=  { sfn2avgripEntry  98 }


	plsfn2Prb96RIPAvg		 OBJECT-TYPE
		SYNTAX					 Integer32( -2147483648 .. 2147483647 )
		MAX-ACCESS			 read-only
		STATUS					 current
		DESCRIPTION			 " -- "
		::=  { sfn2avgripEntry  99 }


	plsfn2Prb97RIPAvg		 OBJECT-TYPE
		SYNTAX					 Integer32( -2147483648 .. 2147483647 )
		MAX-ACCESS			 read-only
		STATUS					 current
		DESCRIPTION			 " -- "
		::=  { sfn2avgripEntry  100 }


	plsfn2Prb98RIPAvg		 OBJECT-TYPE
		SYNTAX					 Integer32( -2147483648 .. 2147483647 )
		MAX-ACCESS			 read-only
		STATUS					 current
		DESCRIPTION			 " -- "
		::=  { sfn2avgripEntry  101 }


	plsfn2Prb99RIPAvg		 OBJECT-TYPE
		SYNTAX					 Integer32( -2147483648 .. 2147483647 )
		MAX-ACCESS			 read-only
		STATUS					 current
		DESCRIPTION			 " -- "
		::=  { sfn2avgripEntry  102 }


	sfn4avgripTable		 OBJECT-TYPE
		SYNTAX					 SEQUENCE  OF	 Sfn4avgripEntry
		MAX-ACCESS			 not-accessible
		STATUS					 current
		DESCRIPTION			 " -- "
		::=  { plrelatedOriginCounter  7 }


	sfn4avgripEntry		 OBJECT-TYPE
		SYNTAX					 Sfn4avgripEntry
		MAX-ACCESS			 not-accessible
		STATUS					 current
		DESCRIPTION			 " -- "
		INDEX						{ sfn4avgripLcId }
		::=  { sfn4avgripTable  1 }


	Sfn4avgripEntry		 ::=  SEQUENCE {
		sfn4avgripLcId					Integer32,
		sfn4avgripRowStatus					RowStatus,
		plsfn4Prb00RIPAvg					Integer32,
		plsfn4Prb01RIPAvg					Integer32,
		plsfn4Prb02RIPAvg					Integer32,
		plsfn4Prb03RIPAvg					Integer32,
		plsfn4Prb04RIPAvg					Integer32,
		plsfn4Prb05RIPAvg					Integer32,
		plsfn4Prb06RIPAvg					Integer32,
		plsfn4Prb07RIPAvg					Integer32,
		plsfn4Prb08RIPAvg					Integer32,
		plsfn4Prb09RIPAvg					Integer32,
		plsfn4Prb10RIPAvg					Integer32,
		plsfn4Prb11RIPAvg					Integer32,
		plsfn4Prb12RIPAvg					Integer32,
		plsfn4Prb13RIPAvg					Integer32,
		plsfn4Prb14RIPAvg					Integer32,
		plsfn4Prb15RIPAvg					Integer32,
		plsfn4Prb16RIPAvg					Integer32,
		plsfn4Prb17RIPAvg					Integer32,
		plsfn4Prb18RIPAvg					Integer32,
		plsfn4Prb19RIPAvg					Integer32,
		plsfn4Prb20RIPAvg					Integer32,
		plsfn4Prb21RIPAvg					Integer32,
		plsfn4Prb22RIPAvg					Integer32,
		plsfn4Prb23RIPAvg					Integer32,
		plsfn4Prb24RIPAvg					Integer32,
		plsfn4Prb25RIPAvg					Integer32,
		plsfn4Prb26RIPAvg					Integer32,
		plsfn4Prb27RIPAvg					Integer32,
		plsfn4Prb28RIPAvg					Integer32,
		plsfn4Prb29RIPAvg					Integer32,
		plsfn4Prb30RIPAvg					Integer32,
		plsfn4Prb31RIPAvg					Integer32,
		plsfn4Prb32RIPAvg					Integer32,
		plsfn4Prb33RIPAvg					Integer32,
		plsfn4Prb34RIPAvg					Integer32,
		plsfn4Prb35RIPAvg					Integer32,
		plsfn4Prb36RIPAvg					Integer32,
		plsfn4Prb37RIPAvg					Integer32,
		plsfn4Prb38RIPAvg					Integer32,
		plsfn4Prb39RIPAvg					Integer32,
		plsfn4Prb40RIPAvg					Integer32,
		plsfn4Prb41RIPAvg					Integer32,
		plsfn4Prb42RIPAvg					Integer32,
		plsfn4Prb43RIPAvg					Integer32,
		plsfn4Prb44RIPAvg					Integer32,
		plsfn4Prb45RIPAvg					Integer32,
		plsfn4Prb46RIPAvg					Integer32,
		plsfn4Prb47RIPAvg					Integer32,
		plsfn4Prb48RIPAvg					Integer32,
		plsfn4Prb49RIPAvg					Integer32,
		plsfn4Prb50RIPAvg					Integer32,
		plsfn4Prb51RIPAvg					Integer32,
		plsfn4Prb52RIPAvg					Integer32,
		plsfn4Prb53RIPAvg					Integer32,
		plsfn4Prb54RIPAvg					Integer32,
		plsfn4Prb55RIPAvg					Integer32,
		plsfn4Prb56RIPAvg					Integer32,
		plsfn4Prb57RIPAvg					Integer32,
		plsfn4Prb58RIPAvg					Integer32,
		plsfn4Prb59RIPAvg					Integer32,
		plsfn4Prb60RIPAvg					Integer32,
		plsfn4Prb61RIPAvg					Integer32,
		plsfn4Prb62RIPAvg					Integer32,
		plsfn4Prb63RIPAvg					Integer32,
		plsfn4Prb64RIPAvg					Integer32,
		plsfn4Prb65RIPAvg					Integer32,
		plsfn4Prb66RIPAvg					Integer32,
		plsfn4Prb67RIPAvg					Integer32,
		plsfn4Prb68RIPAvg					Integer32,
		plsfn4Prb69RIPAvg					Integer32,
		plsfn4Prb70RIPAvg					Integer32,
		plsfn4Prb71RIPAvg					Integer32,
		plsfn4Prb72RIPAvg					Integer32,
		plsfn4Prb73RIPAvg					Integer32,
		plsfn4Prb74RIPAvg					Integer32,
		plsfn4Prb75RIPAvg					Integer32,
		plsfn4Prb76RIPAvg					Integer32,
		plsfn4Prb77RIPAvg					Integer32,
		plsfn4Prb78RIPAvg					Integer32,
		plsfn4Prb79RIPAvg					Integer32,
		plsfn4Prb80RIPAvg					Integer32,
		plsfn4Prb81RIPAvg					Integer32,
		plsfn4Prb82RIPAvg					Integer32,
		plsfn4Prb83RIPAvg					Integer32,
		plsfn4Prb84RIPAvg					Integer32,
		plsfn4Prb85RIPAvg					Integer32,
		plsfn4Prb86RIPAvg					Integer32,
		plsfn4Prb87RIPAvg					Integer32,
		plsfn4Prb88RIPAvg					Integer32,
		plsfn4Prb89RIPAvg					Integer32,
		plsfn4Prb90RIPAvg					Integer32,
		plsfn4Prb91RIPAvg					Integer32,
		plsfn4Prb92RIPAvg					Integer32,
		plsfn4Prb93RIPAvg					Integer32,
		plsfn4Prb94RIPAvg					Integer32,
		plsfn4Prb95RIPAvg					Integer32,
		plsfn4Prb96RIPAvg					Integer32,
		plsfn4Prb97RIPAvg					Integer32,
		plsfn4Prb98RIPAvg					Integer32,
		plsfn4Prb99RIPAvg					Integer32
		}


	sfn4avgripLcId		 OBJECT-TYPE
		SYNTAX					 Integer32( 0 .. 23 )
		MAX-ACCESS			 not-accessible
		STATUS					 current
		DESCRIPTION			 " -- "
		::=  { sfn4avgripEntry  1 }


	sfn4avgripRowStatus		 OBJECT-TYPE
		SYNTAX					 RowStatus
		MAX-ACCESS			 read-only
		STATUS					 current
		DESCRIPTION			 " -- "
		::=  { sfn4avgripEntry  2 }


	plsfn4Prb00RIPAvg		 OBJECT-TYPE
		SYNTAX					 Integer32( -2147483648 .. 2147483647 )
		MAX-ACCESS			 read-only
		STATUS					 current
		DESCRIPTION			 " -- "
		::=  { sfn4avgripEntry  3 }


	plsfn4Prb01RIPAvg		 OBJECT-TYPE
		SYNTAX					 Integer32( -2147483648 .. 2147483647 )
		MAX-ACCESS			 read-only
		STATUS					 current
		DESCRIPTION			 " -- "
		::=  { sfn4avgripEntry  4 }


	plsfn4Prb02RIPAvg		 OBJECT-TYPE
		SYNTAX					 Integer32( -2147483648 .. 2147483647 )
		MAX-ACCESS			 read-only
		STATUS					 current
		DESCRIPTION			 " -- "
		::=  { sfn4avgripEntry  5 }


	plsfn4Prb03RIPAvg		 OBJECT-TYPE
		SYNTAX					 Integer32( -2147483648 .. 2147483647 )
		MAX-ACCESS			 read-only
		STATUS					 current
		DESCRIPTION			 " -- "
		::=  { sfn4avgripEntry  6 }


	plsfn4Prb04RIPAvg		 OBJECT-TYPE
		SYNTAX					 Integer32( -2147483648 .. 2147483647 )
		MAX-ACCESS			 read-only
		STATUS					 current
		DESCRIPTION			 " -- "
		::=  { sfn4avgripEntry  7 }


	plsfn4Prb05RIPAvg		 OBJECT-TYPE
		SYNTAX					 Integer32( -2147483648 .. 2147483647 )
		MAX-ACCESS			 read-only
		STATUS					 current
		DESCRIPTION			 " -- "
		::=  { sfn4avgripEntry  8 }


	plsfn4Prb06RIPAvg		 OBJECT-TYPE
		SYNTAX					 Integer32( -2147483648 .. 2147483647 )
		MAX-ACCESS			 read-only
		STATUS					 current
		DESCRIPTION			 " -- "
		::=  { sfn4avgripEntry  9 }


	plsfn4Prb07RIPAvg		 OBJECT-TYPE
		SYNTAX					 Integer32( -2147483648 .. 2147483647 )
		MAX-ACCESS			 read-only
		STATUS					 current
		DESCRIPTION			 " -- "
		::=  { sfn4avgripEntry  10 }


	plsfn4Prb08RIPAvg		 OBJECT-TYPE
		SYNTAX					 Integer32( -2147483648 .. 2147483647 )
		MAX-ACCESS			 read-only
		STATUS					 current
		DESCRIPTION			 " -- "
		::=  { sfn4avgripEntry  11 }


	plsfn4Prb09RIPAvg		 OBJECT-TYPE
		SYNTAX					 Integer32( -2147483648 .. 2147483647 )
		MAX-ACCESS			 read-only
		STATUS					 current
		DESCRIPTION			 " -- "
		::=  { sfn4avgripEntry  12 }


	plsfn4Prb10RIPAvg		 OBJECT-TYPE
		SYNTAX					 Integer32( -2147483648 .. 2147483647 )
		MAX-ACCESS			 read-only
		STATUS					 current
		DESCRIPTION			 " -- "
		::=  { sfn4avgripEntry  13 }


	plsfn4Prb11RIPAvg		 OBJECT-TYPE
		SYNTAX					 Integer32( -2147483648 .. 2147483647 )
		MAX-ACCESS			 read-only
		STATUS					 current
		DESCRIPTION			 " -- "
		::=  { sfn4avgripEntry  14 }


	plsfn4Prb12RIPAvg		 OBJECT-TYPE
		SYNTAX					 Integer32( -2147483648 .. 2147483647 )
		MAX-ACCESS			 read-only
		STATUS					 current
		DESCRIPTION			 " -- "
		::=  { sfn4avgripEntry  15 }


	plsfn4Prb13RIPAvg		 OBJECT-TYPE
		SYNTAX					 Integer32( -2147483648 .. 2147483647 )
		MAX-ACCESS			 read-only
		STATUS					 current
		DESCRIPTION			 " -- "
		::=  { sfn4avgripEntry  16 }


	plsfn4Prb14RIPAvg		 OBJECT-TYPE
		SYNTAX					 Integer32( -2147483648 .. 2147483647 )
		MAX-ACCESS			 read-only
		STATUS					 current
		DESCRIPTION			 " -- "
		::=  { sfn4avgripEntry  17 }


	plsfn4Prb15RIPAvg		 OBJECT-TYPE
		SYNTAX					 Integer32( -2147483648 .. 2147483647 )
		MAX-ACCESS			 read-only
		STATUS					 current
		DESCRIPTION			 " -- "
		::=  { sfn4avgripEntry  18 }


	plsfn4Prb16RIPAvg		 OBJECT-TYPE
		SYNTAX					 Integer32( -2147483648 .. 2147483647 )
		MAX-ACCESS			 read-only
		STATUS					 current
		DESCRIPTION			 " -- "
		::=  { sfn4avgripEntry  19 }


	plsfn4Prb17RIPAvg		 OBJECT-TYPE
		SYNTAX					 Integer32( -2147483648 .. 2147483647 )
		MAX-ACCESS			 read-only
		STATUS					 current
		DESCRIPTION			 " -- "
		::=  { sfn4avgripEntry  20 }


	plsfn4Prb18RIPAvg		 OBJECT-TYPE
		SYNTAX					 Integer32( -2147483648 .. 2147483647 )
		MAX-ACCESS			 read-only
		STATUS					 current
		DESCRIPTION			 " -- "
		::=  { sfn4avgripEntry  21 }


	plsfn4Prb19RIPAvg		 OBJECT-TYPE
		SYNTAX					 Integer32( -2147483648 .. 2147483647 )
		MAX-ACCESS			 read-only
		STATUS					 current
		DESCRIPTION			 " -- "
		::=  { sfn4avgripEntry  22 }


	plsfn4Prb20RIPAvg		 OBJECT-TYPE
		SYNTAX					 Integer32( -2147483648 .. 2147483647 )
		MAX-ACCESS			 read-only
		STATUS					 current
		DESCRIPTION			 " -- "
		::=  { sfn4avgripEntry  23 }


	plsfn4Prb21RIPAvg		 OBJECT-TYPE
		SYNTAX					 Integer32( -2147483648 .. 2147483647 )
		MAX-ACCESS			 read-only
		STATUS					 current
		DESCRIPTION			 " -- "
		::=  { sfn4avgripEntry  24 }


	plsfn4Prb22RIPAvg		 OBJECT-TYPE
		SYNTAX					 Integer32( -2147483648 .. 2147483647 )
		MAX-ACCESS			 read-only
		STATUS					 current
		DESCRIPTION			 " -- "
		::=  { sfn4avgripEntry  25 }


	plsfn4Prb23RIPAvg		 OBJECT-TYPE
		SYNTAX					 Integer32( -2147483648 .. 2147483647 )
		MAX-ACCESS			 read-only
		STATUS					 current
		DESCRIPTION			 " -- "
		::=  { sfn4avgripEntry  26 }


	plsfn4Prb24RIPAvg		 OBJECT-TYPE
		SYNTAX					 Integer32( -2147483648 .. 2147483647 )
		MAX-ACCESS			 read-only
		STATUS					 current
		DESCRIPTION			 " -- "
		::=  { sfn4avgripEntry  27 }


	plsfn4Prb25RIPAvg		 OBJECT-TYPE
		SYNTAX					 Integer32( -2147483648 .. 2147483647 )
		MAX-ACCESS			 read-only
		STATUS					 current
		DESCRIPTION			 " -- "
		::=  { sfn4avgripEntry  28 }


	plsfn4Prb26RIPAvg		 OBJECT-TYPE
		SYNTAX					 Integer32( -2147483648 .. 2147483647 )
		MAX-ACCESS			 read-only
		STATUS					 current
		DESCRIPTION			 " -- "
		::=  { sfn4avgripEntry  29 }


	plsfn4Prb27RIPAvg		 OBJECT-TYPE
		SYNTAX					 Integer32( -2147483648 .. 2147483647 )
		MAX-ACCESS			 read-only
		STATUS					 current
		DESCRIPTION			 " -- "
		::=  { sfn4avgripEntry  30 }


	plsfn4Prb28RIPAvg		 OBJECT-TYPE
		SYNTAX					 Integer32( -2147483648 .. 2147483647 )
		MAX-ACCESS			 read-only
		STATUS					 current
		DESCRIPTION			 " -- "
		::=  { sfn4avgripEntry  31 }


	plsfn4Prb29RIPAvg		 OBJECT-TYPE
		SYNTAX					 Integer32( -2147483648 .. 2147483647 )
		MAX-ACCESS			 read-only
		STATUS					 current
		DESCRIPTION			 " -- "
		::=  { sfn4avgripEntry  32 }


	plsfn4Prb30RIPAvg		 OBJECT-TYPE
		SYNTAX					 Integer32( -2147483648 .. 2147483647 )
		MAX-ACCESS			 read-only
		STATUS					 current
		DESCRIPTION			 " -- "
		::=  { sfn4avgripEntry  33 }


	plsfn4Prb31RIPAvg		 OBJECT-TYPE
		SYNTAX					 Integer32( -2147483648 .. 2147483647 )
		MAX-ACCESS			 read-only
		STATUS					 current
		DESCRIPTION			 " -- "
		::=  { sfn4avgripEntry  34 }


	plsfn4Prb32RIPAvg		 OBJECT-TYPE
		SYNTAX					 Integer32( -2147483648 .. 2147483647 )
		MAX-ACCESS			 read-only
		STATUS					 current
		DESCRIPTION			 " -- "
		::=  { sfn4avgripEntry  35 }


	plsfn4Prb33RIPAvg		 OBJECT-TYPE
		SYNTAX					 Integer32( -2147483648 .. 2147483647 )
		MAX-ACCESS			 read-only
		STATUS					 current
		DESCRIPTION			 " -- "
		::=  { sfn4avgripEntry  36 }


	plsfn4Prb34RIPAvg		 OBJECT-TYPE
		SYNTAX					 Integer32( -2147483648 .. 2147483647 )
		MAX-ACCESS			 read-only
		STATUS					 current
		DESCRIPTION			 " -- "
		::=  { sfn4avgripEntry  37 }


	plsfn4Prb35RIPAvg		 OBJECT-TYPE
		SYNTAX					 Integer32( -2147483648 .. 2147483647 )
		MAX-ACCESS			 read-only
		STATUS					 current
		DESCRIPTION			 " -- "
		::=  { sfn4avgripEntry  38 }


	plsfn4Prb36RIPAvg		 OBJECT-TYPE
		SYNTAX					 Integer32( -2147483648 .. 2147483647 )
		MAX-ACCESS			 read-only
		STATUS					 current
		DESCRIPTION			 " -- "
		::=  { sfn4avgripEntry  39 }


	plsfn4Prb37RIPAvg		 OBJECT-TYPE
		SYNTAX					 Integer32( -2147483648 .. 2147483647 )
		MAX-ACCESS			 read-only
		STATUS					 current
		DESCRIPTION			 " -- "
		::=  { sfn4avgripEntry  40 }


	plsfn4Prb38RIPAvg		 OBJECT-TYPE
		SYNTAX					 Integer32( -2147483648 .. 2147483647 )
		MAX-ACCESS			 read-only
		STATUS					 current
		DESCRIPTION			 " -- "
		::=  { sfn4avgripEntry  41 }


	plsfn4Prb39RIPAvg		 OBJECT-TYPE
		SYNTAX					 Integer32( -2147483648 .. 2147483647 )
		MAX-ACCESS			 read-only
		STATUS					 current
		DESCRIPTION			 " -- "
		::=  { sfn4avgripEntry  42 }


	plsfn4Prb40RIPAvg		 OBJECT-TYPE
		SYNTAX					 Integer32( -2147483648 .. 2147483647 )
		MAX-ACCESS			 read-only
		STATUS					 current
		DESCRIPTION			 " -- "
		::=  { sfn4avgripEntry  43 }


	plsfn4Prb41RIPAvg		 OBJECT-TYPE
		SYNTAX					 Integer32( -2147483648 .. 2147483647 )
		MAX-ACCESS			 read-only
		STATUS					 current
		DESCRIPTION			 " -- "
		::=  { sfn4avgripEntry  44 }


	plsfn4Prb42RIPAvg		 OBJECT-TYPE
		SYNTAX					 Integer32( -2147483648 .. 2147483647 )
		MAX-ACCESS			 read-only
		STATUS					 current
		DESCRIPTION			 " -- "
		::=  { sfn4avgripEntry  45 }


	plsfn4Prb43RIPAvg		 OBJECT-TYPE
		SYNTAX					 Integer32( -2147483648 .. 2147483647 )
		MAX-ACCESS			 read-only
		STATUS					 current
		DESCRIPTION			 " -- "
		::=  { sfn4avgripEntry  46 }


	plsfn4Prb44RIPAvg		 OBJECT-TYPE
		SYNTAX					 Integer32( -2147483648 .. 2147483647 )
		MAX-ACCESS			 read-only
		STATUS					 current
		DESCRIPTION			 " -- "
		::=  { sfn4avgripEntry  47 }


	plsfn4Prb45RIPAvg		 OBJECT-TYPE
		SYNTAX					 Integer32( -2147483648 .. 2147483647 )
		MAX-ACCESS			 read-only
		STATUS					 current
		DESCRIPTION			 " -- "
		::=  { sfn4avgripEntry  48 }


	plsfn4Prb46RIPAvg		 OBJECT-TYPE
		SYNTAX					 Integer32( -2147483648 .. 2147483647 )
		MAX-ACCESS			 read-only
		STATUS					 current
		DESCRIPTION			 " -- "
		::=  { sfn4avgripEntry  49 }


	plsfn4Prb47RIPAvg		 OBJECT-TYPE
		SYNTAX					 Integer32( -2147483648 .. 2147483647 )
		MAX-ACCESS			 read-only
		STATUS					 current
		DESCRIPTION			 " -- "
		::=  { sfn4avgripEntry  50 }


	plsfn4Prb48RIPAvg		 OBJECT-TYPE
		SYNTAX					 Integer32( -2147483648 .. 2147483647 )
		MAX-ACCESS			 read-only
		STATUS					 current
		DESCRIPTION			 " -- "
		::=  { sfn4avgripEntry  51 }


	plsfn4Prb49RIPAvg		 OBJECT-TYPE
		SYNTAX					 Integer32( -2147483648 .. 2147483647 )
		MAX-ACCESS			 read-only
		STATUS					 current
		DESCRIPTION			 " -- "
		::=  { sfn4avgripEntry  52 }


	plsfn4Prb50RIPAvg		 OBJECT-TYPE
		SYNTAX					 Integer32( -2147483648 .. 2147483647 )
		MAX-ACCESS			 read-only
		STATUS					 current
		DESCRIPTION			 " -- "
		::=  { sfn4avgripEntry  53 }


	plsfn4Prb51RIPAvg		 OBJECT-TYPE
		SYNTAX					 Integer32( -2147483648 .. 2147483647 )
		MAX-ACCESS			 read-only
		STATUS					 current
		DESCRIPTION			 " -- "
		::=  { sfn4avgripEntry  54 }


	plsfn4Prb52RIPAvg		 OBJECT-TYPE
		SYNTAX					 Integer32( -2147483648 .. 2147483647 )
		MAX-ACCESS			 read-only
		STATUS					 current
		DESCRIPTION			 " -- "
		::=  { sfn4avgripEntry  55 }


	plsfn4Prb53RIPAvg		 OBJECT-TYPE
		SYNTAX					 Integer32( -2147483648 .. 2147483647 )
		MAX-ACCESS			 read-only
		STATUS					 current
		DESCRIPTION			 " -- "
		::=  { sfn4avgripEntry  56 }


	plsfn4Prb54RIPAvg		 OBJECT-TYPE
		SYNTAX					 Integer32( -2147483648 .. 2147483647 )
		MAX-ACCESS			 read-only
		STATUS					 current
		DESCRIPTION			 " -- "
		::=  { sfn4avgripEntry  57 }


	plsfn4Prb55RIPAvg		 OBJECT-TYPE
		SYNTAX					 Integer32( -2147483648 .. 2147483647 )
		MAX-ACCESS			 read-only
		STATUS					 current
		DESCRIPTION			 " -- "
		::=  { sfn4avgripEntry  58 }


	plsfn4Prb56RIPAvg		 OBJECT-TYPE
		SYNTAX					 Integer32( -2147483648 .. 2147483647 )
		MAX-ACCESS			 read-only
		STATUS					 current
		DESCRIPTION			 " -- "
		::=  { sfn4avgripEntry  59 }


	plsfn4Prb57RIPAvg		 OBJECT-TYPE
		SYNTAX					 Integer32( -2147483648 .. 2147483647 )
		MAX-ACCESS			 read-only
		STATUS					 current
		DESCRIPTION			 " -- "
		::=  { sfn4avgripEntry  60 }


	plsfn4Prb58RIPAvg		 OBJECT-TYPE
		SYNTAX					 Integer32( -2147483648 .. 2147483647 )
		MAX-ACCESS			 read-only
		STATUS					 current
		DESCRIPTION			 " -- "
		::=  { sfn4avgripEntry  61 }


	plsfn4Prb59RIPAvg		 OBJECT-TYPE
		SYNTAX					 Integer32( -2147483648 .. 2147483647 )
		MAX-ACCESS			 read-only
		STATUS					 current
		DESCRIPTION			 " -- "
		::=  { sfn4avgripEntry  62 }


	plsfn4Prb60RIPAvg		 OBJECT-TYPE
		SYNTAX					 Integer32( -2147483648 .. 2147483647 )
		MAX-ACCESS			 read-only
		STATUS					 current
		DESCRIPTION			 " -- "
		::=  { sfn4avgripEntry  63 }


	plsfn4Prb61RIPAvg		 OBJECT-TYPE
		SYNTAX					 Integer32( -2147483648 .. 2147483647 )
		MAX-ACCESS			 read-only
		STATUS					 current
		DESCRIPTION			 " -- "
		::=  { sfn4avgripEntry  64 }


	plsfn4Prb62RIPAvg		 OBJECT-TYPE
		SYNTAX					 Integer32( -2147483648 .. 2147483647 )
		MAX-ACCESS			 read-only
		STATUS					 current
		DESCRIPTION			 " -- "
		::=  { sfn4avgripEntry  65 }


	plsfn4Prb63RIPAvg		 OBJECT-TYPE
		SYNTAX					 Integer32( -2147483648 .. 2147483647 )
		MAX-ACCESS			 read-only
		STATUS					 current
		DESCRIPTION			 " -- "
		::=  { sfn4avgripEntry  66 }


	plsfn4Prb64RIPAvg		 OBJECT-TYPE
		SYNTAX					 Integer32( -2147483648 .. 2147483647 )
		MAX-ACCESS			 read-only
		STATUS					 current
		DESCRIPTION			 " -- "
		::=  { sfn4avgripEntry  67 }


	plsfn4Prb65RIPAvg		 OBJECT-TYPE
		SYNTAX					 Integer32( -2147483648 .. 2147483647 )
		MAX-ACCESS			 read-only
		STATUS					 current
		DESCRIPTION			 " -- "
		::=  { sfn4avgripEntry  68 }


	plsfn4Prb66RIPAvg		 OBJECT-TYPE
		SYNTAX					 Integer32( -2147483648 .. 2147483647 )
		MAX-ACCESS			 read-only
		STATUS					 current
		DESCRIPTION			 " -- "
		::=  { sfn4avgripEntry  69 }


	plsfn4Prb67RIPAvg		 OBJECT-TYPE
		SYNTAX					 Integer32( -2147483648 .. 2147483647 )
		MAX-ACCESS			 read-only
		STATUS					 current
		DESCRIPTION			 " -- "
		::=  { sfn4avgripEntry  70 }


	plsfn4Prb68RIPAvg		 OBJECT-TYPE
		SYNTAX					 Integer32( -2147483648 .. 2147483647 )
		MAX-ACCESS			 read-only
		STATUS					 current
		DESCRIPTION			 " -- "
		::=  { sfn4avgripEntry  71 }


	plsfn4Prb69RIPAvg		 OBJECT-TYPE
		SYNTAX					 Integer32( -2147483648 .. 2147483647 )
		MAX-ACCESS			 read-only
		STATUS					 current
		DESCRIPTION			 " -- "
		::=  { sfn4avgripEntry  72 }


	plsfn4Prb70RIPAvg		 OBJECT-TYPE
		SYNTAX					 Integer32( -2147483648 .. 2147483647 )
		MAX-ACCESS			 read-only
		STATUS					 current
		DESCRIPTION			 " -- "
		::=  { sfn4avgripEntry  73 }


	plsfn4Prb71RIPAvg		 OBJECT-TYPE
		SYNTAX					 Integer32( -2147483648 .. 2147483647 )
		MAX-ACCESS			 read-only
		STATUS					 current
		DESCRIPTION			 " -- "
		::=  { sfn4avgripEntry  74 }


	plsfn4Prb72RIPAvg		 OBJECT-TYPE
		SYNTAX					 Integer32( -2147483648 .. 2147483647 )
		MAX-ACCESS			 read-only
		STATUS					 current
		DESCRIPTION			 " -- "
		::=  { sfn4avgripEntry  75 }


	plsfn4Prb73RIPAvg		 OBJECT-TYPE
		SYNTAX					 Integer32( -2147483648 .. 2147483647 )
		MAX-ACCESS			 read-only
		STATUS					 current
		DESCRIPTION			 " -- "
		::=  { sfn4avgripEntry  76 }


	plsfn4Prb74RIPAvg		 OBJECT-TYPE
		SYNTAX					 Integer32( -2147483648 .. 2147483647 )
		MAX-ACCESS			 read-only
		STATUS					 current
		DESCRIPTION			 " -- "
		::=  { sfn4avgripEntry  77 }


	plsfn4Prb75RIPAvg		 OBJECT-TYPE
		SYNTAX					 Integer32( -2147483648 .. 2147483647 )
		MAX-ACCESS			 read-only
		STATUS					 current
		DESCRIPTION			 " -- "
		::=  { sfn4avgripEntry  78 }


	plsfn4Prb76RIPAvg		 OBJECT-TYPE
		SYNTAX					 Integer32( -2147483648 .. 2147483647 )
		MAX-ACCESS			 read-only
		STATUS					 current
		DESCRIPTION			 " -- "
		::=  { sfn4avgripEntry  79 }


	plsfn4Prb77RIPAvg		 OBJECT-TYPE
		SYNTAX					 Integer32( -2147483648 .. 2147483647 )
		MAX-ACCESS			 read-only
		STATUS					 current
		DESCRIPTION			 " -- "
		::=  { sfn4avgripEntry  80 }


	plsfn4Prb78RIPAvg		 OBJECT-TYPE
		SYNTAX					 Integer32( -2147483648 .. 2147483647 )
		MAX-ACCESS			 read-only
		STATUS					 current
		DESCRIPTION			 " -- "
		::=  { sfn4avgripEntry  81 }


	plsfn4Prb79RIPAvg		 OBJECT-TYPE
		SYNTAX					 Integer32( -2147483648 .. 2147483647 )
		MAX-ACCESS			 read-only
		STATUS					 current
		DESCRIPTION			 " -- "
		::=  { sfn4avgripEntry  82 }


	plsfn4Prb80RIPAvg		 OBJECT-TYPE
		SYNTAX					 Integer32( -2147483648 .. 2147483647 )
		MAX-ACCESS			 read-only
		STATUS					 current
		DESCRIPTION			 " -- "
		::=  { sfn4avgripEntry  83 }


	plsfn4Prb81RIPAvg		 OBJECT-TYPE
		SYNTAX					 Integer32( -2147483648 .. 2147483647 )
		MAX-ACCESS			 read-only
		STATUS					 current
		DESCRIPTION			 " -- "
		::=  { sfn4avgripEntry  84 }


	plsfn4Prb82RIPAvg		 OBJECT-TYPE
		SYNTAX					 Integer32( -2147483648 .. 2147483647 )
		MAX-ACCESS			 read-only
		STATUS					 current
		DESCRIPTION			 " -- "
		::=  { sfn4avgripEntry  85 }


	plsfn4Prb83RIPAvg		 OBJECT-TYPE
		SYNTAX					 Integer32( -2147483648 .. 2147483647 )
		MAX-ACCESS			 read-only
		STATUS					 current
		DESCRIPTION			 " -- "
		::=  { sfn4avgripEntry  86 }


	plsfn4Prb84RIPAvg		 OBJECT-TYPE
		SYNTAX					 Integer32( -2147483648 .. 2147483647 )
		MAX-ACCESS			 read-only
		STATUS					 current
		DESCRIPTION			 " -- "
		::=  { sfn4avgripEntry  87 }


	plsfn4Prb85RIPAvg		 OBJECT-TYPE
		SYNTAX					 Integer32( -2147483648 .. 2147483647 )
		MAX-ACCESS			 read-only
		STATUS					 current
		DESCRIPTION			 " -- "
		::=  { sfn4avgripEntry  88 }


	plsfn4Prb86RIPAvg		 OBJECT-TYPE
		SYNTAX					 Integer32( -2147483648 .. 2147483647 )
		MAX-ACCESS			 read-only
		STATUS					 current
		DESCRIPTION			 " -- "
		::=  { sfn4avgripEntry  89 }


	plsfn4Prb87RIPAvg		 OBJECT-TYPE
		SYNTAX					 Integer32( -2147483648 .. 2147483647 )
		MAX-ACCESS			 read-only
		STATUS					 current
		DESCRIPTION			 " -- "
		::=  { sfn4avgripEntry  90 }


	plsfn4Prb88RIPAvg		 OBJECT-TYPE
		SYNTAX					 Integer32( -2147483648 .. 2147483647 )
		MAX-ACCESS			 read-only
		STATUS					 current
		DESCRIPTION			 " -- "
		::=  { sfn4avgripEntry  91 }


	plsfn4Prb89RIPAvg		 OBJECT-TYPE
		SYNTAX					 Integer32( -2147483648 .. 2147483647 )
		MAX-ACCESS			 read-only
		STATUS					 current
		DESCRIPTION			 " -- "
		::=  { sfn4avgripEntry  92 }


	plsfn4Prb90RIPAvg		 OBJECT-TYPE
		SYNTAX					 Integer32( -2147483648 .. 2147483647 )
		MAX-ACCESS			 read-only
		STATUS					 current
		DESCRIPTION			 " -- "
		::=  { sfn4avgripEntry  93 }


	plsfn4Prb91RIPAvg		 OBJECT-TYPE
		SYNTAX					 Integer32( -2147483648 .. 2147483647 )
		MAX-ACCESS			 read-only
		STATUS					 current
		DESCRIPTION			 " -- "
		::=  { sfn4avgripEntry  94 }


	plsfn4Prb92RIPAvg		 OBJECT-TYPE
		SYNTAX					 Integer32( -2147483648 .. 2147483647 )
		MAX-ACCESS			 read-only
		STATUS					 current
		DESCRIPTION			 " -- "
		::=  { sfn4avgripEntry  95 }


	plsfn4Prb93RIPAvg		 OBJECT-TYPE
		SYNTAX					 Integer32( -2147483648 .. 2147483647 )
		MAX-ACCESS			 read-only
		STATUS					 current
		DESCRIPTION			 " -- "
		::=  { sfn4avgripEntry  96 }


	plsfn4Prb94RIPAvg		 OBJECT-TYPE
		SYNTAX					 Integer32( -2147483648 .. 2147483647 )
		MAX-ACCESS			 read-only
		STATUS					 current
		DESCRIPTION			 " -- "
		::=  { sfn4avgripEntry  97 }


	plsfn4Prb95RIPAvg		 OBJECT-TYPE
		SYNTAX					 Integer32( -2147483648 .. 2147483647 )
		MAX-ACCESS			 read-only
		STATUS					 current
		DESCRIPTION			 " -- "
		::=  { sfn4avgripEntry  98 }


	plsfn4Prb96RIPAvg		 OBJECT-TYPE
		SYNTAX					 Integer32( -2147483648 .. 2147483647 )
		MAX-ACCESS			 read-only
		STATUS					 current
		DESCRIPTION			 " -- "
		::=  { sfn4avgripEntry  99 }


	plsfn4Prb97RIPAvg		 OBJECT-TYPE
		SYNTAX					 Integer32( -2147483648 .. 2147483647 )
		MAX-ACCESS			 read-only
		STATUS					 current
		DESCRIPTION			 " -- "
		::=  { sfn4avgripEntry  100 }


	plsfn4Prb98RIPAvg		 OBJECT-TYPE
		SYNTAX					 Integer32( -2147483648 .. 2147483647 )
		MAX-ACCESS			 read-only
		STATUS					 current
		DESCRIPTION			 " -- "
		::=  { sfn4avgripEntry  101 }


	plsfn4Prb99RIPAvg		 OBJECT-TYPE
		SYNTAX					 Integer32( -2147483648 .. 2147483647 )
		MAX-ACCESS			 read-only
		STATUS					 current
		DESCRIPTION			 " -- "
		::=  { sfn4avgripEntry  102 }


	sfn3avgripTable		 OBJECT-TYPE
		SYNTAX					 SEQUENCE  OF	 Sfn3avgripEntry
		MAX-ACCESS			 not-accessible
		STATUS					 current
		DESCRIPTION			 " -- "
		::=  { plrelatedOriginCounter  8 }


	sfn3avgripEntry		 OBJECT-TYPE
		SYNTAX					 Sfn3avgripEntry
		MAX-ACCESS			 not-accessible
		STATUS					 current
		DESCRIPTION			 " -- "
		INDEX						{ sfn3avgripLcId }
		::=  { sfn3avgripTable  1 }


	Sfn3avgripEntry		 ::=  SEQUENCE {
		sfn3avgripLcId					Integer32,
		sfn3avgripRowStatus					RowStatus,
		plsfn3Prb00RIPAvg					Integer32,
		plsfn3Prb01RIPAvg					Integer32,
		plsfn3Prb02RIPAvg					Integer32,
		plsfn3Prb03RIPAvg					Integer32,
		plsfn3Prb04RIPAvg					Integer32,
		plsfn3Prb05RIPAvg					Integer32,
		plsfn3Prb06RIPAvg					Integer32,
		plsfn3Prb07RIPAvg					Integer32,
		plsfn3Prb08RIPAvg					Integer32,
		plsfn3Prb09RIPAvg					Integer32,
		plsfn3Prb10RIPAvg					Integer32,
		plsfn3Prb11RIPAvg					Integer32,
		plsfn3Prb12RIPAvg					Integer32,
		plsfn3Prb13RIPAvg					Integer32,
		plsfn3Prb14RIPAvg					Integer32,
		plsfn3Prb15RIPAvg					Integer32,
		plsfn3Prb16RIPAvg					Integer32,
		plsfn3Prb17RIPAvg					Integer32,
		plsfn3Prb18RIPAvg					Integer32,
		plsfn3Prb19RIPAvg					Integer32,
		plsfn3Prb20RIPAvg					Integer32,
		plsfn3Prb21RIPAvg					Integer32,
		plsfn3Prb22RIPAvg					Integer32,
		plsfn3Prb23RIPAvg					Integer32,
		plsfn3Prb24RIPAvg					Integer32,
		plsfn3Prb25RIPAvg					Integer32,
		plsfn3Prb26RIPAvg					Integer32,
		plsfn3Prb27RIPAvg					Integer32,
		plsfn3Prb28RIPAvg					Integer32,
		plsfn3Prb29RIPAvg					Integer32,
		plsfn3Prb30RIPAvg					Integer32,
		plsfn3Prb31RIPAvg					Integer32,
		plsfn3Prb32RIPAvg					Integer32,
		plsfn3Prb33RIPAvg					Integer32,
		plsfn3Prb34RIPAvg					Integer32,
		plsfn3Prb35RIPAvg					Integer32,
		plsfn3Prb36RIPAvg					Integer32,
		plsfn3Prb37RIPAvg					Integer32,
		plsfn3Prb38RIPAvg					Integer32,
		plsfn3Prb39RIPAvg					Integer32,
		plsfn3Prb40RIPAvg					Integer32,
		plsfn3Prb41RIPAvg					Integer32,
		plsfn3Prb42RIPAvg					Integer32,
		plsfn3Prb43RIPAvg					Integer32,
		plsfn3Prb44RIPAvg					Integer32,
		plsfn3Prb45RIPAvg					Integer32,
		plsfn3Prb46RIPAvg					Integer32,
		plsfn3Prb47RIPAvg					Integer32,
		plsfn3Prb48RIPAvg					Integer32,
		plsfn3Prb49RIPAvg					Integer32,
		plsfn3Prb50RIPAvg					Integer32,
		plsfn3Prb51RIPAvg					Integer32,
		plsfn3Prb52RIPAvg					Integer32,
		plsfn3Prb53RIPAvg					Integer32,
		plsfn3Prb54RIPAvg					Integer32,
		plsfn3Prb55RIPAvg					Integer32,
		plsfn3Prb56RIPAvg					Integer32,
		plsfn3Prb57RIPAvg					Integer32,
		plsfn3Prb58RIPAvg					Integer32,
		plsfn3Prb59RIPAvg					Integer32,
		plsfn3Prb60RIPAvg					Integer32,
		plsfn3Prb61RIPAvg					Integer32,
		plsfn3Prb62RIPAvg					Integer32,
		plsfn3Prb63RIPAvg					Integer32,
		plsfn3Prb64RIPAvg					Integer32,
		plsfn3Prb65RIPAvg					Integer32,
		plsfn3Prb66RIPAvg					Integer32,
		plsfn3Prb67RIPAvg					Integer32,
		plsfn3Prb68RIPAvg					Integer32,
		plsfn3Prb69RIPAvg					Integer32,
		plsfn3Prb70RIPAvg					Integer32,
		plsfn3Prb71RIPAvg					Integer32,
		plsfn3Prb72RIPAvg					Integer32,
		plsfn3Prb73RIPAvg					Integer32,
		plsfn3Prb74RIPAvg					Integer32,
		plsfn3Prb75RIPAvg					Integer32,
		plsfn3Prb76RIPAvg					Integer32,
		plsfn3Prb77RIPAvg					Integer32,
		plsfn3Prb78RIPAvg					Integer32,
		plsfn3Prb79RIPAvg					Integer32,
		plsfn3Prb80RIPAvg					Integer32,
		plsfn3Prb81RIPAvg					Integer32,
		plsfn3Prb82RIPAvg					Integer32,
		plsfn3Prb83RIPAvg					Integer32,
		plsfn3Prb84RIPAvg					Integer32,
		plsfn3Prb85RIPAvg					Integer32,
		plsfn3Prb86RIPAvg					Integer32,
		plsfn3Prb87RIPAvg					Integer32,
		plsfn3Prb88RIPAvg					Integer32,
		plsfn3Prb89RIPAvg					Integer32,
		plsfn3Prb90RIPAvg					Integer32,
		plsfn3Prb91RIPAvg					Integer32,
		plsfn3Prb92RIPAvg					Integer32,
		plsfn3Prb93RIPAvg					Integer32,
		plsfn3Prb94RIPAvg					Integer32,
		plsfn3Prb95RIPAvg					Integer32,
		plsfn3Prb96RIPAvg					Integer32,
		plsfn3Prb97RIPAvg					Integer32,
		plsfn3Prb98RIPAvg					Integer32,
		plsfn3Prb99RIPAvg					Integer32
		}


	sfn3avgripLcId		 OBJECT-TYPE
		SYNTAX					 Integer32( 0 .. 23 )
		MAX-ACCESS			 not-accessible
		STATUS					 current
		DESCRIPTION			 " -- "
		::=  { sfn3avgripEntry  1 }


	sfn3avgripRowStatus		 OBJECT-TYPE
		SYNTAX					 RowStatus
		MAX-ACCESS			 read-only
		STATUS					 current
		DESCRIPTION			 " -- "
		::=  { sfn3avgripEntry  2 }


	plsfn3Prb00RIPAvg		 OBJECT-TYPE
		SYNTAX					 Integer32( -2147483648 .. 2147483647 )
		MAX-ACCESS			 read-only
		STATUS					 current
		DESCRIPTION			 " -- "
		::=  { sfn3avgripEntry  3 }


	plsfn3Prb01RIPAvg		 OBJECT-TYPE
		SYNTAX					 Integer32( -2147483648 .. 2147483647 )
		MAX-ACCESS			 read-only
		STATUS					 current
		DESCRIPTION			 " -- "
		::=  { sfn3avgripEntry  4 }


	plsfn3Prb02RIPAvg		 OBJECT-TYPE
		SYNTAX					 Integer32( -2147483648 .. 2147483647 )
		MAX-ACCESS			 read-only
		STATUS					 current
		DESCRIPTION			 " -- "
		::=  { sfn3avgripEntry  5 }


	plsfn3Prb03RIPAvg		 OBJECT-TYPE
		SYNTAX					 Integer32( -2147483648 .. 2147483647 )
		MAX-ACCESS			 read-only
		STATUS					 current
		DESCRIPTION			 " -- "
		::=  { sfn3avgripEntry  6 }


	plsfn3Prb04RIPAvg		 OBJECT-TYPE
		SYNTAX					 Integer32( -2147483648 .. 2147483647 )
		MAX-ACCESS			 read-only
		STATUS					 current
		DESCRIPTION			 " -- "
		::=  { sfn3avgripEntry  7 }


	plsfn3Prb05RIPAvg		 OBJECT-TYPE
		SYNTAX					 Integer32( -2147483648 .. 2147483647 )
		MAX-ACCESS			 read-only
		STATUS					 current
		DESCRIPTION			 " -- "
		::=  { sfn3avgripEntry  8 }


	plsfn3Prb06RIPAvg		 OBJECT-TYPE
		SYNTAX					 Integer32( -2147483648 .. 2147483647 )
		MAX-ACCESS			 read-only
		STATUS					 current
		DESCRIPTION			 " -- "
		::=  { sfn3avgripEntry  9 }


	plsfn3Prb07RIPAvg		 OBJECT-TYPE
		SYNTAX					 Integer32( -2147483648 .. 2147483647 )
		MAX-ACCESS			 read-only
		STATUS					 current
		DESCRIPTION			 " -- "
		::=  { sfn3avgripEntry  10 }


	plsfn3Prb08RIPAvg		 OBJECT-TYPE
		SYNTAX					 Integer32( -2147483648 .. 2147483647 )
		MAX-ACCESS			 read-only
		STATUS					 current
		DESCRIPTION			 " -- "
		::=  { sfn3avgripEntry  11 }


	plsfn3Prb09RIPAvg		 OBJECT-TYPE
		SYNTAX					 Integer32( -2147483648 .. 2147483647 )
		MAX-ACCESS			 read-only
		STATUS					 current
		DESCRIPTION			 " -- "
		::=  { sfn3avgripEntry  12 }


	plsfn3Prb10RIPAvg		 OBJECT-TYPE
		SYNTAX					 Integer32( -2147483648 .. 2147483647 )
		MAX-ACCESS			 read-only
		STATUS					 current
		DESCRIPTION			 " -- "
		::=  { sfn3avgripEntry  13 }


	plsfn3Prb11RIPAvg		 OBJECT-TYPE
		SYNTAX					 Integer32( -2147483648 .. 2147483647 )
		MAX-ACCESS			 read-only
		STATUS					 current
		DESCRIPTION			 " -- "
		::=  { sfn3avgripEntry  14 }


	plsfn3Prb12RIPAvg		 OBJECT-TYPE
		SYNTAX					 Integer32( -2147483648 .. 2147483647 )
		MAX-ACCESS			 read-only
		STATUS					 current
		DESCRIPTION			 " -- "
		::=  { sfn3avgripEntry  15 }


	plsfn3Prb13RIPAvg		 OBJECT-TYPE
		SYNTAX					 Integer32( -2147483648 .. 2147483647 )
		MAX-ACCESS			 read-only
		STATUS					 current
		DESCRIPTION			 " -- "
		::=  { sfn3avgripEntry  16 }


	plsfn3Prb14RIPAvg		 OBJECT-TYPE
		SYNTAX					 Integer32( -2147483648 .. 2147483647 )
		MAX-ACCESS			 read-only
		STATUS					 current
		DESCRIPTION			 " -- "
		::=  { sfn3avgripEntry  17 }


	plsfn3Prb15RIPAvg		 OBJECT-TYPE
		SYNTAX					 Integer32( -2147483648 .. 2147483647 )
		MAX-ACCESS			 read-only
		STATUS					 current
		DESCRIPTION			 " -- "
		::=  { sfn3avgripEntry  18 }


	plsfn3Prb16RIPAvg		 OBJECT-TYPE
		SYNTAX					 Integer32( -2147483648 .. 2147483647 )
		MAX-ACCESS			 read-only
		STATUS					 current
		DESCRIPTION			 " -- "
		::=  { sfn3avgripEntry  19 }


	plsfn3Prb17RIPAvg		 OBJECT-TYPE
		SYNTAX					 Integer32( -2147483648 .. 2147483647 )
		MAX-ACCESS			 read-only
		STATUS					 current
		DESCRIPTION			 " -- "
		::=  { sfn3avgripEntry  20 }


	plsfn3Prb18RIPAvg		 OBJECT-TYPE
		SYNTAX					 Integer32( -2147483648 .. 2147483647 )
		MAX-ACCESS			 read-only
		STATUS					 current
		DESCRIPTION			 " -- "
		::=  { sfn3avgripEntry  21 }


	plsfn3Prb19RIPAvg		 OBJECT-TYPE
		SYNTAX					 Integer32( -2147483648 .. 2147483647 )
		MAX-ACCESS			 read-only
		STATUS					 current
		DESCRIPTION			 " -- "
		::=  { sfn3avgripEntry  22 }


	plsfn3Prb20RIPAvg		 OBJECT-TYPE
		SYNTAX					 Integer32( -2147483648 .. 2147483647 )
		MAX-ACCESS			 read-only
		STATUS					 current
		DESCRIPTION			 " -- "
		::=  { sfn3avgripEntry  23 }


	plsfn3Prb21RIPAvg		 OBJECT-TYPE
		SYNTAX					 Integer32( -2147483648 .. 2147483647 )
		MAX-ACCESS			 read-only
		STATUS					 current
		DESCRIPTION			 " -- "
		::=  { sfn3avgripEntry  24 }


	plsfn3Prb22RIPAvg		 OBJECT-TYPE
		SYNTAX					 Integer32( -2147483648 .. 2147483647 )
		MAX-ACCESS			 read-only
		STATUS					 current
		DESCRIPTION			 " -- "
		::=  { sfn3avgripEntry  25 }


	plsfn3Prb23RIPAvg		 OBJECT-TYPE
		SYNTAX					 Integer32( -2147483648 .. 2147483647 )
		MAX-ACCESS			 read-only
		STATUS					 current
		DESCRIPTION			 " -- "
		::=  { sfn3avgripEntry  26 }


	plsfn3Prb24RIPAvg		 OBJECT-TYPE
		SYNTAX					 Integer32( -2147483648 .. 2147483647 )
		MAX-ACCESS			 read-only
		STATUS					 current
		DESCRIPTION			 " -- "
		::=  { sfn3avgripEntry  27 }


	plsfn3Prb25RIPAvg		 OBJECT-TYPE
		SYNTAX					 Integer32( -2147483648 .. 2147483647 )
		MAX-ACCESS			 read-only
		STATUS					 current
		DESCRIPTION			 " -- "
		::=  { sfn3avgripEntry  28 }


	plsfn3Prb26RIPAvg		 OBJECT-TYPE
		SYNTAX					 Integer32( -2147483648 .. 2147483647 )
		MAX-ACCESS			 read-only
		STATUS					 current
		DESCRIPTION			 " -- "
		::=  { sfn3avgripEntry  29 }


	plsfn3Prb27RIPAvg		 OBJECT-TYPE
		SYNTAX					 Integer32( -2147483648 .. 2147483647 )
		MAX-ACCESS			 read-only
		STATUS					 current
		DESCRIPTION			 " -- "
		::=  { sfn3avgripEntry  30 }


	plsfn3Prb28RIPAvg		 OBJECT-TYPE
		SYNTAX					 Integer32( -2147483648 .. 2147483647 )
		MAX-ACCESS			 read-only
		STATUS					 current
		DESCRIPTION			 " -- "
		::=  { sfn3avgripEntry  31 }


	plsfn3Prb29RIPAvg		 OBJECT-TYPE
		SYNTAX					 Integer32( -2147483648 .. 2147483647 )
		MAX-ACCESS			 read-only
		STATUS					 current
		DESCRIPTION			 " -- "
		::=  { sfn3avgripEntry  32 }


	plsfn3Prb30RIPAvg		 OBJECT-TYPE
		SYNTAX					 Integer32( -2147483648 .. 2147483647 )
		MAX-ACCESS			 read-only
		STATUS					 current
		DESCRIPTION			 " -- "
		::=  { sfn3avgripEntry  33 }


	plsfn3Prb31RIPAvg		 OBJECT-TYPE
		SYNTAX					 Integer32( -2147483648 .. 2147483647 )
		MAX-ACCESS			 read-only
		STATUS					 current
		DESCRIPTION			 " -- "
		::=  { sfn3avgripEntry  34 }


	plsfn3Prb32RIPAvg		 OBJECT-TYPE
		SYNTAX					 Integer32( -2147483648 .. 2147483647 )
		MAX-ACCESS			 read-only
		STATUS					 current
		DESCRIPTION			 " -- "
		::=  { sfn3avgripEntry  35 }


	plsfn3Prb33RIPAvg		 OBJECT-TYPE
		SYNTAX					 Integer32( -2147483648 .. 2147483647 )
		MAX-ACCESS			 read-only
		STATUS					 current
		DESCRIPTION			 " -- "
		::=  { sfn3avgripEntry  36 }


	plsfn3Prb34RIPAvg		 OBJECT-TYPE
		SYNTAX					 Integer32( -2147483648 .. 2147483647 )
		MAX-ACCESS			 read-only
		STATUS					 current
		DESCRIPTION			 " -- "
		::=  { sfn3avgripEntry  37 }


	plsfn3Prb35RIPAvg		 OBJECT-TYPE
		SYNTAX					 Integer32( -2147483648 .. 2147483647 )
		MAX-ACCESS			 read-only
		STATUS					 current
		DESCRIPTION			 " -- "
		::=  { sfn3avgripEntry  38 }


	plsfn3Prb36RIPAvg		 OBJECT-TYPE
		SYNTAX					 Integer32( -2147483648 .. 2147483647 )
		MAX-ACCESS			 read-only
		STATUS					 current
		DESCRIPTION			 " -- "
		::=  { sfn3avgripEntry  39 }


	plsfn3Prb37RIPAvg		 OBJECT-TYPE
		SYNTAX					 Integer32( -2147483648 .. 2147483647 )
		MAX-ACCESS			 read-only
		STATUS					 current
		DESCRIPTION			 " -- "
		::=  { sfn3avgripEntry  40 }


	plsfn3Prb38RIPAvg		 OBJECT-TYPE
		SYNTAX					 Integer32( -2147483648 .. 2147483647 )
		MAX-ACCESS			 read-only
		STATUS					 current
		DESCRIPTION			 " -- "
		::=  { sfn3avgripEntry  41 }


	plsfn3Prb39RIPAvg		 OBJECT-TYPE
		SYNTAX					 Integer32( -2147483648 .. 2147483647 )
		MAX-ACCESS			 read-only
		STATUS					 current
		DESCRIPTION			 " -- "
		::=  { sfn3avgripEntry  42 }


	plsfn3Prb40RIPAvg		 OBJECT-TYPE
		SYNTAX					 Integer32( -2147483648 .. 2147483647 )
		MAX-ACCESS			 read-only
		STATUS					 current
		DESCRIPTION			 " -- "
		::=  { sfn3avgripEntry  43 }


	plsfn3Prb41RIPAvg		 OBJECT-TYPE
		SYNTAX					 Integer32( -2147483648 .. 2147483647 )
		MAX-ACCESS			 read-only
		STATUS					 current
		DESCRIPTION			 " -- "
		::=  { sfn3avgripEntry  44 }


	plsfn3Prb42RIPAvg		 OBJECT-TYPE
		SYNTAX					 Integer32( -2147483648 .. 2147483647 )
		MAX-ACCESS			 read-only
		STATUS					 current
		DESCRIPTION			 " -- "
		::=  { sfn3avgripEntry  45 }


	plsfn3Prb43RIPAvg		 OBJECT-TYPE
		SYNTAX					 Integer32( -2147483648 .. 2147483647 )
		MAX-ACCESS			 read-only
		STATUS					 current
		DESCRIPTION			 " -- "
		::=  { sfn3avgripEntry  46 }


	plsfn3Prb44RIPAvg		 OBJECT-TYPE
		SYNTAX					 Integer32( -2147483648 .. 2147483647 )
		MAX-ACCESS			 read-only
		STATUS					 current
		DESCRIPTION			 " -- "
		::=  { sfn3avgripEntry  47 }


	plsfn3Prb45RIPAvg		 OBJECT-TYPE
		SYNTAX					 Integer32( -2147483648 .. 2147483647 )
		MAX-ACCESS			 read-only
		STATUS					 current
		DESCRIPTION			 " -- "
		::=  { sfn3avgripEntry  48 }


	plsfn3Prb46RIPAvg		 OBJECT-TYPE
		SYNTAX					 Integer32( -2147483648 .. 2147483647 )
		MAX-ACCESS			 read-only
		STATUS					 current
		DESCRIPTION			 " -- "
		::=  { sfn3avgripEntry  49 }


	plsfn3Prb47RIPAvg		 OBJECT-TYPE
		SYNTAX					 Integer32( -2147483648 .. 2147483647 )
		MAX-ACCESS			 read-only
		STATUS					 current
		DESCRIPTION			 " -- "
		::=  { sfn3avgripEntry  50 }


	plsfn3Prb48RIPAvg		 OBJECT-TYPE
		SYNTAX					 Integer32( -2147483648 .. 2147483647 )
		MAX-ACCESS			 read-only
		STATUS					 current
		DESCRIPTION			 " -- "
		::=  { sfn3avgripEntry  51 }


	plsfn3Prb49RIPAvg		 OBJECT-TYPE
		SYNTAX					 Integer32( -2147483648 .. 2147483647 )
		MAX-ACCESS			 read-only
		STATUS					 current
		DESCRIPTION			 " -- "
		::=  { sfn3avgripEntry  52 }


	plsfn3Prb50RIPAvg		 OBJECT-TYPE
		SYNTAX					 Integer32( -2147483648 .. 2147483647 )
		MAX-ACCESS			 read-only
		STATUS					 current
		DESCRIPTION			 " -- "
		::=  { sfn3avgripEntry  53 }


	plsfn3Prb51RIPAvg		 OBJECT-TYPE
		SYNTAX					 Integer32( -2147483648 .. 2147483647 )
		MAX-ACCESS			 read-only
		STATUS					 current
		DESCRIPTION			 " -- "
		::=  { sfn3avgripEntry  54 }


	plsfn3Prb52RIPAvg		 OBJECT-TYPE
		SYNTAX					 Integer32( -2147483648 .. 2147483647 )
		MAX-ACCESS			 read-only
		STATUS					 current
		DESCRIPTION			 " -- "
		::=  { sfn3avgripEntry  55 }


	plsfn3Prb53RIPAvg		 OBJECT-TYPE
		SYNTAX					 Integer32( -2147483648 .. 2147483647 )
		MAX-ACCESS			 read-only
		STATUS					 current
		DESCRIPTION			 " -- "
		::=  { sfn3avgripEntry  56 }


	plsfn3Prb54RIPAvg		 OBJECT-TYPE
		SYNTAX					 Integer32( -2147483648 .. 2147483647 )
		MAX-ACCESS			 read-only
		STATUS					 current
		DESCRIPTION			 " -- "
		::=  { sfn3avgripEntry  57 }


	plsfn3Prb55RIPAvg		 OBJECT-TYPE
		SYNTAX					 Integer32( -2147483648 .. 2147483647 )
		MAX-ACCESS			 read-only
		STATUS					 current
		DESCRIPTION			 " -- "
		::=  { sfn3avgripEntry  58 }


	plsfn3Prb56RIPAvg		 OBJECT-TYPE
		SYNTAX					 Integer32( -2147483648 .. 2147483647 )
		MAX-ACCESS			 read-only
		STATUS					 current
		DESCRIPTION			 " -- "
		::=  { sfn3avgripEntry  59 }


	plsfn3Prb57RIPAvg		 OBJECT-TYPE
		SYNTAX					 Integer32( -2147483648 .. 2147483647 )
		MAX-ACCESS			 read-only
		STATUS					 current
		DESCRIPTION			 " -- "
		::=  { sfn3avgripEntry  60 }


	plsfn3Prb58RIPAvg		 OBJECT-TYPE
		SYNTAX					 Integer32( -2147483648 .. 2147483647 )
		MAX-ACCESS			 read-only
		STATUS					 current
		DESCRIPTION			 " -- "
		::=  { sfn3avgripEntry  61 }


	plsfn3Prb59RIPAvg		 OBJECT-TYPE
		SYNTAX					 Integer32( -2147483648 .. 2147483647 )
		MAX-ACCESS			 read-only
		STATUS					 current
		DESCRIPTION			 " -- "
		::=  { sfn3avgripEntry  62 }


	plsfn3Prb60RIPAvg		 OBJECT-TYPE
		SYNTAX					 Integer32( -2147483648 .. 2147483647 )
		MAX-ACCESS			 read-only
		STATUS					 current
		DESCRIPTION			 " -- "
		::=  { sfn3avgripEntry  63 }


	plsfn3Prb61RIPAvg		 OBJECT-TYPE
		SYNTAX					 Integer32( -2147483648 .. 2147483647 )
		MAX-ACCESS			 read-only
		STATUS					 current
		DESCRIPTION			 " -- "
		::=  { sfn3avgripEntry  64 }


	plsfn3Prb62RIPAvg		 OBJECT-TYPE
		SYNTAX					 Integer32( -2147483648 .. 2147483647 )
		MAX-ACCESS			 read-only
		STATUS					 current
		DESCRIPTION			 " -- "
		::=  { sfn3avgripEntry  65 }


	plsfn3Prb63RIPAvg		 OBJECT-TYPE
		SYNTAX					 Integer32( -2147483648 .. 2147483647 )
		MAX-ACCESS			 read-only
		STATUS					 current
		DESCRIPTION			 " -- "
		::=  { sfn3avgripEntry  66 }


	plsfn3Prb64RIPAvg		 OBJECT-TYPE
		SYNTAX					 Integer32( -2147483648 .. 2147483647 )
		MAX-ACCESS			 read-only
		STATUS					 current
		DESCRIPTION			 " -- "
		::=  { sfn3avgripEntry  67 }


	plsfn3Prb65RIPAvg		 OBJECT-TYPE
		SYNTAX					 Integer32( -2147483648 .. 2147483647 )
		MAX-ACCESS			 read-only
		STATUS					 current
		DESCRIPTION			 " -- "
		::=  { sfn3avgripEntry  68 }


	plsfn3Prb66RIPAvg		 OBJECT-TYPE
		SYNTAX					 Integer32( -2147483648 .. 2147483647 )
		MAX-ACCESS			 read-only
		STATUS					 current
		DESCRIPTION			 " -- "
		::=  { sfn3avgripEntry  69 }


	plsfn3Prb67RIPAvg		 OBJECT-TYPE
		SYNTAX					 Integer32( -2147483648 .. 2147483647 )
		MAX-ACCESS			 read-only
		STATUS					 current
		DESCRIPTION			 " -- "
		::=  { sfn3avgripEntry  70 }


	plsfn3Prb68RIPAvg		 OBJECT-TYPE
		SYNTAX					 Integer32( -2147483648 .. 2147483647 )
		MAX-ACCESS			 read-only
		STATUS					 current
		DESCRIPTION			 " -- "
		::=  { sfn3avgripEntry  71 }


	plsfn3Prb69RIPAvg		 OBJECT-TYPE
		SYNTAX					 Integer32( -2147483648 .. 2147483647 )
		MAX-ACCESS			 read-only
		STATUS					 current
		DESCRIPTION			 " -- "
		::=  { sfn3avgripEntry  72 }


	plsfn3Prb70RIPAvg		 OBJECT-TYPE
		SYNTAX					 Integer32( -2147483648 .. 2147483647 )
		MAX-ACCESS			 read-only
		STATUS					 current
		DESCRIPTION			 " -- "
		::=  { sfn3avgripEntry  73 }


	plsfn3Prb71RIPAvg		 OBJECT-TYPE
		SYNTAX					 Integer32( -2147483648 .. 2147483647 )
		MAX-ACCESS			 read-only
		STATUS					 current
		DESCRIPTION			 " -- "
		::=  { sfn3avgripEntry  74 }


	plsfn3Prb72RIPAvg		 OBJECT-TYPE
		SYNTAX					 Integer32( -2147483648 .. 2147483647 )
		MAX-ACCESS			 read-only
		STATUS					 current
		DESCRIPTION			 " -- "
		::=  { sfn3avgripEntry  75 }


	plsfn3Prb73RIPAvg		 OBJECT-TYPE
		SYNTAX					 Integer32( -2147483648 .. 2147483647 )
		MAX-ACCESS			 read-only
		STATUS					 current
		DESCRIPTION			 " -- "
		::=  { sfn3avgripEntry  76 }


	plsfn3Prb74RIPAvg		 OBJECT-TYPE
		SYNTAX					 Integer32( -2147483648 .. 2147483647 )
		MAX-ACCESS			 read-only
		STATUS					 current
		DESCRIPTION			 " -- "
		::=  { sfn3avgripEntry  77 }


	plsfn3Prb75RIPAvg		 OBJECT-TYPE
		SYNTAX					 Integer32( -2147483648 .. 2147483647 )
		MAX-ACCESS			 read-only
		STATUS					 current
		DESCRIPTION			 " -- "
		::=  { sfn3avgripEntry  78 }


	plsfn3Prb76RIPAvg		 OBJECT-TYPE
		SYNTAX					 Integer32( -2147483648 .. 2147483647 )
		MAX-ACCESS			 read-only
		STATUS					 current
		DESCRIPTION			 " -- "
		::=  { sfn3avgripEntry  79 }


	plsfn3Prb77RIPAvg		 OBJECT-TYPE
		SYNTAX					 Integer32( -2147483648 .. 2147483647 )
		MAX-ACCESS			 read-only
		STATUS					 current
		DESCRIPTION			 " -- "
		::=  { sfn3avgripEntry  80 }


	plsfn3Prb78RIPAvg		 OBJECT-TYPE
		SYNTAX					 Integer32( -2147483648 .. 2147483647 )
		MAX-ACCESS			 read-only
		STATUS					 current
		DESCRIPTION			 " -- "
		::=  { sfn3avgripEntry  81 }


	plsfn3Prb79RIPAvg		 OBJECT-TYPE
		SYNTAX					 Integer32( -2147483648 .. 2147483647 )
		MAX-ACCESS			 read-only
		STATUS					 current
		DESCRIPTION			 " -- "
		::=  { sfn3avgripEntry  82 }


	plsfn3Prb80RIPAvg		 OBJECT-TYPE
		SYNTAX					 Integer32( -2147483648 .. 2147483647 )
		MAX-ACCESS			 read-only
		STATUS					 current
		DESCRIPTION			 " -- "
		::=  { sfn3avgripEntry  83 }


	plsfn3Prb81RIPAvg		 OBJECT-TYPE
		SYNTAX					 Integer32( -2147483648 .. 2147483647 )
		MAX-ACCESS			 read-only
		STATUS					 current
		DESCRIPTION			 " -- "
		::=  { sfn3avgripEntry  84 }


	plsfn3Prb82RIPAvg		 OBJECT-TYPE
		SYNTAX					 Integer32( -2147483648 .. 2147483647 )
		MAX-ACCESS			 read-only
		STATUS					 current
		DESCRIPTION			 " -- "
		::=  { sfn3avgripEntry  85 }


	plsfn3Prb83RIPAvg		 OBJECT-TYPE
		SYNTAX					 Integer32( -2147483648 .. 2147483647 )
		MAX-ACCESS			 read-only
		STATUS					 current
		DESCRIPTION			 " -- "
		::=  { sfn3avgripEntry  86 }


	plsfn3Prb84RIPAvg		 OBJECT-TYPE
		SYNTAX					 Integer32( -2147483648 .. 2147483647 )
		MAX-ACCESS			 read-only
		STATUS					 current
		DESCRIPTION			 " -- "
		::=  { sfn3avgripEntry  87 }


	plsfn3Prb85RIPAvg		 OBJECT-TYPE
		SYNTAX					 Integer32( -2147483648 .. 2147483647 )
		MAX-ACCESS			 read-only
		STATUS					 current
		DESCRIPTION			 " -- "
		::=  { sfn3avgripEntry  88 }


	plsfn3Prb86RIPAvg		 OBJECT-TYPE
		SYNTAX					 Integer32( -2147483648 .. 2147483647 )
		MAX-ACCESS			 read-only
		STATUS					 current
		DESCRIPTION			 " -- "
		::=  { sfn3avgripEntry  89 }


	plsfn3Prb87RIPAvg		 OBJECT-TYPE
		SYNTAX					 Integer32( -2147483648 .. 2147483647 )
		MAX-ACCESS			 read-only
		STATUS					 current
		DESCRIPTION			 " -- "
		::=  { sfn3avgripEntry  90 }


	plsfn3Prb88RIPAvg		 OBJECT-TYPE
		SYNTAX					 Integer32( -2147483648 .. 2147483647 )
		MAX-ACCESS			 read-only
		STATUS					 current
		DESCRIPTION			 " -- "
		::=  { sfn3avgripEntry  91 }


	plsfn3Prb89RIPAvg		 OBJECT-TYPE
		SYNTAX					 Integer32( -2147483648 .. 2147483647 )
		MAX-ACCESS			 read-only
		STATUS					 current
		DESCRIPTION			 " -- "
		::=  { sfn3avgripEntry  92 }


	plsfn3Prb90RIPAvg		 OBJECT-TYPE
		SYNTAX					 Integer32( -2147483648 .. 2147483647 )
		MAX-ACCESS			 read-only
		STATUS					 current
		DESCRIPTION			 " -- "
		::=  { sfn3avgripEntry  93 }


	plsfn3Prb91RIPAvg		 OBJECT-TYPE
		SYNTAX					 Integer32( -2147483648 .. 2147483647 )
		MAX-ACCESS			 read-only
		STATUS					 current
		DESCRIPTION			 " -- "
		::=  { sfn3avgripEntry  94 }


	plsfn3Prb92RIPAvg		 OBJECT-TYPE
		SYNTAX					 Integer32( -2147483648 .. 2147483647 )
		MAX-ACCESS			 read-only
		STATUS					 current
		DESCRIPTION			 " -- "
		::=  { sfn3avgripEntry  95 }


	plsfn3Prb93RIPAvg		 OBJECT-TYPE
		SYNTAX					 Integer32( -2147483648 .. 2147483647 )
		MAX-ACCESS			 read-only
		STATUS					 current
		DESCRIPTION			 " -- "
		::=  { sfn3avgripEntry  96 }


	plsfn3Prb94RIPAvg		 OBJECT-TYPE
		SYNTAX					 Integer32( -2147483648 .. 2147483647 )
		MAX-ACCESS			 read-only
		STATUS					 current
		DESCRIPTION			 " -- "
		::=  { sfn3avgripEntry  97 }


	plsfn3Prb95RIPAvg		 OBJECT-TYPE
		SYNTAX					 Integer32( -2147483648 .. 2147483647 )
		MAX-ACCESS			 read-only
		STATUS					 current
		DESCRIPTION			 " -- "
		::=  { sfn3avgripEntry  98 }


	plsfn3Prb96RIPAvg		 OBJECT-TYPE
		SYNTAX					 Integer32( -2147483648 .. 2147483647 )
		MAX-ACCESS			 read-only
		STATUS					 current
		DESCRIPTION			 " -- "
		::=  { sfn3avgripEntry  99 }


	plsfn3Prb97RIPAvg		 OBJECT-TYPE
		SYNTAX					 Integer32( -2147483648 .. 2147483647 )
		MAX-ACCESS			 read-only
		STATUS					 current
		DESCRIPTION			 " -- "
		::=  { sfn3avgripEntry  100 }


	plsfn3Prb98RIPAvg		 OBJECT-TYPE
		SYNTAX					 Integer32( -2147483648 .. 2147483647 )
		MAX-ACCESS			 read-only
		STATUS					 current
		DESCRIPTION			 " -- "
		::=  { sfn3avgripEntry  101 }


	plsfn3Prb99RIPAvg		 OBJECT-TYPE
		SYNTAX					 Integer32( -2147483648 .. 2147483647 )
		MAX-ACCESS			 read-only
		STATUS					 current
		DESCRIPTION			 " -- "
		::=  { sfn3avgripEntry  102 }


	sfn5avgripTable		 OBJECT-TYPE
		SYNTAX					 SEQUENCE  OF	 Sfn5avgripEntry
		MAX-ACCESS			 not-accessible
		STATUS					 current
		DESCRIPTION			 " -- "
		::=  { plrelatedOriginCounter  9 }


	sfn5avgripEntry		 OBJECT-TYPE
		SYNTAX					 Sfn5avgripEntry
		MAX-ACCESS			 not-accessible
		STATUS					 current
		DESCRIPTION			 " -- "
		INDEX						{ sfn5avgripLcId }
		::=  { sfn5avgripTable  1 }


	Sfn5avgripEntry		 ::=  SEQUENCE {
		sfn5avgripLcId					Integer32,
		sfn5avgripRowStatus					RowStatus,
		plsfn5Prb00RIPAvg					Integer32,
		plsfn5Prb01RIPAvg					Integer32,
		plsfn5Prb02RIPAvg					Integer32,
		plsfn5Prb03RIPAvg					Integer32,
		plsfn5Prb04RIPAvg					Integer32,
		plsfn5Prb05RIPAvg					Integer32,
		plsfn5Prb06RIPAvg					Integer32,
		plsfn5Prb07RIPAvg					Integer32,
		plsfn5Prb08RIPAvg					Integer32,
		plsfn5Prb09RIPAvg					Integer32,
		plsfn5Prb10RIPAvg					Integer32,
		plsfn5Prb11RIPAvg					Integer32,
		plsfn5Prb12RIPAvg					Integer32,
		plsfn5Prb13RIPAvg					Integer32,
		plsfn5Prb14RIPAvg					Integer32,
		plsfn5Prb15RIPAvg					Integer32,
		plsfn5Prb16RIPAvg					Integer32,
		plsfn5Prb17RIPAvg					Integer32,
		plsfn5Prb18RIPAvg					Integer32,
		plsfn5Prb19RIPAvg					Integer32,
		plsfn5Prb20RIPAvg					Integer32,
		plsfn5Prb21RIPAvg					Integer32,
		plsfn5Prb22RIPAvg					Integer32,
		plsfn5Prb23RIPAvg					Integer32,
		plsfn5Prb24RIPAvg					Integer32,
		plsfn5Prb25RIPAvg					Integer32,
		plsfn5Prb26RIPAvg					Integer32,
		plsfn5Prb27RIPAvg					Integer32,
		plsfn5Prb28RIPAvg					Integer32,
		plsfn5Prb29RIPAvg					Integer32,
		plsfn5Prb30RIPAvg					Integer32,
		plsfn5Prb31RIPAvg					Integer32,
		plsfn5Prb32RIPAvg					Integer32,
		plsfn5Prb33RIPAvg					Integer32,
		plsfn5Prb34RIPAvg					Integer32,
		plsfn5Prb35RIPAvg					Integer32,
		plsfn5Prb36RIPAvg					Integer32,
		plsfn5Prb37RIPAvg					Integer32,
		plsfn5Prb38RIPAvg					Integer32,
		plsfn5Prb39RIPAvg					Integer32,
		plsfn5Prb40RIPAvg					Integer32,
		plsfn5Prb41RIPAvg					Integer32,
		plsfn5Prb42RIPAvg					Integer32,
		plsfn5Prb43RIPAvg					Integer32,
		plsfn5Prb44RIPAvg					Integer32,
		plsfn5Prb45RIPAvg					Integer32,
		plsfn5Prb46RIPAvg					Integer32,
		plsfn5Prb47RIPAvg					Integer32,
		plsfn5Prb48RIPAvg					Integer32,
		plsfn5Prb49RIPAvg					Integer32,
		plsfn5Prb50RIPAvg					Integer32,
		plsfn5Prb51RIPAvg					Integer32,
		plsfn5Prb52RIPAvg					Integer32,
		plsfn5Prb53RIPAvg					Integer32,
		plsfn5Prb54RIPAvg					Integer32,
		plsfn5Prb55RIPAvg					Integer32,
		plsfn5Prb56RIPAvg					Integer32,
		plsfn5Prb57RIPAvg					Integer32,
		plsfn5Prb58RIPAvg					Integer32,
		plsfn5Prb59RIPAvg					Integer32,
		plsfn5Prb60RIPAvg					Integer32,
		plsfn5Prb61RIPAvg					Integer32,
		plsfn5Prb62RIPAvg					Integer32,
		plsfn5Prb63RIPAvg					Integer32,
		plsfn5Prb64RIPAvg					Integer32,
		plsfn5Prb65RIPAvg					Integer32,
		plsfn5Prb66RIPAvg					Integer32,
		plsfn5Prb67RIPAvg					Integer32,
		plsfn5Prb68RIPAvg					Integer32,
		plsfn5Prb69RIPAvg					Integer32,
		plsfn5Prb70RIPAvg					Integer32,
		plsfn5Prb71RIPAvg					Integer32,
		plsfn5Prb72RIPAvg					Integer32,
		plsfn5Prb73RIPAvg					Integer32,
		plsfn5Prb74RIPAvg					Integer32,
		plsfn5Prb75RIPAvg					Integer32,
		plsfn5Prb76RIPAvg					Integer32,
		plsfn5Prb77RIPAvg					Integer32,
		plsfn5Prb78RIPAvg					Integer32,
		plsfn5Prb79RIPAvg					Integer32,
		plsfn5Prb80RIPAvg					Integer32,
		plsfn5Prb81RIPAvg					Integer32,
		plsfn5Prb82RIPAvg					Integer32,
		plsfn5Prb83RIPAvg					Integer32,
		plsfn5Prb84RIPAvg					Integer32,
		plsfn5Prb85RIPAvg					Integer32,
		plsfn5Prb86RIPAvg					Integer32,
		plsfn5Prb87RIPAvg					Integer32,
		plsfn5Prb88RIPAvg					Integer32,
		plsfn5Prb89RIPAvg					Integer32,
		plsfn5Prb90RIPAvg					Integer32,
		plsfn5Prb91RIPAvg					Integer32,
		plsfn5Prb92RIPAvg					Integer32,
		plsfn5Prb93RIPAvg					Integer32,
		plsfn5Prb94RIPAvg					Integer32,
		plsfn5Prb95RIPAvg					Integer32,
		plsfn5Prb96RIPAvg					Integer32,
		plsfn5Prb97RIPAvg					Integer32,
		plsfn5Prb98RIPAvg					Integer32,
		plsfn5Prb99RIPAvg					Integer32
		}


	sfn5avgripLcId		 OBJECT-TYPE
		SYNTAX					 Integer32( 0 .. 23 )
		MAX-ACCESS			 not-accessible
		STATUS					 current
		DESCRIPTION			 " -- "
		::=  { sfn5avgripEntry  1 }


	sfn5avgripRowStatus		 OBJECT-TYPE
		SYNTAX					 RowStatus
		MAX-ACCESS			 read-only
		STATUS					 current
		DESCRIPTION			 " -- "
		::=  { sfn5avgripEntry  2 }


	plsfn5Prb00RIPAvg		 OBJECT-TYPE
		SYNTAX					 Integer32( -2147483648 .. 2147483647 )
		MAX-ACCESS			 read-only
		STATUS					 current
		DESCRIPTION			 " -- "
		::=  { sfn5avgripEntry  3 }


	plsfn5Prb01RIPAvg		 OBJECT-TYPE
		SYNTAX					 Integer32( -2147483648 .. 2147483647 )
		MAX-ACCESS			 read-only
		STATUS					 current
		DESCRIPTION			 " -- "
		::=  { sfn5avgripEntry  4 }


	plsfn5Prb02RIPAvg		 OBJECT-TYPE
		SYNTAX					 Integer32( -2147483648 .. 2147483647 )
		MAX-ACCESS			 read-only
		STATUS					 current
		DESCRIPTION			 " -- "
		::=  { sfn5avgripEntry  5 }


	plsfn5Prb03RIPAvg		 OBJECT-TYPE
		SYNTAX					 Integer32( -2147483648 .. 2147483647 )
		MAX-ACCESS			 read-only
		STATUS					 current
		DESCRIPTION			 " -- "
		::=  { sfn5avgripEntry  6 }


	plsfn5Prb04RIPAvg		 OBJECT-TYPE
		SYNTAX					 Integer32( -2147483648 .. 2147483647 )
		MAX-ACCESS			 read-only
		STATUS					 current
		DESCRIPTION			 " -- "
		::=  { sfn5avgripEntry  7 }


	plsfn5Prb05RIPAvg		 OBJECT-TYPE
		SYNTAX					 Integer32( -2147483648 .. 2147483647 )
		MAX-ACCESS			 read-only
		STATUS					 current
		DESCRIPTION			 " -- "
		::=  { sfn5avgripEntry  8 }


	plsfn5Prb06RIPAvg		 OBJECT-TYPE
		SYNTAX					 Integer32( -2147483648 .. 2147483647 )
		MAX-ACCESS			 read-only
		STATUS					 current
		DESCRIPTION			 " -- "
		::=  { sfn5avgripEntry  9 }


	plsfn5Prb07RIPAvg		 OBJECT-TYPE
		SYNTAX					 Integer32( -2147483648 .. 2147483647 )
		MAX-ACCESS			 read-only
		STATUS					 current
		DESCRIPTION			 " -- "
		::=  { sfn5avgripEntry  10 }


	plsfn5Prb08RIPAvg		 OBJECT-TYPE
		SYNTAX					 Integer32( -2147483648 .. 2147483647 )
		MAX-ACCESS			 read-only
		STATUS					 current
		DESCRIPTION			 " -- "
		::=  { sfn5avgripEntry  11 }


	plsfn5Prb09RIPAvg		 OBJECT-TYPE
		SYNTAX					 Integer32( -2147483648 .. 2147483647 )
		MAX-ACCESS			 read-only
		STATUS					 current
		DESCRIPTION			 " -- "
		::=  { sfn5avgripEntry  12 }


	plsfn5Prb10RIPAvg		 OBJECT-TYPE
		SYNTAX					 Integer32( -2147483648 .. 2147483647 )
		MAX-ACCESS			 read-only
		STATUS					 current
		DESCRIPTION			 " -- "
		::=  { sfn5avgripEntry  13 }


	plsfn5Prb11RIPAvg		 OBJECT-TYPE
		SYNTAX					 Integer32( -2147483648 .. 2147483647 )
		MAX-ACCESS			 read-only
		STATUS					 current
		DESCRIPTION			 " -- "
		::=  { sfn5avgripEntry  14 }


	plsfn5Prb12RIPAvg		 OBJECT-TYPE
		SYNTAX					 Integer32( -2147483648 .. 2147483647 )
		MAX-ACCESS			 read-only
		STATUS					 current
		DESCRIPTION			 " -- "
		::=  { sfn5avgripEntry  15 }


	plsfn5Prb13RIPAvg		 OBJECT-TYPE
		SYNTAX					 Integer32( -2147483648 .. 2147483647 )
		MAX-ACCESS			 read-only
		STATUS					 current
		DESCRIPTION			 " -- "
		::=  { sfn5avgripEntry  16 }


	plsfn5Prb14RIPAvg		 OBJECT-TYPE
		SYNTAX					 Integer32( -2147483648 .. 2147483647 )
		MAX-ACCESS			 read-only
		STATUS					 current
		DESCRIPTION			 " -- "
		::=  { sfn5avgripEntry  17 }


	plsfn5Prb15RIPAvg		 OBJECT-TYPE
		SYNTAX					 Integer32( -2147483648 .. 2147483647 )
		MAX-ACCESS			 read-only
		STATUS					 current
		DESCRIPTION			 " -- "
		::=  { sfn5avgripEntry  18 }


	plsfn5Prb16RIPAvg		 OBJECT-TYPE
		SYNTAX					 Integer32( -2147483648 .. 2147483647 )
		MAX-ACCESS			 read-only
		STATUS					 current
		DESCRIPTION			 " -- "
		::=  { sfn5avgripEntry  19 }


	plsfn5Prb17RIPAvg		 OBJECT-TYPE
		SYNTAX					 Integer32( -2147483648 .. 2147483647 )
		MAX-ACCESS			 read-only
		STATUS					 current
		DESCRIPTION			 " -- "
		::=  { sfn5avgripEntry  20 }


	plsfn5Prb18RIPAvg		 OBJECT-TYPE
		SYNTAX					 Integer32( -2147483648 .. 2147483647 )
		MAX-ACCESS			 read-only
		STATUS					 current
		DESCRIPTION			 " -- "
		::=  { sfn5avgripEntry  21 }


	plsfn5Prb19RIPAvg		 OBJECT-TYPE
		SYNTAX					 Integer32( -2147483648 .. 2147483647 )
		MAX-ACCESS			 read-only
		STATUS					 current
		DESCRIPTION			 " -- "
		::=  { sfn5avgripEntry  22 }


	plsfn5Prb20RIPAvg		 OBJECT-TYPE
		SYNTAX					 Integer32( -2147483648 .. 2147483647 )
		MAX-ACCESS			 read-only
		STATUS					 current
		DESCRIPTION			 " -- "
		::=  { sfn5avgripEntry  23 }


	plsfn5Prb21RIPAvg		 OBJECT-TYPE
		SYNTAX					 Integer32( -2147483648 .. 2147483647 )
		MAX-ACCESS			 read-only
		STATUS					 current
		DESCRIPTION			 " -- "
		::=  { sfn5avgripEntry  24 }


	plsfn5Prb22RIPAvg		 OBJECT-TYPE
		SYNTAX					 Integer32( -2147483648 .. 2147483647 )
		MAX-ACCESS			 read-only
		STATUS					 current
		DESCRIPTION			 " -- "
		::=  { sfn5avgripEntry  25 }


	plsfn5Prb23RIPAvg		 OBJECT-TYPE
		SYNTAX					 Integer32( -2147483648 .. 2147483647 )
		MAX-ACCESS			 read-only
		STATUS					 current
		DESCRIPTION			 " -- "
		::=  { sfn5avgripEntry  26 }


	plsfn5Prb24RIPAvg		 OBJECT-TYPE
		SYNTAX					 Integer32( -2147483648 .. 2147483647 )
		MAX-ACCESS			 read-only
		STATUS					 current
		DESCRIPTION			 " -- "
		::=  { sfn5avgripEntry  27 }


	plsfn5Prb25RIPAvg		 OBJECT-TYPE
		SYNTAX					 Integer32( -2147483648 .. 2147483647 )
		MAX-ACCESS			 read-only
		STATUS					 current
		DESCRIPTION			 " -- "
		::=  { sfn5avgripEntry  28 }


	plsfn5Prb26RIPAvg		 OBJECT-TYPE
		SYNTAX					 Integer32( -2147483648 .. 2147483647 )
		MAX-ACCESS			 read-only
		STATUS					 current
		DESCRIPTION			 " -- "
		::=  { sfn5avgripEntry  29 }


	plsfn5Prb27RIPAvg		 OBJECT-TYPE
		SYNTAX					 Integer32( -2147483648 .. 2147483647 )
		MAX-ACCESS			 read-only
		STATUS					 current
		DESCRIPTION			 " -- "
		::=  { sfn5avgripEntry  30 }


	plsfn5Prb28RIPAvg		 OBJECT-TYPE
		SYNTAX					 Integer32( -2147483648 .. 2147483647 )
		MAX-ACCESS			 read-only
		STATUS					 current
		DESCRIPTION			 " -- "
		::=  { sfn5avgripEntry  31 }


	plsfn5Prb29RIPAvg		 OBJECT-TYPE
		SYNTAX					 Integer32( -2147483648 .. 2147483647 )
		MAX-ACCESS			 read-only
		STATUS					 current
		DESCRIPTION			 " -- "
		::=  { sfn5avgripEntry  32 }


	plsfn5Prb30RIPAvg		 OBJECT-TYPE
		SYNTAX					 Integer32( -2147483648 .. 2147483647 )
		MAX-ACCESS			 read-only
		STATUS					 current
		DESCRIPTION			 " -- "
		::=  { sfn5avgripEntry  33 }


	plsfn5Prb31RIPAvg		 OBJECT-TYPE
		SYNTAX					 Integer32( -2147483648 .. 2147483647 )
		MAX-ACCESS			 read-only
		STATUS					 current
		DESCRIPTION			 " -- "
		::=  { sfn5avgripEntry  34 }


	plsfn5Prb32RIPAvg		 OBJECT-TYPE
		SYNTAX					 Integer32( -2147483648 .. 2147483647 )
		MAX-ACCESS			 read-only
		STATUS					 current
		DESCRIPTION			 " -- "
		::=  { sfn5avgripEntry  35 }


	plsfn5Prb33RIPAvg		 OBJECT-TYPE
		SYNTAX					 Integer32( -2147483648 .. 2147483647 )
		MAX-ACCESS			 read-only
		STATUS					 current
		DESCRIPTION			 " -- "
		::=  { sfn5avgripEntry  36 }


	plsfn5Prb34RIPAvg		 OBJECT-TYPE
		SYNTAX					 Integer32( -2147483648 .. 2147483647 )
		MAX-ACCESS			 read-only
		STATUS					 current
		DESCRIPTION			 " -- "
		::=  { sfn5avgripEntry  37 }


	plsfn5Prb35RIPAvg		 OBJECT-TYPE
		SYNTAX					 Integer32( -2147483648 .. 2147483647 )
		MAX-ACCESS			 read-only
		STATUS					 current
		DESCRIPTION			 " -- "
		::=  { sfn5avgripEntry  38 }


	plsfn5Prb36RIPAvg		 OBJECT-TYPE
		SYNTAX					 Integer32( -2147483648 .. 2147483647 )
		MAX-ACCESS			 read-only
		STATUS					 current
		DESCRIPTION			 " -- "
		::=  { sfn5avgripEntry  39 }


	plsfn5Prb37RIPAvg		 OBJECT-TYPE
		SYNTAX					 Integer32( -2147483648 .. 2147483647 )
		MAX-ACCESS			 read-only
		STATUS					 current
		DESCRIPTION			 " -- "
		::=  { sfn5avgripEntry  40 }


	plsfn5Prb38RIPAvg		 OBJECT-TYPE
		SYNTAX					 Integer32( -2147483648 .. 2147483647 )
		MAX-ACCESS			 read-only
		STATUS					 current
		DESCRIPTION			 " -- "
		::=  { sfn5avgripEntry  41 }


	plsfn5Prb39RIPAvg		 OBJECT-TYPE
		SYNTAX					 Integer32( -2147483648 .. 2147483647 )
		MAX-ACCESS			 read-only
		STATUS					 current
		DESCRIPTION			 " -- "
		::=  { sfn5avgripEntry  42 }


	plsfn5Prb40RIPAvg		 OBJECT-TYPE
		SYNTAX					 Integer32( -2147483648 .. 2147483647 )
		MAX-ACCESS			 read-only
		STATUS					 current
		DESCRIPTION			 " -- "
		::=  { sfn5avgripEntry  43 }


	plsfn5Prb41RIPAvg		 OBJECT-TYPE
		SYNTAX					 Integer32( -2147483648 .. 2147483647 )
		MAX-ACCESS			 read-only
		STATUS					 current
		DESCRIPTION			 " -- "
		::=  { sfn5avgripEntry  44 }


	plsfn5Prb42RIPAvg		 OBJECT-TYPE
		SYNTAX					 Integer32( -2147483648 .. 2147483647 )
		MAX-ACCESS			 read-only
		STATUS					 current
		DESCRIPTION			 " -- "
		::=  { sfn5avgripEntry  45 }


	plsfn5Prb43RIPAvg		 OBJECT-TYPE
		SYNTAX					 Integer32( -2147483648 .. 2147483647 )
		MAX-ACCESS			 read-only
		STATUS					 current
		DESCRIPTION			 " -- "
		::=  { sfn5avgripEntry  46 }


	plsfn5Prb44RIPAvg		 OBJECT-TYPE
		SYNTAX					 Integer32( -2147483648 .. 2147483647 )
		MAX-ACCESS			 read-only
		STATUS					 current
		DESCRIPTION			 " -- "
		::=  { sfn5avgripEntry  47 }


	plsfn5Prb45RIPAvg		 OBJECT-TYPE
		SYNTAX					 Integer32( -2147483648 .. 2147483647 )
		MAX-ACCESS			 read-only
		STATUS					 current
		DESCRIPTION			 " -- "
		::=  { sfn5avgripEntry  48 }


	plsfn5Prb46RIPAvg		 OBJECT-TYPE
		SYNTAX					 Integer32( -2147483648 .. 2147483647 )
		MAX-ACCESS			 read-only
		STATUS					 current
		DESCRIPTION			 " -- "
		::=  { sfn5avgripEntry  49 }


	plsfn5Prb47RIPAvg		 OBJECT-TYPE
		SYNTAX					 Integer32( -2147483648 .. 2147483647 )
		MAX-ACCESS			 read-only
		STATUS					 current
		DESCRIPTION			 " -- "
		::=  { sfn5avgripEntry  50 }


	plsfn5Prb48RIPAvg		 OBJECT-TYPE
		SYNTAX					 Integer32( -2147483648 .. 2147483647 )
		MAX-ACCESS			 read-only
		STATUS					 current
		DESCRIPTION			 " -- "
		::=  { sfn5avgripEntry  51 }


	plsfn5Prb49RIPAvg		 OBJECT-TYPE
		SYNTAX					 Integer32( -2147483648 .. 2147483647 )
		MAX-ACCESS			 read-only
		STATUS					 current
		DESCRIPTION			 " -- "
		::=  { sfn5avgripEntry  52 }


	plsfn5Prb50RIPAvg		 OBJECT-TYPE
		SYNTAX					 Integer32( -2147483648 .. 2147483647 )
		MAX-ACCESS			 read-only
		STATUS					 current
		DESCRIPTION			 " -- "
		::=  { sfn5avgripEntry  53 }


	plsfn5Prb51RIPAvg		 OBJECT-TYPE
		SYNTAX					 Integer32( -2147483648 .. 2147483647 )
		MAX-ACCESS			 read-only
		STATUS					 current
		DESCRIPTION			 " -- "
		::=  { sfn5avgripEntry  54 }


	plsfn5Prb52RIPAvg		 OBJECT-TYPE
		SYNTAX					 Integer32( -2147483648 .. 2147483647 )
		MAX-ACCESS			 read-only
		STATUS					 current
		DESCRIPTION			 " -- "
		::=  { sfn5avgripEntry  55 }


	plsfn5Prb53RIPAvg		 OBJECT-TYPE
		SYNTAX					 Integer32( -2147483648 .. 2147483647 )
		MAX-ACCESS			 read-only
		STATUS					 current
		DESCRIPTION			 " -- "
		::=  { sfn5avgripEntry  56 }


	plsfn5Prb54RIPAvg		 OBJECT-TYPE
		SYNTAX					 Integer32( -2147483648 .. 2147483647 )
		MAX-ACCESS			 read-only
		STATUS					 current
		DESCRIPTION			 " -- "
		::=  { sfn5avgripEntry  57 }


	plsfn5Prb55RIPAvg		 OBJECT-TYPE
		SYNTAX					 Integer32( -2147483648 .. 2147483647 )
		MAX-ACCESS			 read-only
		STATUS					 current
		DESCRIPTION			 " -- "
		::=  { sfn5avgripEntry  58 }


	plsfn5Prb56RIPAvg		 OBJECT-TYPE
		SYNTAX					 Integer32( -2147483648 .. 2147483647 )
		MAX-ACCESS			 read-only
		STATUS					 current
		DESCRIPTION			 " -- "
		::=  { sfn5avgripEntry  59 }


	plsfn5Prb57RIPAvg		 OBJECT-TYPE
		SYNTAX					 Integer32( -2147483648 .. 2147483647 )
		MAX-ACCESS			 read-only
		STATUS					 current
		DESCRIPTION			 " -- "
		::=  { sfn5avgripEntry  60 }


	plsfn5Prb58RIPAvg		 OBJECT-TYPE
		SYNTAX					 Integer32( -2147483648 .. 2147483647 )
		MAX-ACCESS			 read-only
		STATUS					 current
		DESCRIPTION			 " -- "
		::=  { sfn5avgripEntry  61 }


	plsfn5Prb59RIPAvg		 OBJECT-TYPE
		SYNTAX					 Integer32( -2147483648 .. 2147483647 )
		MAX-ACCESS			 read-only
		STATUS					 current
		DESCRIPTION			 " -- "
		::=  { sfn5avgripEntry  62 }


	plsfn5Prb60RIPAvg		 OBJECT-TYPE
		SYNTAX					 Integer32( -2147483648 .. 2147483647 )
		MAX-ACCESS			 read-only
		STATUS					 current
		DESCRIPTION			 " -- "
		::=  { sfn5avgripEntry  63 }


	plsfn5Prb61RIPAvg		 OBJECT-TYPE
		SYNTAX					 Integer32( -2147483648 .. 2147483647 )
		MAX-ACCESS			 read-only
		STATUS					 current
		DESCRIPTION			 " -- "
		::=  { sfn5avgripEntry  64 }


	plsfn5Prb62RIPAvg		 OBJECT-TYPE
		SYNTAX					 Integer32( -2147483648 .. 2147483647 )
		MAX-ACCESS			 read-only
		STATUS					 current
		DESCRIPTION			 " -- "
		::=  { sfn5avgripEntry  65 }


	plsfn5Prb63RIPAvg		 OBJECT-TYPE
		SYNTAX					 Integer32( -2147483648 .. 2147483647 )
		MAX-ACCESS			 read-only
		STATUS					 current
		DESCRIPTION			 " -- "
		::=  { sfn5avgripEntry  66 }


	plsfn5Prb64RIPAvg		 OBJECT-TYPE
		SYNTAX					 Integer32( -2147483648 .. 2147483647 )
		MAX-ACCESS			 read-only
		STATUS					 current
		DESCRIPTION			 " -- "
		::=  { sfn5avgripEntry  67 }


	plsfn5Prb65RIPAvg		 OBJECT-TYPE
		SYNTAX					 Integer32( -2147483648 .. 2147483647 )
		MAX-ACCESS			 read-only
		STATUS					 current
		DESCRIPTION			 " -- "
		::=  { sfn5avgripEntry  68 }


	plsfn5Prb66RIPAvg		 OBJECT-TYPE
		SYNTAX					 Integer32( -2147483648 .. 2147483647 )
		MAX-ACCESS			 read-only
		STATUS					 current
		DESCRIPTION			 " -- "
		::=  { sfn5avgripEntry  69 }


	plsfn5Prb67RIPAvg		 OBJECT-TYPE
		SYNTAX					 Integer32( -2147483648 .. 2147483647 )
		MAX-ACCESS			 read-only
		STATUS					 current
		DESCRIPTION			 " -- "
		::=  { sfn5avgripEntry  70 }


	plsfn5Prb68RIPAvg		 OBJECT-TYPE
		SYNTAX					 Integer32( -2147483648 .. 2147483647 )
		MAX-ACCESS			 read-only
		STATUS					 current
		DESCRIPTION			 " -- "
		::=  { sfn5avgripEntry  71 }


	plsfn5Prb69RIPAvg		 OBJECT-TYPE
		SYNTAX					 Integer32( -2147483648 .. 2147483647 )
		MAX-ACCESS			 read-only
		STATUS					 current
		DESCRIPTION			 " -- "
		::=  { sfn5avgripEntry  72 }


	plsfn5Prb70RIPAvg		 OBJECT-TYPE
		SYNTAX					 Integer32( -2147483648 .. 2147483647 )
		MAX-ACCESS			 read-only
		STATUS					 current
		DESCRIPTION			 " -- "
		::=  { sfn5avgripEntry  73 }


	plsfn5Prb71RIPAvg		 OBJECT-TYPE
		SYNTAX					 Integer32( -2147483648 .. 2147483647 )
		MAX-ACCESS			 read-only
		STATUS					 current
		DESCRIPTION			 " -- "
		::=  { sfn5avgripEntry  74 }


	plsfn5Prb72RIPAvg		 OBJECT-TYPE
		SYNTAX					 Integer32( -2147483648 .. 2147483647 )
		MAX-ACCESS			 read-only
		STATUS					 current
		DESCRIPTION			 " -- "
		::=  { sfn5avgripEntry  75 }


	plsfn5Prb73RIPAvg		 OBJECT-TYPE
		SYNTAX					 Integer32( -2147483648 .. 2147483647 )
		MAX-ACCESS			 read-only
		STATUS					 current
		DESCRIPTION			 " -- "
		::=  { sfn5avgripEntry  76 }


	plsfn5Prb74RIPAvg		 OBJECT-TYPE
		SYNTAX					 Integer32( -2147483648 .. 2147483647 )
		MAX-ACCESS			 read-only
		STATUS					 current
		DESCRIPTION			 " -- "
		::=  { sfn5avgripEntry  77 }


	plsfn5Prb75RIPAvg		 OBJECT-TYPE
		SYNTAX					 Integer32( -2147483648 .. 2147483647 )
		MAX-ACCESS			 read-only
		STATUS					 current
		DESCRIPTION			 " -- "
		::=  { sfn5avgripEntry  78 }


	plsfn5Prb76RIPAvg		 OBJECT-TYPE
		SYNTAX					 Integer32( -2147483648 .. 2147483647 )
		MAX-ACCESS			 read-only
		STATUS					 current
		DESCRIPTION			 " -- "
		::=  { sfn5avgripEntry  79 }


	plsfn5Prb77RIPAvg		 OBJECT-TYPE
		SYNTAX					 Integer32( -2147483648 .. 2147483647 )
		MAX-ACCESS			 read-only
		STATUS					 current
		DESCRIPTION			 " -- "
		::=  { sfn5avgripEntry  80 }


	plsfn5Prb78RIPAvg		 OBJECT-TYPE
		SYNTAX					 Integer32( -2147483648 .. 2147483647 )
		MAX-ACCESS			 read-only
		STATUS					 current
		DESCRIPTION			 " -- "
		::=  { sfn5avgripEntry  81 }


	plsfn5Prb79RIPAvg		 OBJECT-TYPE
		SYNTAX					 Integer32( -2147483648 .. 2147483647 )
		MAX-ACCESS			 read-only
		STATUS					 current
		DESCRIPTION			 " -- "
		::=  { sfn5avgripEntry  82 }


	plsfn5Prb80RIPAvg		 OBJECT-TYPE
		SYNTAX					 Integer32( -2147483648 .. 2147483647 )
		MAX-ACCESS			 read-only
		STATUS					 current
		DESCRIPTION			 " -- "
		::=  { sfn5avgripEntry  83 }


	plsfn5Prb81RIPAvg		 OBJECT-TYPE
		SYNTAX					 Integer32( -2147483648 .. 2147483647 )
		MAX-ACCESS			 read-only
		STATUS					 current
		DESCRIPTION			 " -- "
		::=  { sfn5avgripEntry  84 }


	plsfn5Prb82RIPAvg		 OBJECT-TYPE
		SYNTAX					 Integer32( -2147483648 .. 2147483647 )
		MAX-ACCESS			 read-only
		STATUS					 current
		DESCRIPTION			 " -- "
		::=  { sfn5avgripEntry  85 }


	plsfn5Prb83RIPAvg		 OBJECT-TYPE
		SYNTAX					 Integer32( -2147483648 .. 2147483647 )
		MAX-ACCESS			 read-only
		STATUS					 current
		DESCRIPTION			 " -- "
		::=  { sfn5avgripEntry  86 }


	plsfn5Prb84RIPAvg		 OBJECT-TYPE
		SYNTAX					 Integer32( -2147483648 .. 2147483647 )
		MAX-ACCESS			 read-only
		STATUS					 current
		DESCRIPTION			 " -- "
		::=  { sfn5avgripEntry  87 }


	plsfn5Prb85RIPAvg		 OBJECT-TYPE
		SYNTAX					 Integer32( -2147483648 .. 2147483647 )
		MAX-ACCESS			 read-only
		STATUS					 current
		DESCRIPTION			 " -- "
		::=  { sfn5avgripEntry  88 }


	plsfn5Prb86RIPAvg		 OBJECT-TYPE
		SYNTAX					 Integer32( -2147483648 .. 2147483647 )
		MAX-ACCESS			 read-only
		STATUS					 current
		DESCRIPTION			 " -- "
		::=  { sfn5avgripEntry  89 }


	plsfn5Prb87RIPAvg		 OBJECT-TYPE
		SYNTAX					 Integer32( -2147483648 .. 2147483647 )
		MAX-ACCESS			 read-only
		STATUS					 current
		DESCRIPTION			 " -- "
		::=  { sfn5avgripEntry  90 }


	plsfn5Prb88RIPAvg		 OBJECT-TYPE
		SYNTAX					 Integer32( -2147483648 .. 2147483647 )
		MAX-ACCESS			 read-only
		STATUS					 current
		DESCRIPTION			 " -- "
		::=  { sfn5avgripEntry  91 }


	plsfn5Prb89RIPAvg		 OBJECT-TYPE
		SYNTAX					 Integer32( -2147483648 .. 2147483647 )
		MAX-ACCESS			 read-only
		STATUS					 current
		DESCRIPTION			 " -- "
		::=  { sfn5avgripEntry  92 }


	plsfn5Prb90RIPAvg		 OBJECT-TYPE
		SYNTAX					 Integer32( -2147483648 .. 2147483647 )
		MAX-ACCESS			 read-only
		STATUS					 current
		DESCRIPTION			 " -- "
		::=  { sfn5avgripEntry  93 }


	plsfn5Prb91RIPAvg		 OBJECT-TYPE
		SYNTAX					 Integer32( -2147483648 .. 2147483647 )
		MAX-ACCESS			 read-only
		STATUS					 current
		DESCRIPTION			 " -- "
		::=  { sfn5avgripEntry  94 }


	plsfn5Prb92RIPAvg		 OBJECT-TYPE
		SYNTAX					 Integer32( -2147483648 .. 2147483647 )
		MAX-ACCESS			 read-only
		STATUS					 current
		DESCRIPTION			 " -- "
		::=  { sfn5avgripEntry  95 }


	plsfn5Prb93RIPAvg		 OBJECT-TYPE
		SYNTAX					 Integer32( -2147483648 .. 2147483647 )
		MAX-ACCESS			 read-only
		STATUS					 current
		DESCRIPTION			 " -- "
		::=  { sfn5avgripEntry  96 }


	plsfn5Prb94RIPAvg		 OBJECT-TYPE
		SYNTAX					 Integer32( -2147483648 .. 2147483647 )
		MAX-ACCESS			 read-only
		STATUS					 current
		DESCRIPTION			 " -- "
		::=  { sfn5avgripEntry  97 }


	plsfn5Prb95RIPAvg		 OBJECT-TYPE
		SYNTAX					 Integer32( -2147483648 .. 2147483647 )
		MAX-ACCESS			 read-only
		STATUS					 current
		DESCRIPTION			 " -- "
		::=  { sfn5avgripEntry  98 }


	plsfn5Prb96RIPAvg		 OBJECT-TYPE
		SYNTAX					 Integer32( -2147483648 .. 2147483647 )
		MAX-ACCESS			 read-only
		STATUS					 current
		DESCRIPTION			 " -- "
		::=  { sfn5avgripEntry  99 }


	plsfn5Prb97RIPAvg		 OBJECT-TYPE
		SYNTAX					 Integer32( -2147483648 .. 2147483647 )
		MAX-ACCESS			 read-only
		STATUS					 current
		DESCRIPTION			 " -- "
		::=  { sfn5avgripEntry  100 }


	plsfn5Prb98RIPAvg		 OBJECT-TYPE
		SYNTAX					 Integer32( -2147483648 .. 2147483647 )
		MAX-ACCESS			 read-only
		STATUS					 current
		DESCRIPTION			 " -- "
		::=  { sfn5avgripEntry  101 }


	plsfn5Prb99RIPAvg		 OBJECT-TYPE
		SYNTAX					 Integer32( -2147483648 .. 2147483647 )
		MAX-ACCESS			 read-only
		STATUS					 current
		DESCRIPTION			 " -- "
		::=  { sfn5avgripEntry  102 }


	sfn6avgripTable		 OBJECT-TYPE
		SYNTAX					 SEQUENCE  OF	 Sfn6avgripEntry
		MAX-ACCESS			 not-accessible
		STATUS					 current
		DESCRIPTION			 " -- "
		::=  { plrelatedOriginCounter  10 }


	sfn6avgripEntry		 OBJECT-TYPE
		SYNTAX					 Sfn6avgripEntry
		MAX-ACCESS			 not-accessible
		STATUS					 current
		DESCRIPTION			 " -- "
		INDEX						{ sfn6avgripLcId }
		::=  { sfn6avgripTable  1 }


	Sfn6avgripEntry		 ::=  SEQUENCE {
		sfn6avgripLcId					Integer32,
		sfn6avgripRowStatus					RowStatus,
		plsfn6Prb00RIPAvg					Integer32,
		plsfn6Prb01RIPAvg					Integer32,
		plsfn6Prb02RIPAvg					Integer32,
		plsfn6Prb03RIPAvg					Integer32,
		plsfn6Prb04RIPAvg					Integer32,
		plsfn6Prb05RIPAvg					Integer32,
		plsfn6Prb06RIPAvg					Integer32,
		plsfn6Prb07RIPAvg					Integer32,
		plsfn6Prb08RIPAvg					Integer32,
		plsfn6Prb09RIPAvg					Integer32,
		plsfn6Prb10RIPAvg					Integer32,
		plsfn6Prb11RIPAvg					Integer32,
		plsfn6Prb12RIPAvg					Integer32,
		plsfn6Prb13RIPAvg					Integer32,
		plsfn6Prb14RIPAvg					Integer32,
		plsfn6Prb15RIPAvg					Integer32,
		plsfn6Prb16RIPAvg					Integer32,
		plsfn6Prb17RIPAvg					Integer32,
		plsfn6Prb18RIPAvg					Integer32,
		plsfn6Prb19RIPAvg					Integer32,
		plsfn6Prb20RIPAvg					Integer32,
		plsfn6Prb21RIPAvg					Integer32,
		plsfn6Prb22RIPAvg					Integer32,
		plsfn6Prb23RIPAvg					Integer32,
		plsfn6Prb24RIPAvg					Integer32,
		plsfn6Prb25RIPAvg					Integer32,
		plsfn6Prb26RIPAvg					Integer32,
		plsfn6Prb27RIPAvg					Integer32,
		plsfn6Prb28RIPAvg					Integer32,
		plsfn6Prb29RIPAvg					Integer32,
		plsfn6Prb30RIPAvg					Integer32,
		plsfn6Prb31RIPAvg					Integer32,
		plsfn6Prb32RIPAvg					Integer32,
		plsfn6Prb33RIPAvg					Integer32,
		plsfn6Prb34RIPAvg					Integer32,
		plsfn6Prb35RIPAvg					Integer32,
		plsfn6Prb36RIPAvg					Integer32,
		plsfn6Prb37RIPAvg					Integer32,
		plsfn6Prb38RIPAvg					Integer32,
		plsfn6Prb39RIPAvg					Integer32,
		plsfn6Prb40RIPAvg					Integer32,
		plsfn6Prb41RIPAvg					Integer32,
		plsfn6Prb42RIPAvg					Integer32,
		plsfn6Prb43RIPAvg					Integer32,
		plsfn6Prb44RIPAvg					Integer32,
		plsfn6Prb45RIPAvg					Integer32,
		plsfn6Prb46RIPAvg					Integer32,
		plsfn6Prb47RIPAvg					Integer32,
		plsfn6Prb48RIPAvg					Integer32,
		plsfn6Prb49RIPAvg					Integer32,
		plsfn6Prb50RIPAvg					Integer32,
		plsfn6Prb51RIPAvg					Integer32,
		plsfn6Prb52RIPAvg					Integer32,
		plsfn6Prb53RIPAvg					Integer32,
		plsfn6Prb54RIPAvg					Integer32,
		plsfn6Prb55RIPAvg					Integer32,
		plsfn6Prb56RIPAvg					Integer32,
		plsfn6Prb57RIPAvg					Integer32,
		plsfn6Prb58RIPAvg					Integer32,
		plsfn6Prb59RIPAvg					Integer32,
		plsfn6Prb60RIPAvg					Integer32,
		plsfn6Prb61RIPAvg					Integer32,
		plsfn6Prb62RIPAvg					Integer32,
		plsfn6Prb63RIPAvg					Integer32,
		plsfn6Prb64RIPAvg					Integer32,
		plsfn6Prb65RIPAvg					Integer32,
		plsfn6Prb66RIPAvg					Integer32,
		plsfn6Prb67RIPAvg					Integer32,
		plsfn6Prb68RIPAvg					Integer32,
		plsfn6Prb69RIPAvg					Integer32,
		plsfn6Prb70RIPAvg					Integer32,
		plsfn6Prb71RIPAvg					Integer32,
		plsfn6Prb72RIPAvg					Integer32,
		plsfn6Prb73RIPAvg					Integer32,
		plsfn6Prb74RIPAvg					Integer32,
		plsfn6Prb75RIPAvg					Integer32,
		plsfn6Prb76RIPAvg					Integer32,
		plsfn6Prb77RIPAvg					Integer32,
		plsfn6Prb78RIPAvg					Integer32,
		plsfn6Prb79RIPAvg					Integer32,
		plsfn6Prb80RIPAvg					Integer32,
		plsfn6Prb81RIPAvg					Integer32,
		plsfn6Prb82RIPAvg					Integer32,
		plsfn6Prb83RIPAvg					Integer32,
		plsfn6Prb84RIPAvg					Integer32,
		plsfn6Prb85RIPAvg					Integer32,
		plsfn6Prb86RIPAvg					Integer32,
		plsfn6Prb87RIPAvg					Integer32,
		plsfn6Prb88RIPAvg					Integer32,
		plsfn6Prb89RIPAvg					Integer32,
		plsfn6Prb90RIPAvg					Integer32,
		plsfn6Prb91RIPAvg					Integer32,
		plsfn6Prb92RIPAvg					Integer32,
		plsfn6Prb93RIPAvg					Integer32,
		plsfn6Prb94RIPAvg					Integer32,
		plsfn6Prb95RIPAvg					Integer32,
		plsfn6Prb96RIPAvg					Integer32,
		plsfn6Prb97RIPAvg					Integer32,
		plsfn6Prb98RIPAvg					Integer32,
		plsfn6Prb99RIPAvg					Integer32
		}


	sfn6avgripLcId		 OBJECT-TYPE
		SYNTAX					 Integer32( 0 .. 23 )
		MAX-ACCESS			 not-accessible
		STATUS					 current
		DESCRIPTION			 " -- "
		::=  { sfn6avgripEntry  1 }


	sfn6avgripRowStatus		 OBJECT-TYPE
		SYNTAX					 RowStatus
		MAX-ACCESS			 read-only
		STATUS					 current
		DESCRIPTION			 " -- "
		::=  { sfn6avgripEntry  2 }


	plsfn6Prb00RIPAvg		 OBJECT-TYPE
		SYNTAX					 Integer32( -2147483648 .. 2147483647 )
		MAX-ACCESS			 read-only
		STATUS					 current
		DESCRIPTION			 " -- "
		::=  { sfn6avgripEntry  3 }


	plsfn6Prb01RIPAvg		 OBJECT-TYPE
		SYNTAX					 Integer32( -2147483648 .. 2147483647 )
		MAX-ACCESS			 read-only
		STATUS					 current
		DESCRIPTION			 " -- "
		::=  { sfn6avgripEntry  4 }


	plsfn6Prb02RIPAvg		 OBJECT-TYPE
		SYNTAX					 Integer32( -2147483648 .. 2147483647 )
		MAX-ACCESS			 read-only
		STATUS					 current
		DESCRIPTION			 " -- "
		::=  { sfn6avgripEntry  5 }


	plsfn6Prb03RIPAvg		 OBJECT-TYPE
		SYNTAX					 Integer32( -2147483648 .. 2147483647 )
		MAX-ACCESS			 read-only
		STATUS					 current
		DESCRIPTION			 " -- "
		::=  { sfn6avgripEntry  6 }


	plsfn6Prb04RIPAvg		 OBJECT-TYPE
		SYNTAX					 Integer32( -2147483648 .. 2147483647 )
		MAX-ACCESS			 read-only
		STATUS					 current
		DESCRIPTION			 " -- "
		::=  { sfn6avgripEntry  7 }


	plsfn6Prb05RIPAvg		 OBJECT-TYPE
		SYNTAX					 Integer32( -2147483648 .. 2147483647 )
		MAX-ACCESS			 read-only
		STATUS					 current
		DESCRIPTION			 " -- "
		::=  { sfn6avgripEntry  8 }


	plsfn6Prb06RIPAvg		 OBJECT-TYPE
		SYNTAX					 Integer32( -2147483648 .. 2147483647 )
		MAX-ACCESS			 read-only
		STATUS					 current
		DESCRIPTION			 " -- "
		::=  { sfn6avgripEntry  9 }


	plsfn6Prb07RIPAvg		 OBJECT-TYPE
		SYNTAX					 Integer32( -2147483648 .. 2147483647 )
		MAX-ACCESS			 read-only
		STATUS					 current
		DESCRIPTION			 " -- "
		::=  { sfn6avgripEntry  10 }


	plsfn6Prb08RIPAvg		 OBJECT-TYPE
		SYNTAX					 Integer32( -2147483648 .. 2147483647 )
		MAX-ACCESS			 read-only
		STATUS					 current
		DESCRIPTION			 " -- "
		::=  { sfn6avgripEntry  11 }


	plsfn6Prb09RIPAvg		 OBJECT-TYPE
		SYNTAX					 Integer32( -2147483648 .. 2147483647 )
		MAX-ACCESS			 read-only
		STATUS					 current
		DESCRIPTION			 " -- "
		::=  { sfn6avgripEntry  12 }


	plsfn6Prb10RIPAvg		 OBJECT-TYPE
		SYNTAX					 Integer32( -2147483648 .. 2147483647 )
		MAX-ACCESS			 read-only
		STATUS					 current
		DESCRIPTION			 " -- "
		::=  { sfn6avgripEntry  13 }


	plsfn6Prb11RIPAvg		 OBJECT-TYPE
		SYNTAX					 Integer32( -2147483648 .. 2147483647 )
		MAX-ACCESS			 read-only
		STATUS					 current
		DESCRIPTION			 " -- "
		::=  { sfn6avgripEntry  14 }


	plsfn6Prb12RIPAvg		 OBJECT-TYPE
		SYNTAX					 Integer32( -2147483648 .. 2147483647 )
		MAX-ACCESS			 read-only
		STATUS					 current
		DESCRIPTION			 " -- "
		::=  { sfn6avgripEntry  15 }


	plsfn6Prb13RIPAvg		 OBJECT-TYPE
		SYNTAX					 Integer32( -2147483648 .. 2147483647 )
		MAX-ACCESS			 read-only
		STATUS					 current
		DESCRIPTION			 " -- "
		::=  { sfn6avgripEntry  16 }


	plsfn6Prb14RIPAvg		 OBJECT-TYPE
		SYNTAX					 Integer32( -2147483648 .. 2147483647 )
		MAX-ACCESS			 read-only
		STATUS					 current
		DESCRIPTION			 " -- "
		::=  { sfn6avgripEntry  17 }


	plsfn6Prb15RIPAvg		 OBJECT-TYPE
		SYNTAX					 Integer32( -2147483648 .. 2147483647 )
		MAX-ACCESS			 read-only
		STATUS					 current
		DESCRIPTION			 " -- "
		::=  { sfn6avgripEntry  18 }


	plsfn6Prb16RIPAvg		 OBJECT-TYPE
		SYNTAX					 Integer32( -2147483648 .. 2147483647 )
		MAX-ACCESS			 read-only
		STATUS					 current
		DESCRIPTION			 " -- "
		::=  { sfn6avgripEntry  19 }


	plsfn6Prb17RIPAvg		 OBJECT-TYPE
		SYNTAX					 Integer32( -2147483648 .. 2147483647 )
		MAX-ACCESS			 read-only
		STATUS					 current
		DESCRIPTION			 " -- "
		::=  { sfn6avgripEntry  20 }


	plsfn6Prb18RIPAvg		 OBJECT-TYPE
		SYNTAX					 Integer32( -2147483648 .. 2147483647 )
		MAX-ACCESS			 read-only
		STATUS					 current
		DESCRIPTION			 " -- "
		::=  { sfn6avgripEntry  21 }


	plsfn6Prb19RIPAvg		 OBJECT-TYPE
		SYNTAX					 Integer32( -2147483648 .. 2147483647 )
		MAX-ACCESS			 read-only
		STATUS					 current
		DESCRIPTION			 " -- "
		::=  { sfn6avgripEntry  22 }


	plsfn6Prb20RIPAvg		 OBJECT-TYPE
		SYNTAX					 Integer32( -2147483648 .. 2147483647 )
		MAX-ACCESS			 read-only
		STATUS					 current
		DESCRIPTION			 " -- "
		::=  { sfn6avgripEntry  23 }


	plsfn6Prb21RIPAvg		 OBJECT-TYPE
		SYNTAX					 Integer32( -2147483648 .. 2147483647 )
		MAX-ACCESS			 read-only
		STATUS					 current
		DESCRIPTION			 " -- "
		::=  { sfn6avgripEntry  24 }


	plsfn6Prb22RIPAvg		 OBJECT-TYPE
		SYNTAX					 Integer32( -2147483648 .. 2147483647 )
		MAX-ACCESS			 read-only
		STATUS					 current
		DESCRIPTION			 " -- "
		::=  { sfn6avgripEntry  25 }


	plsfn6Prb23RIPAvg		 OBJECT-TYPE
		SYNTAX					 Integer32( -2147483648 .. 2147483647 )
		MAX-ACCESS			 read-only
		STATUS					 current
		DESCRIPTION			 " -- "
		::=  { sfn6avgripEntry  26 }


	plsfn6Prb24RIPAvg		 OBJECT-TYPE
		SYNTAX					 Integer32( -2147483648 .. 2147483647 )
		MAX-ACCESS			 read-only
		STATUS					 current
		DESCRIPTION			 " -- "
		::=  { sfn6avgripEntry  27 }


	plsfn6Prb25RIPAvg		 OBJECT-TYPE
		SYNTAX					 Integer32( -2147483648 .. 2147483647 )
		MAX-ACCESS			 read-only
		STATUS					 current
		DESCRIPTION			 " -- "
		::=  { sfn6avgripEntry  28 }


	plsfn6Prb26RIPAvg		 OBJECT-TYPE
		SYNTAX					 Integer32( -2147483648 .. 2147483647 )
		MAX-ACCESS			 read-only
		STATUS					 current
		DESCRIPTION			 " -- "
		::=  { sfn6avgripEntry  29 }


	plsfn6Prb27RIPAvg		 OBJECT-TYPE
		SYNTAX					 Integer32( -2147483648 .. 2147483647 )
		MAX-ACCESS			 read-only
		STATUS					 current
		DESCRIPTION			 " -- "
		::=  { sfn6avgripEntry  30 }


	plsfn6Prb28RIPAvg		 OBJECT-TYPE
		SYNTAX					 Integer32( -2147483648 .. 2147483647 )
		MAX-ACCESS			 read-only
		STATUS					 current
		DESCRIPTION			 " -- "
		::=  { sfn6avgripEntry  31 }


	plsfn6Prb29RIPAvg		 OBJECT-TYPE
		SYNTAX					 Integer32( -2147483648 .. 2147483647 )
		MAX-ACCESS			 read-only
		STATUS					 current
		DESCRIPTION			 " -- "
		::=  { sfn6avgripEntry  32 }


	plsfn6Prb30RIPAvg		 OBJECT-TYPE
		SYNTAX					 Integer32( -2147483648 .. 2147483647 )
		MAX-ACCESS			 read-only
		STATUS					 current
		DESCRIPTION			 " -- "
		::=  { sfn6avgripEntry  33 }


	plsfn6Prb31RIPAvg		 OBJECT-TYPE
		SYNTAX					 Integer32( -2147483648 .. 2147483647 )
		MAX-ACCESS			 read-only
		STATUS					 current
		DESCRIPTION			 " -- "
		::=  { sfn6avgripEntry  34 }


	plsfn6Prb32RIPAvg		 OBJECT-TYPE
		SYNTAX					 Integer32( -2147483648 .. 2147483647 )
		MAX-ACCESS			 read-only
		STATUS					 current
		DESCRIPTION			 " -- "
		::=  { sfn6avgripEntry  35 }


	plsfn6Prb33RIPAvg		 OBJECT-TYPE
		SYNTAX					 Integer32( -2147483648 .. 2147483647 )
		MAX-ACCESS			 read-only
		STATUS					 current
		DESCRIPTION			 " -- "
		::=  { sfn6avgripEntry  36 }


	plsfn6Prb34RIPAvg		 OBJECT-TYPE
		SYNTAX					 Integer32( -2147483648 .. 2147483647 )
		MAX-ACCESS			 read-only
		STATUS					 current
		DESCRIPTION			 " -- "
		::=  { sfn6avgripEntry  37 }


	plsfn6Prb35RIPAvg		 OBJECT-TYPE
		SYNTAX					 Integer32( -2147483648 .. 2147483647 )
		MAX-ACCESS			 read-only
		STATUS					 current
		DESCRIPTION			 " -- "
		::=  { sfn6avgripEntry  38 }


	plsfn6Prb36RIPAvg		 OBJECT-TYPE
		SYNTAX					 Integer32( -2147483648 .. 2147483647 )
		MAX-ACCESS			 read-only
		STATUS					 current
		DESCRIPTION			 " -- "
		::=  { sfn6avgripEntry  39 }


	plsfn6Prb37RIPAvg		 OBJECT-TYPE
		SYNTAX					 Integer32( -2147483648 .. 2147483647 )
		MAX-ACCESS			 read-only
		STATUS					 current
		DESCRIPTION			 " -- "
		::=  { sfn6avgripEntry  40 }


	plsfn6Prb38RIPAvg		 OBJECT-TYPE
		SYNTAX					 Integer32( -2147483648 .. 2147483647 )
		MAX-ACCESS			 read-only
		STATUS					 current
		DESCRIPTION			 " -- "
		::=  { sfn6avgripEntry  41 }


	plsfn6Prb39RIPAvg		 OBJECT-TYPE
		SYNTAX					 Integer32( -2147483648 .. 2147483647 )
		MAX-ACCESS			 read-only
		STATUS					 current
		DESCRIPTION			 " -- "
		::=  { sfn6avgripEntry  42 }


	plsfn6Prb40RIPAvg		 OBJECT-TYPE
		SYNTAX					 Integer32( -2147483648 .. 2147483647 )
		MAX-ACCESS			 read-only
		STATUS					 current
		DESCRIPTION			 " -- "
		::=  { sfn6avgripEntry  43 }


	plsfn6Prb41RIPAvg		 OBJECT-TYPE
		SYNTAX					 Integer32( -2147483648 .. 2147483647 )
		MAX-ACCESS			 read-only
		STATUS					 current
		DESCRIPTION			 " -- "
		::=  { sfn6avgripEntry  44 }


	plsfn6Prb42RIPAvg		 OBJECT-TYPE
		SYNTAX					 Integer32( -2147483648 .. 2147483647 )
		MAX-ACCESS			 read-only
		STATUS					 current
		DESCRIPTION			 " -- "
		::=  { sfn6avgripEntry  45 }


	plsfn6Prb43RIPAvg		 OBJECT-TYPE
		SYNTAX					 Integer32( -2147483648 .. 2147483647 )
		MAX-ACCESS			 read-only
		STATUS					 current
		DESCRIPTION			 " -- "
		::=  { sfn6avgripEntry  46 }


	plsfn6Prb44RIPAvg		 OBJECT-TYPE
		SYNTAX					 Integer32( -2147483648 .. 2147483647 )
		MAX-ACCESS			 read-only
		STATUS					 current
		DESCRIPTION			 " -- "
		::=  { sfn6avgripEntry  47 }


	plsfn6Prb45RIPAvg		 OBJECT-TYPE
		SYNTAX					 Integer32( -2147483648 .. 2147483647 )
		MAX-ACCESS			 read-only
		STATUS					 current
		DESCRIPTION			 " -- "
		::=  { sfn6avgripEntry  48 }


	plsfn6Prb46RIPAvg		 OBJECT-TYPE
		SYNTAX					 Integer32( -2147483648 .. 2147483647 )
		MAX-ACCESS			 read-only
		STATUS					 current
		DESCRIPTION			 " -- "
		::=  { sfn6avgripEntry  49 }


	plsfn6Prb47RIPAvg		 OBJECT-TYPE
		SYNTAX					 Integer32( -2147483648 .. 2147483647 )
		MAX-ACCESS			 read-only
		STATUS					 current
		DESCRIPTION			 " -- "
		::=  { sfn6avgripEntry  50 }


	plsfn6Prb48RIPAvg		 OBJECT-TYPE
		SYNTAX					 Integer32( -2147483648 .. 2147483647 )
		MAX-ACCESS			 read-only
		STATUS					 current
		DESCRIPTION			 " -- "
		::=  { sfn6avgripEntry  51 }


	plsfn6Prb49RIPAvg		 OBJECT-TYPE
		SYNTAX					 Integer32( -2147483648 .. 2147483647 )
		MAX-ACCESS			 read-only
		STATUS					 current
		DESCRIPTION			 " -- "
		::=  { sfn6avgripEntry  52 }


	plsfn6Prb50RIPAvg		 OBJECT-TYPE
		SYNTAX					 Integer32( -2147483648 .. 2147483647 )
		MAX-ACCESS			 read-only
		STATUS					 current
		DESCRIPTION			 " -- "
		::=  { sfn6avgripEntry  53 }


	plsfn6Prb51RIPAvg		 OBJECT-TYPE
		SYNTAX					 Integer32( -2147483648 .. 2147483647 )
		MAX-ACCESS			 read-only
		STATUS					 current
		DESCRIPTION			 " -- "
		::=  { sfn6avgripEntry  54 }


	plsfn6Prb52RIPAvg		 OBJECT-TYPE
		SYNTAX					 Integer32( -2147483648 .. 2147483647 )
		MAX-ACCESS			 read-only
		STATUS					 current
		DESCRIPTION			 " -- "
		::=  { sfn6avgripEntry  55 }


	plsfn6Prb53RIPAvg		 OBJECT-TYPE
		SYNTAX					 Integer32( -2147483648 .. 2147483647 )
		MAX-ACCESS			 read-only
		STATUS					 current
		DESCRIPTION			 " -- "
		::=  { sfn6avgripEntry  56 }


	plsfn6Prb54RIPAvg		 OBJECT-TYPE
		SYNTAX					 Integer32( -2147483648 .. 2147483647 )
		MAX-ACCESS			 read-only
		STATUS					 current
		DESCRIPTION			 " -- "
		::=  { sfn6avgripEntry  57 }


	plsfn6Prb55RIPAvg		 OBJECT-TYPE
		SYNTAX					 Integer32( -2147483648 .. 2147483647 )
		MAX-ACCESS			 read-only
		STATUS					 current
		DESCRIPTION			 " -- "
		::=  { sfn6avgripEntry  58 }


	plsfn6Prb56RIPAvg		 OBJECT-TYPE
		SYNTAX					 Integer32( -2147483648 .. 2147483647 )
		MAX-ACCESS			 read-only
		STATUS					 current
		DESCRIPTION			 " -- "
		::=  { sfn6avgripEntry  59 }


	plsfn6Prb57RIPAvg		 OBJECT-TYPE
		SYNTAX					 Integer32( -2147483648 .. 2147483647 )
		MAX-ACCESS			 read-only
		STATUS					 current
		DESCRIPTION			 " -- "
		::=  { sfn6avgripEntry  60 }


	plsfn6Prb58RIPAvg		 OBJECT-TYPE
		SYNTAX					 Integer32( -2147483648 .. 2147483647 )
		MAX-ACCESS			 read-only
		STATUS					 current
		DESCRIPTION			 " -- "
		::=  { sfn6avgripEntry  61 }


	plsfn6Prb59RIPAvg		 OBJECT-TYPE
		SYNTAX					 Integer32( -2147483648 .. 2147483647 )
		MAX-ACCESS			 read-only
		STATUS					 current
		DESCRIPTION			 " -- "
		::=  { sfn6avgripEntry  62 }


	plsfn6Prb60RIPAvg		 OBJECT-TYPE
		SYNTAX					 Integer32( -2147483648 .. 2147483647 )
		MAX-ACCESS			 read-only
		STATUS					 current
		DESCRIPTION			 " -- "
		::=  { sfn6avgripEntry  63 }


	plsfn6Prb61RIPAvg		 OBJECT-TYPE
		SYNTAX					 Integer32( -2147483648 .. 2147483647 )
		MAX-ACCESS			 read-only
		STATUS					 current
		DESCRIPTION			 " -- "
		::=  { sfn6avgripEntry  64 }


	plsfn6Prb62RIPAvg		 OBJECT-TYPE
		SYNTAX					 Integer32( -2147483648 .. 2147483647 )
		MAX-ACCESS			 read-only
		STATUS					 current
		DESCRIPTION			 " -- "
		::=  { sfn6avgripEntry  65 }


	plsfn6Prb63RIPAvg		 OBJECT-TYPE
		SYNTAX					 Integer32( -2147483648 .. 2147483647 )
		MAX-ACCESS			 read-only
		STATUS					 current
		DESCRIPTION			 " -- "
		::=  { sfn6avgripEntry  66 }


	plsfn6Prb64RIPAvg		 OBJECT-TYPE
		SYNTAX					 Integer32( -2147483648 .. 2147483647 )
		MAX-ACCESS			 read-only
		STATUS					 current
		DESCRIPTION			 " -- "
		::=  { sfn6avgripEntry  67 }


	plsfn6Prb65RIPAvg		 OBJECT-TYPE
		SYNTAX					 Integer32( -2147483648 .. 2147483647 )
		MAX-ACCESS			 read-only
		STATUS					 current
		DESCRIPTION			 " -- "
		::=  { sfn6avgripEntry  68 }


	plsfn6Prb66RIPAvg		 OBJECT-TYPE
		SYNTAX					 Integer32( -2147483648 .. 2147483647 )
		MAX-ACCESS			 read-only
		STATUS					 current
		DESCRIPTION			 " -- "
		::=  { sfn6avgripEntry  69 }


	plsfn6Prb67RIPAvg		 OBJECT-TYPE
		SYNTAX					 Integer32( -2147483648 .. 2147483647 )
		MAX-ACCESS			 read-only
		STATUS					 current
		DESCRIPTION			 " -- "
		::=  { sfn6avgripEntry  70 }


	plsfn6Prb68RIPAvg		 OBJECT-TYPE
		SYNTAX					 Integer32( -2147483648 .. 2147483647 )
		MAX-ACCESS			 read-only
		STATUS					 current
		DESCRIPTION			 " -- "
		::=  { sfn6avgripEntry  71 }


	plsfn6Prb69RIPAvg		 OBJECT-TYPE
		SYNTAX					 Integer32( -2147483648 .. 2147483647 )
		MAX-ACCESS			 read-only
		STATUS					 current
		DESCRIPTION			 " -- "
		::=  { sfn6avgripEntry  72 }


	plsfn6Prb70RIPAvg		 OBJECT-TYPE
		SYNTAX					 Integer32( -2147483648 .. 2147483647 )
		MAX-ACCESS			 read-only
		STATUS					 current
		DESCRIPTION			 " -- "
		::=  { sfn6avgripEntry  73 }


	plsfn6Prb71RIPAvg		 OBJECT-TYPE
		SYNTAX					 Integer32( -2147483648 .. 2147483647 )
		MAX-ACCESS			 read-only
		STATUS					 current
		DESCRIPTION			 " -- "
		::=  { sfn6avgripEntry  74 }


	plsfn6Prb72RIPAvg		 OBJECT-TYPE
		SYNTAX					 Integer32( -2147483648 .. 2147483647 )
		MAX-ACCESS			 read-only
		STATUS					 current
		DESCRIPTION			 " -- "
		::=  { sfn6avgripEntry  75 }


	plsfn6Prb73RIPAvg		 OBJECT-TYPE
		SYNTAX					 Integer32( -2147483648 .. 2147483647 )
		MAX-ACCESS			 read-only
		STATUS					 current
		DESCRIPTION			 " -- "
		::=  { sfn6avgripEntry  76 }


	plsfn6Prb74RIPAvg		 OBJECT-TYPE
		SYNTAX					 Integer32( -2147483648 .. 2147483647 )
		MAX-ACCESS			 read-only
		STATUS					 current
		DESCRIPTION			 " -- "
		::=  { sfn6avgripEntry  77 }


	plsfn6Prb75RIPAvg		 OBJECT-TYPE
		SYNTAX					 Integer32( -2147483648 .. 2147483647 )
		MAX-ACCESS			 read-only
		STATUS					 current
		DESCRIPTION			 " -- "
		::=  { sfn6avgripEntry  78 }


	plsfn6Prb76RIPAvg		 OBJECT-TYPE
		SYNTAX					 Integer32( -2147483648 .. 2147483647 )
		MAX-ACCESS			 read-only
		STATUS					 current
		DESCRIPTION			 " -- "
		::=  { sfn6avgripEntry  79 }


	plsfn6Prb77RIPAvg		 OBJECT-TYPE
		SYNTAX					 Integer32( -2147483648 .. 2147483647 )
		MAX-ACCESS			 read-only
		STATUS					 current
		DESCRIPTION			 " -- "
		::=  { sfn6avgripEntry  80 }


	plsfn6Prb78RIPAvg		 OBJECT-TYPE
		SYNTAX					 Integer32( -2147483648 .. 2147483647 )
		MAX-ACCESS			 read-only
		STATUS					 current
		DESCRIPTION			 " -- "
		::=  { sfn6avgripEntry  81 }


	plsfn6Prb79RIPAvg		 OBJECT-TYPE
		SYNTAX					 Integer32( -2147483648 .. 2147483647 )
		MAX-ACCESS			 read-only
		STATUS					 current
		DESCRIPTION			 " -- "
		::=  { sfn6avgripEntry  82 }


	plsfn6Prb80RIPAvg		 OBJECT-TYPE
		SYNTAX					 Integer32( -2147483648 .. 2147483647 )
		MAX-ACCESS			 read-only
		STATUS					 current
		DESCRIPTION			 " -- "
		::=  { sfn6avgripEntry  83 }


	plsfn6Prb81RIPAvg		 OBJECT-TYPE
		SYNTAX					 Integer32( -2147483648 .. 2147483647 )
		MAX-ACCESS			 read-only
		STATUS					 current
		DESCRIPTION			 " -- "
		::=  { sfn6avgripEntry  84 }


	plsfn6Prb82RIPAvg		 OBJECT-TYPE
		SYNTAX					 Integer32( -2147483648 .. 2147483647 )
		MAX-ACCESS			 read-only
		STATUS					 current
		DESCRIPTION			 " -- "
		::=  { sfn6avgripEntry  85 }


	plsfn6Prb83RIPAvg		 OBJECT-TYPE
		SYNTAX					 Integer32( -2147483648 .. 2147483647 )
		MAX-ACCESS			 read-only
		STATUS					 current
		DESCRIPTION			 " -- "
		::=  { sfn6avgripEntry  86 }


	plsfn6Prb84RIPAvg		 OBJECT-TYPE
		SYNTAX					 Integer32( -2147483648 .. 2147483647 )
		MAX-ACCESS			 read-only
		STATUS					 current
		DESCRIPTION			 " -- "
		::=  { sfn6avgripEntry  87 }


	plsfn6Prb85RIPAvg		 OBJECT-TYPE
		SYNTAX					 Integer32( -2147483648 .. 2147483647 )
		MAX-ACCESS			 read-only
		STATUS					 current
		DESCRIPTION			 " -- "
		::=  { sfn6avgripEntry  88 }


	plsfn6Prb86RIPAvg		 OBJECT-TYPE
		SYNTAX					 Integer32( -2147483648 .. 2147483647 )
		MAX-ACCESS			 read-only
		STATUS					 current
		DESCRIPTION			 " -- "
		::=  { sfn6avgripEntry  89 }


	plsfn6Prb87RIPAvg		 OBJECT-TYPE
		SYNTAX					 Integer32( -2147483648 .. 2147483647 )
		MAX-ACCESS			 read-only
		STATUS					 current
		DESCRIPTION			 " -- "
		::=  { sfn6avgripEntry  90 }


	plsfn6Prb88RIPAvg		 OBJECT-TYPE
		SYNTAX					 Integer32( -2147483648 .. 2147483647 )
		MAX-ACCESS			 read-only
		STATUS					 current
		DESCRIPTION			 " -- "
		::=  { sfn6avgripEntry  91 }


	plsfn6Prb89RIPAvg		 OBJECT-TYPE
		SYNTAX					 Integer32( -2147483648 .. 2147483647 )
		MAX-ACCESS			 read-only
		STATUS					 current
		DESCRIPTION			 " -- "
		::=  { sfn6avgripEntry  92 }


	plsfn6Prb90RIPAvg		 OBJECT-TYPE
		SYNTAX					 Integer32( -2147483648 .. 2147483647 )
		MAX-ACCESS			 read-only
		STATUS					 current
		DESCRIPTION			 " -- "
		::=  { sfn6avgripEntry  93 }


	plsfn6Prb91RIPAvg		 OBJECT-TYPE
		SYNTAX					 Integer32( -2147483648 .. 2147483647 )
		MAX-ACCESS			 read-only
		STATUS					 current
		DESCRIPTION			 " -- "
		::=  { sfn6avgripEntry  94 }


	plsfn6Prb92RIPAvg		 OBJECT-TYPE
		SYNTAX					 Integer32( -2147483648 .. 2147483647 )
		MAX-ACCESS			 read-only
		STATUS					 current
		DESCRIPTION			 " -- "
		::=  { sfn6avgripEntry  95 }


	plsfn6Prb93RIPAvg		 OBJECT-TYPE
		SYNTAX					 Integer32( -2147483648 .. 2147483647 )
		MAX-ACCESS			 read-only
		STATUS					 current
		DESCRIPTION			 " -- "
		::=  { sfn6avgripEntry  96 }


	plsfn6Prb94RIPAvg		 OBJECT-TYPE
		SYNTAX					 Integer32( -2147483648 .. 2147483647 )
		MAX-ACCESS			 read-only
		STATUS					 current
		DESCRIPTION			 " -- "
		::=  { sfn6avgripEntry  97 }


	plsfn6Prb95RIPAvg		 OBJECT-TYPE
		SYNTAX					 Integer32( -2147483648 .. 2147483647 )
		MAX-ACCESS			 read-only
		STATUS					 current
		DESCRIPTION			 " -- "
		::=  { sfn6avgripEntry  98 }


	plsfn6Prb96RIPAvg		 OBJECT-TYPE
		SYNTAX					 Integer32( -2147483648 .. 2147483647 )
		MAX-ACCESS			 read-only
		STATUS					 current
		DESCRIPTION			 " -- "
		::=  { sfn6avgripEntry  99 }


	plsfn6Prb97RIPAvg		 OBJECT-TYPE
		SYNTAX					 Integer32( -2147483648 .. 2147483647 )
		MAX-ACCESS			 read-only
		STATUS					 current
		DESCRIPTION			 " -- "
		::=  { sfn6avgripEntry  100 }


	plsfn6Prb98RIPAvg		 OBJECT-TYPE
		SYNTAX					 Integer32( -2147483648 .. 2147483647 )
		MAX-ACCESS			 read-only
		STATUS					 current
		DESCRIPTION			 " -- "
		::=  { sfn6avgripEntry  101 }


	plsfn6Prb99RIPAvg		 OBJECT-TYPE
		SYNTAX					 Integer32( -2147483648 .. 2147483647 )
		MAX-ACCESS			 read-only
		STATUS					 current
		DESCRIPTION			 " -- "
		::=  { sfn6avgripEntry  102 }


	sfn9avgripTable		 OBJECT-TYPE
		SYNTAX					 SEQUENCE  OF	 Sfn9avgripEntry
		MAX-ACCESS			 not-accessible
		STATUS					 current
		DESCRIPTION			 " -- "
		::=  { plrelatedOriginCounter  11 }


	sfn9avgripEntry		 OBJECT-TYPE
		SYNTAX					 Sfn9avgripEntry
		MAX-ACCESS			 not-accessible
		STATUS					 current
		DESCRIPTION			 " -- "
		INDEX						{ sfn9avgripLcId }
		::=  { sfn9avgripTable  1 }


	Sfn9avgripEntry		 ::=  SEQUENCE {
		sfn9avgripLcId					Integer32,
		sfn9avgripRowStatus					RowStatus,
		plsfn9Prb00RIPAvg					Integer32,
		plsfn9Prb01RIPAvg					Integer32,
		plsfn9Prb02RIPAvg					Integer32,
		plsfn9Prb03RIPAvg					Integer32,
		plsfn9Prb04RIPAvg					Integer32,
		plsfn9Prb05RIPAvg					Integer32,
		plsfn9Prb06RIPAvg					Integer32,
		plsfn9Prb07RIPAvg					Integer32,
		plsfn9Prb08RIPAvg					Integer32,
		plsfn9Prb09RIPAvg					Integer32,
		plsfn9Prb10RIPAvg					Integer32,
		plsfn9Prb11RIPAvg					Integer32,
		plsfn9Prb12RIPAvg					Integer32,
		plsfn9Prb13RIPAvg					Integer32,
		plsfn9Prb14RIPAvg					Integer32,
		plsfn9Prb15RIPAvg					Integer32,
		plsfn9Prb16RIPAvg					Integer32,
		plsfn9Prb17RIPAvg					Integer32,
		plsfn9Prb18RIPAvg					Integer32,
		plsfn9Prb19RIPAvg					Integer32,
		plsfn9Prb20RIPAvg					Integer32,
		plsfn9Prb21RIPAvg					Integer32,
		plsfn9Prb22RIPAvg					Integer32,
		plsfn9Prb23RIPAvg					Integer32,
		plsfn9Prb24RIPAvg					Integer32,
		plsfn9Prb25RIPAvg					Integer32,
		plsfn9Prb26RIPAvg					Integer32,
		plsfn9Prb27RIPAvg					Integer32,
		plsfn9Prb28RIPAvg					Integer32,
		plsfn9Prb29RIPAvg					Integer32,
		plsfn9Prb30RIPAvg					Integer32,
		plsfn9Prb31RIPAvg					Integer32,
		plsfn9Prb32RIPAvg					Integer32,
		plsfn9Prb33RIPAvg					Integer32,
		plsfn9Prb34RIPAvg					Integer32,
		plsfn9Prb35RIPAvg					Integer32,
		plsfn9Prb36RIPAvg					Integer32,
		plsfn9Prb37RIPAvg					Integer32,
		plsfn9Prb38RIPAvg					Integer32,
		plsfn9Prb39RIPAvg					Integer32,
		plsfn9Prb40RIPAvg					Integer32,
		plsfn9Prb41RIPAvg					Integer32,
		plsfn9Prb42RIPAvg					Integer32,
		plsfn9Prb43RIPAvg					Integer32,
		plsfn9Prb44RIPAvg					Integer32,
		plsfn9Prb45RIPAvg					Integer32,
		plsfn9Prb46RIPAvg					Integer32,
		plsfn9Prb47RIPAvg					Integer32,
		plsfn9Prb48RIPAvg					Integer32,
		plsfn9Prb49RIPAvg					Integer32,
		plsfn9Prb50RIPAvg					Integer32,
		plsfn9Prb51RIPAvg					Integer32,
		plsfn9Prb52RIPAvg					Integer32,
		plsfn9Prb53RIPAvg					Integer32,
		plsfn9Prb54RIPAvg					Integer32,
		plsfn9Prb55RIPAvg					Integer32,
		plsfn9Prb56RIPAvg					Integer32,
		plsfn9Prb57RIPAvg					Integer32,
		plsfn9Prb58RIPAvg					Integer32,
		plsfn9Prb59RIPAvg					Integer32,
		plsfn9Prb60RIPAvg					Integer32,
		plsfn9Prb61RIPAvg					Integer32,
		plsfn9Prb62RIPAvg					Integer32,
		plsfn9Prb63RIPAvg					Integer32,
		plsfn9Prb64RIPAvg					Integer32,
		plsfn9Prb65RIPAvg					Integer32,
		plsfn9Prb66RIPAvg					Integer32,
		plsfn9Prb67RIPAvg					Integer32,
		plsfn9Prb68RIPAvg					Integer32,
		plsfn9Prb69RIPAvg					Integer32,
		plsfn9Prb70RIPAvg					Integer32,
		plsfn9Prb71RIPAvg					Integer32,
		plsfn9Prb72RIPAvg					Integer32,
		plsfn9Prb73RIPAvg					Integer32,
		plsfn9Prb74RIPAvg					Integer32,
		plsfn9Prb75RIPAvg					Integer32,
		plsfn9Prb76RIPAvg					Integer32,
		plsfn9Prb77RIPAvg					Integer32,
		plsfn9Prb78RIPAvg					Integer32,
		plsfn9Prb79RIPAvg					Integer32,
		plsfn9Prb80RIPAvg					Integer32,
		plsfn9Prb81RIPAvg					Integer32,
		plsfn9Prb82RIPAvg					Integer32,
		plsfn9Prb83RIPAvg					Integer32,
		plsfn9Prb84RIPAvg					Integer32,
		plsfn9Prb85RIPAvg					Integer32,
		plsfn9Prb86RIPAvg					Integer32,
		plsfn9Prb87RIPAvg					Integer32,
		plsfn9Prb88RIPAvg					Integer32,
		plsfn9Prb89RIPAvg					Integer32,
		plsfn9Prb90RIPAvg					Integer32,
		plsfn9Prb91RIPAvg					Integer32,
		plsfn9Prb92RIPAvg					Integer32,
		plsfn9Prb93RIPAvg					Integer32,
		plsfn9Prb94RIPAvg					Integer32,
		plsfn9Prb95RIPAvg					Integer32,
		plsfn9Prb96RIPAvg					Integer32,
		plsfn9Prb97RIPAvg					Integer32,
		plsfn9Prb98RIPAvg					Integer32,
		plsfn9Prb99RIPAvg					Integer32
		}


	sfn9avgripLcId		 OBJECT-TYPE
		SYNTAX					 Integer32( 0 .. 23 )
		MAX-ACCESS			 not-accessible
		STATUS					 current
		DESCRIPTION			 " -- "
		::=  { sfn9avgripEntry  1 }


	sfn9avgripRowStatus		 OBJECT-TYPE
		SYNTAX					 RowStatus
		MAX-ACCESS			 read-only
		STATUS					 current
		DESCRIPTION			 " -- "
		::=  { sfn9avgripEntry  2 }


	plsfn9Prb00RIPAvg		 OBJECT-TYPE
		SYNTAX					 Integer32( -2147483648 .. 2147483647 )
		MAX-ACCESS			 read-only
		STATUS					 current
		DESCRIPTION			 " -- "
		::=  { sfn9avgripEntry  3 }


	plsfn9Prb01RIPAvg		 OBJECT-TYPE
		SYNTAX					 Integer32( -2147483648 .. 2147483647 )
		MAX-ACCESS			 read-only
		STATUS					 current
		DESCRIPTION			 " -- "
		::=  { sfn9avgripEntry  4 }


	plsfn9Prb02RIPAvg		 OBJECT-TYPE
		SYNTAX					 Integer32( -2147483648 .. 2147483647 )
		MAX-ACCESS			 read-only
		STATUS					 current
		DESCRIPTION			 " -- "
		::=  { sfn9avgripEntry  5 }


	plsfn9Prb03RIPAvg		 OBJECT-TYPE
		SYNTAX					 Integer32( -2147483648 .. 2147483647 )
		MAX-ACCESS			 read-only
		STATUS					 current
		DESCRIPTION			 " -- "
		::=  { sfn9avgripEntry  6 }


	plsfn9Prb04RIPAvg		 OBJECT-TYPE
		SYNTAX					 Integer32( -2147483648 .. 2147483647 )
		MAX-ACCESS			 read-only
		STATUS					 current
		DESCRIPTION			 " -- "
		::=  { sfn9avgripEntry  7 }


	plsfn9Prb05RIPAvg		 OBJECT-TYPE
		SYNTAX					 Integer32( -2147483648 .. 2147483647 )
		MAX-ACCESS			 read-only
		STATUS					 current
		DESCRIPTION			 " -- "
		::=  { sfn9avgripEntry  8 }


	plsfn9Prb06RIPAvg		 OBJECT-TYPE
		SYNTAX					 Integer32( -2147483648 .. 2147483647 )
		MAX-ACCESS			 read-only
		STATUS					 current
		DESCRIPTION			 " -- "
		::=  { sfn9avgripEntry  9 }


	plsfn9Prb07RIPAvg		 OBJECT-TYPE
		SYNTAX					 Integer32( -2147483648 .. 2147483647 )
		MAX-ACCESS			 read-only
		STATUS					 current
		DESCRIPTION			 " -- "
		::=  { sfn9avgripEntry  10 }


	plsfn9Prb08RIPAvg		 OBJECT-TYPE
		SYNTAX					 Integer32( -2147483648 .. 2147483647 )
		MAX-ACCESS			 read-only
		STATUS					 current
		DESCRIPTION			 " -- "
		::=  { sfn9avgripEntry  11 }


	plsfn9Prb09RIPAvg		 OBJECT-TYPE
		SYNTAX					 Integer32( -2147483648 .. 2147483647 )
		MAX-ACCESS			 read-only
		STATUS					 current
		DESCRIPTION			 " -- "
		::=  { sfn9avgripEntry  12 }


	plsfn9Prb10RIPAvg		 OBJECT-TYPE
		SYNTAX					 Integer32( -2147483648 .. 2147483647 )
		MAX-ACCESS			 read-only
		STATUS					 current
		DESCRIPTION			 " -- "
		::=  { sfn9avgripEntry  13 }


	plsfn9Prb11RIPAvg		 OBJECT-TYPE
		SYNTAX					 Integer32( -2147483648 .. 2147483647 )
		MAX-ACCESS			 read-only
		STATUS					 current
		DESCRIPTION			 " -- "
		::=  { sfn9avgripEntry  14 }


	plsfn9Prb12RIPAvg		 OBJECT-TYPE
		SYNTAX					 Integer32( -2147483648 .. 2147483647 )
		MAX-ACCESS			 read-only
		STATUS					 current
		DESCRIPTION			 " -- "
		::=  { sfn9avgripEntry  15 }


	plsfn9Prb13RIPAvg		 OBJECT-TYPE
		SYNTAX					 Integer32( -2147483648 .. 2147483647 )
		MAX-ACCESS			 read-only
		STATUS					 current
		DESCRIPTION			 " -- "
		::=  { sfn9avgripEntry  16 }


	plsfn9Prb14RIPAvg		 OBJECT-TYPE
		SYNTAX					 Integer32( -2147483648 .. 2147483647 )
		MAX-ACCESS			 read-only
		STATUS					 current
		DESCRIPTION			 " -- "
		::=  { sfn9avgripEntry  17 }


	plsfn9Prb15RIPAvg		 OBJECT-TYPE
		SYNTAX					 Integer32( -2147483648 .. 2147483647 )
		MAX-ACCESS			 read-only
		STATUS					 current
		DESCRIPTION			 " -- "
		::=  { sfn9avgripEntry  18 }


	plsfn9Prb16RIPAvg		 OBJECT-TYPE
		SYNTAX					 Integer32( -2147483648 .. 2147483647 )
		MAX-ACCESS			 read-only
		STATUS					 current
		DESCRIPTION			 " -- "
		::=  { sfn9avgripEntry  19 }


	plsfn9Prb17RIPAvg		 OBJECT-TYPE
		SYNTAX					 Integer32( -2147483648 .. 2147483647 )
		MAX-ACCESS			 read-only
		STATUS					 current
		DESCRIPTION			 " -- "
		::=  { sfn9avgripEntry  20 }


	plsfn9Prb18RIPAvg		 OBJECT-TYPE
		SYNTAX					 Integer32( -2147483648 .. 2147483647 )
		MAX-ACCESS			 read-only
		STATUS					 current
		DESCRIPTION			 " -- "
		::=  { sfn9avgripEntry  21 }


	plsfn9Prb19RIPAvg		 OBJECT-TYPE
		SYNTAX					 Integer32( -2147483648 .. 2147483647 )
		MAX-ACCESS			 read-only
		STATUS					 current
		DESCRIPTION			 " -- "
		::=  { sfn9avgripEntry  22 }


	plsfn9Prb20RIPAvg		 OBJECT-TYPE
		SYNTAX					 Integer32( -2147483648 .. 2147483647 )
		MAX-ACCESS			 read-only
		STATUS					 current
		DESCRIPTION			 " -- "
		::=  { sfn9avgripEntry  23 }


	plsfn9Prb21RIPAvg		 OBJECT-TYPE
		SYNTAX					 Integer32( -2147483648 .. 2147483647 )
		MAX-ACCESS			 read-only
		STATUS					 current
		DESCRIPTION			 " -- "
		::=  { sfn9avgripEntry  24 }


	plsfn9Prb22RIPAvg		 OBJECT-TYPE
		SYNTAX					 Integer32( -2147483648 .. 2147483647 )
		MAX-ACCESS			 read-only
		STATUS					 current
		DESCRIPTION			 " -- "
		::=  { sfn9avgripEntry  25 }


	plsfn9Prb23RIPAvg		 OBJECT-TYPE
		SYNTAX					 Integer32( -2147483648 .. 2147483647 )
		MAX-ACCESS			 read-only
		STATUS					 current
		DESCRIPTION			 " -- "
		::=  { sfn9avgripEntry  26 }


	plsfn9Prb24RIPAvg		 OBJECT-TYPE
		SYNTAX					 Integer32( -2147483648 .. 2147483647 )
		MAX-ACCESS			 read-only
		STATUS					 current
		DESCRIPTION			 " -- "
		::=  { sfn9avgripEntry  27 }


	plsfn9Prb25RIPAvg		 OBJECT-TYPE
		SYNTAX					 Integer32( -2147483648 .. 2147483647 )
		MAX-ACCESS			 read-only
		STATUS					 current
		DESCRIPTION			 " -- "
		::=  { sfn9avgripEntry  28 }


	plsfn9Prb26RIPAvg		 OBJECT-TYPE
		SYNTAX					 Integer32( -2147483648 .. 2147483647 )
		MAX-ACCESS			 read-only
		STATUS					 current
		DESCRIPTION			 " -- "
		::=  { sfn9avgripEntry  29 }


	plsfn9Prb27RIPAvg		 OBJECT-TYPE
		SYNTAX					 Integer32( -2147483648 .. 2147483647 )
		MAX-ACCESS			 read-only
		STATUS					 current
		DESCRIPTION			 " -- "
		::=  { sfn9avgripEntry  30 }


	plsfn9Prb28RIPAvg		 OBJECT-TYPE
		SYNTAX					 Integer32( -2147483648 .. 2147483647 )
		MAX-ACCESS			 read-only
		STATUS					 current
		DESCRIPTION			 " -- "
		::=  { sfn9avgripEntry  31 }


	plsfn9Prb29RIPAvg		 OBJECT-TYPE
		SYNTAX					 Integer32( -2147483648 .. 2147483647 )
		MAX-ACCESS			 read-only
		STATUS					 current
		DESCRIPTION			 " -- "
		::=  { sfn9avgripEntry  32 }


	plsfn9Prb30RIPAvg		 OBJECT-TYPE
		SYNTAX					 Integer32( -2147483648 .. 2147483647 )
		MAX-ACCESS			 read-only
		STATUS					 current
		DESCRIPTION			 " -- "
		::=  { sfn9avgripEntry  33 }


	plsfn9Prb31RIPAvg		 OBJECT-TYPE
		SYNTAX					 Integer32( -2147483648 .. 2147483647 )
		MAX-ACCESS			 read-only
		STATUS					 current
		DESCRIPTION			 " -- "
		::=  { sfn9avgripEntry  34 }


	plsfn9Prb32RIPAvg		 OBJECT-TYPE
		SYNTAX					 Integer32( -2147483648 .. 2147483647 )
		MAX-ACCESS			 read-only
		STATUS					 current
		DESCRIPTION			 " -- "
		::=  { sfn9avgripEntry  35 }


	plsfn9Prb33RIPAvg		 OBJECT-TYPE
		SYNTAX					 Integer32( -2147483648 .. 2147483647 )
		MAX-ACCESS			 read-only
		STATUS					 current
		DESCRIPTION			 " -- "
		::=  { sfn9avgripEntry  36 }


	plsfn9Prb34RIPAvg		 OBJECT-TYPE
		SYNTAX					 Integer32( -2147483648 .. 2147483647 )
		MAX-ACCESS			 read-only
		STATUS					 current
		DESCRIPTION			 " -- "
		::=  { sfn9avgripEntry  37 }


	plsfn9Prb35RIPAvg		 OBJECT-TYPE
		SYNTAX					 Integer32( -2147483648 .. 2147483647 )
		MAX-ACCESS			 read-only
		STATUS					 current
		DESCRIPTION			 " -- "
		::=  { sfn9avgripEntry  38 }


	plsfn9Prb36RIPAvg		 OBJECT-TYPE
		SYNTAX					 Integer32( -2147483648 .. 2147483647 )
		MAX-ACCESS			 read-only
		STATUS					 current
		DESCRIPTION			 " -- "
		::=  { sfn9avgripEntry  39 }


	plsfn9Prb37RIPAvg		 OBJECT-TYPE
		SYNTAX					 Integer32( -2147483648 .. 2147483647 )
		MAX-ACCESS			 read-only
		STATUS					 current
		DESCRIPTION			 " -- "
		::=  { sfn9avgripEntry  40 }


	plsfn9Prb38RIPAvg		 OBJECT-TYPE
		SYNTAX					 Integer32( -2147483648 .. 2147483647 )
		MAX-ACCESS			 read-only
		STATUS					 current
		DESCRIPTION			 " -- "
		::=  { sfn9avgripEntry  41 }


	plsfn9Prb39RIPAvg		 OBJECT-TYPE
		SYNTAX					 Integer32( -2147483648 .. 2147483647 )
		MAX-ACCESS			 read-only
		STATUS					 current
		DESCRIPTION			 " -- "
		::=  { sfn9avgripEntry  42 }


	plsfn9Prb40RIPAvg		 OBJECT-TYPE
		SYNTAX					 Integer32( -2147483648 .. 2147483647 )
		MAX-ACCESS			 read-only
		STATUS					 current
		DESCRIPTION			 " -- "
		::=  { sfn9avgripEntry  43 }


	plsfn9Prb41RIPAvg		 OBJECT-TYPE
		SYNTAX					 Integer32( -2147483648 .. 2147483647 )
		MAX-ACCESS			 read-only
		STATUS					 current
		DESCRIPTION			 " -- "
		::=  { sfn9avgripEntry  44 }


	plsfn9Prb42RIPAvg		 OBJECT-TYPE
		SYNTAX					 Integer32( -2147483648 .. 2147483647 )
		MAX-ACCESS			 read-only
		STATUS					 current
		DESCRIPTION			 " -- "
		::=  { sfn9avgripEntry  45 }


	plsfn9Prb43RIPAvg		 OBJECT-TYPE
		SYNTAX					 Integer32( -2147483648 .. 2147483647 )
		MAX-ACCESS			 read-only
		STATUS					 current
		DESCRIPTION			 " -- "
		::=  { sfn9avgripEntry  46 }


	plsfn9Prb44RIPAvg		 OBJECT-TYPE
		SYNTAX					 Integer32( -2147483648 .. 2147483647 )
		MAX-ACCESS			 read-only
		STATUS					 current
		DESCRIPTION			 " -- "
		::=  { sfn9avgripEntry  47 }


	plsfn9Prb45RIPAvg		 OBJECT-TYPE
		SYNTAX					 Integer32( -2147483648 .. 2147483647 )
		MAX-ACCESS			 read-only
		STATUS					 current
		DESCRIPTION			 " -- "
		::=  { sfn9avgripEntry  48 }


	plsfn9Prb46RIPAvg		 OBJECT-TYPE
		SYNTAX					 Integer32( -2147483648 .. 2147483647 )
		MAX-ACCESS			 read-only
		STATUS					 current
		DESCRIPTION			 " -- "
		::=  { sfn9avgripEntry  49 }


	plsfn9Prb47RIPAvg		 OBJECT-TYPE
		SYNTAX					 Integer32( -2147483648 .. 2147483647 )
		MAX-ACCESS			 read-only
		STATUS					 current
		DESCRIPTION			 " -- "
		::=  { sfn9avgripEntry  50 }


	plsfn9Prb48RIPAvg		 OBJECT-TYPE
		SYNTAX					 Integer32( -2147483648 .. 2147483647 )
		MAX-ACCESS			 read-only
		STATUS					 current
		DESCRIPTION			 " -- "
		::=  { sfn9avgripEntry  51 }


	plsfn9Prb49RIPAvg		 OBJECT-TYPE
		SYNTAX					 Integer32( -2147483648 .. 2147483647 )
		MAX-ACCESS			 read-only
		STATUS					 current
		DESCRIPTION			 " -- "
		::=  { sfn9avgripEntry  52 }


	plsfn9Prb50RIPAvg		 OBJECT-TYPE
		SYNTAX					 Integer32( -2147483648 .. 2147483647 )
		MAX-ACCESS			 read-only
		STATUS					 current
		DESCRIPTION			 " -- "
		::=  { sfn9avgripEntry  53 }


	plsfn9Prb51RIPAvg		 OBJECT-TYPE
		SYNTAX					 Integer32( -2147483648 .. 2147483647 )
		MAX-ACCESS			 read-only
		STATUS					 current
		DESCRIPTION			 " -- "
		::=  { sfn9avgripEntry  54 }


	plsfn9Prb52RIPAvg		 OBJECT-TYPE
		SYNTAX					 Integer32( -2147483648 .. 2147483647 )
		MAX-ACCESS			 read-only
		STATUS					 current
		DESCRIPTION			 " -- "
		::=  { sfn9avgripEntry  55 }


	plsfn9Prb53RIPAvg		 OBJECT-TYPE
		SYNTAX					 Integer32( -2147483648 .. 2147483647 )
		MAX-ACCESS			 read-only
		STATUS					 current
		DESCRIPTION			 " -- "
		::=  { sfn9avgripEntry  56 }


	plsfn9Prb54RIPAvg		 OBJECT-TYPE
		SYNTAX					 Integer32( -2147483648 .. 2147483647 )
		MAX-ACCESS			 read-only
		STATUS					 current
		DESCRIPTION			 " -- "
		::=  { sfn9avgripEntry  57 }


	plsfn9Prb55RIPAvg		 OBJECT-TYPE
		SYNTAX					 Integer32( -2147483648 .. 2147483647 )
		MAX-ACCESS			 read-only
		STATUS					 current
		DESCRIPTION			 " -- "
		::=  { sfn9avgripEntry  58 }


	plsfn9Prb56RIPAvg		 OBJECT-TYPE
		SYNTAX					 Integer32( -2147483648 .. 2147483647 )
		MAX-ACCESS			 read-only
		STATUS					 current
		DESCRIPTION			 " -- "
		::=  { sfn9avgripEntry  59 }


	plsfn9Prb57RIPAvg		 OBJECT-TYPE
		SYNTAX					 Integer32( -2147483648 .. 2147483647 )
		MAX-ACCESS			 read-only
		STATUS					 current
		DESCRIPTION			 " -- "
		::=  { sfn9avgripEntry  60 }


	plsfn9Prb58RIPAvg		 OBJECT-TYPE
		SYNTAX					 Integer32( -2147483648 .. 2147483647 )
		MAX-ACCESS			 read-only
		STATUS					 current
		DESCRIPTION			 " -- "
		::=  { sfn9avgripEntry  61 }


	plsfn9Prb59RIPAvg		 OBJECT-TYPE
		SYNTAX					 Integer32( -2147483648 .. 2147483647 )
		MAX-ACCESS			 read-only
		STATUS					 current
		DESCRIPTION			 " -- "
		::=  { sfn9avgripEntry  62 }


	plsfn9Prb60RIPAvg		 OBJECT-TYPE
		SYNTAX					 Integer32( -2147483648 .. 2147483647 )
		MAX-ACCESS			 read-only
		STATUS					 current
		DESCRIPTION			 " -- "
		::=  { sfn9avgripEntry  63 }


	plsfn9Prb61RIPAvg		 OBJECT-TYPE
		SYNTAX					 Integer32( -2147483648 .. 2147483647 )
		MAX-ACCESS			 read-only
		STATUS					 current
		DESCRIPTION			 " -- "
		::=  { sfn9avgripEntry  64 }


	plsfn9Prb62RIPAvg		 OBJECT-TYPE
		SYNTAX					 Integer32( -2147483648 .. 2147483647 )
		MAX-ACCESS			 read-only
		STATUS					 current
		DESCRIPTION			 " -- "
		::=  { sfn9avgripEntry  65 }


	plsfn9Prb63RIPAvg		 OBJECT-TYPE
		SYNTAX					 Integer32( -2147483648 .. 2147483647 )
		MAX-ACCESS			 read-only
		STATUS					 current
		DESCRIPTION			 " -- "
		::=  { sfn9avgripEntry  66 }


	plsfn9Prb64RIPAvg		 OBJECT-TYPE
		SYNTAX					 Integer32( -2147483648 .. 2147483647 )
		MAX-ACCESS			 read-only
		STATUS					 current
		DESCRIPTION			 " -- "
		::=  { sfn9avgripEntry  67 }


	plsfn9Prb65RIPAvg		 OBJECT-TYPE
		SYNTAX					 Integer32( -2147483648 .. 2147483647 )
		MAX-ACCESS			 read-only
		STATUS					 current
		DESCRIPTION			 " -- "
		::=  { sfn9avgripEntry  68 }


	plsfn9Prb66RIPAvg		 OBJECT-TYPE
		SYNTAX					 Integer32( -2147483648 .. 2147483647 )
		MAX-ACCESS			 read-only
		STATUS					 current
		DESCRIPTION			 " -- "
		::=  { sfn9avgripEntry  69 }


	plsfn9Prb67RIPAvg		 OBJECT-TYPE
		SYNTAX					 Integer32( -2147483648 .. 2147483647 )
		MAX-ACCESS			 read-only
		STATUS					 current
		DESCRIPTION			 " -- "
		::=  { sfn9avgripEntry  70 }


	plsfn9Prb68RIPAvg		 OBJECT-TYPE
		SYNTAX					 Integer32( -2147483648 .. 2147483647 )
		MAX-ACCESS			 read-only
		STATUS					 current
		DESCRIPTION			 " -- "
		::=  { sfn9avgripEntry  71 }


	plsfn9Prb69RIPAvg		 OBJECT-TYPE
		SYNTAX					 Integer32( -2147483648 .. 2147483647 )
		MAX-ACCESS			 read-only
		STATUS					 current
		DESCRIPTION			 " -- "
		::=  { sfn9avgripEntry  72 }


	plsfn9Prb70RIPAvg		 OBJECT-TYPE
		SYNTAX					 Integer32( -2147483648 .. 2147483647 )
		MAX-ACCESS			 read-only
		STATUS					 current
		DESCRIPTION			 " -- "
		::=  { sfn9avgripEntry  73 }


	plsfn9Prb71RIPAvg		 OBJECT-TYPE
		SYNTAX					 Integer32( -2147483648 .. 2147483647 )
		MAX-ACCESS			 read-only
		STATUS					 current
		DESCRIPTION			 " -- "
		::=  { sfn9avgripEntry  74 }


	plsfn9Prb72RIPAvg		 OBJECT-TYPE
		SYNTAX					 Integer32( -2147483648 .. 2147483647 )
		MAX-ACCESS			 read-only
		STATUS					 current
		DESCRIPTION			 " -- "
		::=  { sfn9avgripEntry  75 }


	plsfn9Prb73RIPAvg		 OBJECT-TYPE
		SYNTAX					 Integer32( -2147483648 .. 2147483647 )
		MAX-ACCESS			 read-only
		STATUS					 current
		DESCRIPTION			 " -- "
		::=  { sfn9avgripEntry  76 }


	plsfn9Prb74RIPAvg		 OBJECT-TYPE
		SYNTAX					 Integer32( -2147483648 .. 2147483647 )
		MAX-ACCESS			 read-only
		STATUS					 current
		DESCRIPTION			 " -- "
		::=  { sfn9avgripEntry  77 }


	plsfn9Prb75RIPAvg		 OBJECT-TYPE
		SYNTAX					 Integer32( -2147483648 .. 2147483647 )
		MAX-ACCESS			 read-only
		STATUS					 current
		DESCRIPTION			 " -- "
		::=  { sfn9avgripEntry  78 }


	plsfn9Prb76RIPAvg		 OBJECT-TYPE
		SYNTAX					 Integer32( -2147483648 .. 2147483647 )
		MAX-ACCESS			 read-only
		STATUS					 current
		DESCRIPTION			 " -- "
		::=  { sfn9avgripEntry  79 }


	plsfn9Prb77RIPAvg		 OBJECT-TYPE
		SYNTAX					 Integer32( -2147483648 .. 2147483647 )
		MAX-ACCESS			 read-only
		STATUS					 current
		DESCRIPTION			 " -- "
		::=  { sfn9avgripEntry  80 }


	plsfn9Prb78RIPAvg		 OBJECT-TYPE
		SYNTAX					 Integer32( -2147483648 .. 2147483647 )
		MAX-ACCESS			 read-only
		STATUS					 current
		DESCRIPTION			 " -- "
		::=  { sfn9avgripEntry  81 }


	plsfn9Prb79RIPAvg		 OBJECT-TYPE
		SYNTAX					 Integer32( -2147483648 .. 2147483647 )
		MAX-ACCESS			 read-only
		STATUS					 current
		DESCRIPTION			 " -- "
		::=  { sfn9avgripEntry  82 }


	plsfn9Prb80RIPAvg		 OBJECT-TYPE
		SYNTAX					 Integer32( -2147483648 .. 2147483647 )
		MAX-ACCESS			 read-only
		STATUS					 current
		DESCRIPTION			 " -- "
		::=  { sfn9avgripEntry  83 }


	plsfn9Prb81RIPAvg		 OBJECT-TYPE
		SYNTAX					 Integer32( -2147483648 .. 2147483647 )
		MAX-ACCESS			 read-only
		STATUS					 current
		DESCRIPTION			 " -- "
		::=  { sfn9avgripEntry  84 }


	plsfn9Prb82RIPAvg		 OBJECT-TYPE
		SYNTAX					 Integer32( -2147483648 .. 2147483647 )
		MAX-ACCESS			 read-only
		STATUS					 current
		DESCRIPTION			 " -- "
		::=  { sfn9avgripEntry  85 }


	plsfn9Prb83RIPAvg		 OBJECT-TYPE
		SYNTAX					 Integer32( -2147483648 .. 2147483647 )
		MAX-ACCESS			 read-only
		STATUS					 current
		DESCRIPTION			 " -- "
		::=  { sfn9avgripEntry  86 }


	plsfn9Prb84RIPAvg		 OBJECT-TYPE
		SYNTAX					 Integer32( -2147483648 .. 2147483647 )
		MAX-ACCESS			 read-only
		STATUS					 current
		DESCRIPTION			 " -- "
		::=  { sfn9avgripEntry  87 }


	plsfn9Prb85RIPAvg		 OBJECT-TYPE
		SYNTAX					 Integer32( -2147483648 .. 2147483647 )
		MAX-ACCESS			 read-only
		STATUS					 current
		DESCRIPTION			 " -- "
		::=  { sfn9avgripEntry  88 }


	plsfn9Prb86RIPAvg		 OBJECT-TYPE
		SYNTAX					 Integer32( -2147483648 .. 2147483647 )
		MAX-ACCESS			 read-only
		STATUS					 current
		DESCRIPTION			 " -- "
		::=  { sfn9avgripEntry  89 }


	plsfn9Prb87RIPAvg		 OBJECT-TYPE
		SYNTAX					 Integer32( -2147483648 .. 2147483647 )
		MAX-ACCESS			 read-only
		STATUS					 current
		DESCRIPTION			 " -- "
		::=  { sfn9avgripEntry  90 }


	plsfn9Prb88RIPAvg		 OBJECT-TYPE
		SYNTAX					 Integer32( -2147483648 .. 2147483647 )
		MAX-ACCESS			 read-only
		STATUS					 current
		DESCRIPTION			 " -- "
		::=  { sfn9avgripEntry  91 }


	plsfn9Prb89RIPAvg		 OBJECT-TYPE
		SYNTAX					 Integer32( -2147483648 .. 2147483647 )
		MAX-ACCESS			 read-only
		STATUS					 current
		DESCRIPTION			 " -- "
		::=  { sfn9avgripEntry  92 }


	plsfn9Prb90RIPAvg		 OBJECT-TYPE
		SYNTAX					 Integer32( -2147483648 .. 2147483647 )
		MAX-ACCESS			 read-only
		STATUS					 current
		DESCRIPTION			 " -- "
		::=  { sfn9avgripEntry  93 }


	plsfn9Prb91RIPAvg		 OBJECT-TYPE
		SYNTAX					 Integer32( -2147483648 .. 2147483647 )
		MAX-ACCESS			 read-only
		STATUS					 current
		DESCRIPTION			 " -- "
		::=  { sfn9avgripEntry  94 }


	plsfn9Prb92RIPAvg		 OBJECT-TYPE
		SYNTAX					 Integer32( -2147483648 .. 2147483647 )
		MAX-ACCESS			 read-only
		STATUS					 current
		DESCRIPTION			 " -- "
		::=  { sfn9avgripEntry  95 }


	plsfn9Prb93RIPAvg		 OBJECT-TYPE
		SYNTAX					 Integer32( -2147483648 .. 2147483647 )
		MAX-ACCESS			 read-only
		STATUS					 current
		DESCRIPTION			 " -- "
		::=  { sfn9avgripEntry  96 }


	plsfn9Prb94RIPAvg		 OBJECT-TYPE
		SYNTAX					 Integer32( -2147483648 .. 2147483647 )
		MAX-ACCESS			 read-only
		STATUS					 current
		DESCRIPTION			 " -- "
		::=  { sfn9avgripEntry  97 }


	plsfn9Prb95RIPAvg		 OBJECT-TYPE
		SYNTAX					 Integer32( -2147483648 .. 2147483647 )
		MAX-ACCESS			 read-only
		STATUS					 current
		DESCRIPTION			 " -- "
		::=  { sfn9avgripEntry  98 }


	plsfn9Prb96RIPAvg		 OBJECT-TYPE
		SYNTAX					 Integer32( -2147483648 .. 2147483647 )
		MAX-ACCESS			 read-only
		STATUS					 current
		DESCRIPTION			 " -- "
		::=  { sfn9avgripEntry  99 }


	plsfn9Prb97RIPAvg		 OBJECT-TYPE
		SYNTAX					 Integer32( -2147483648 .. 2147483647 )
		MAX-ACCESS			 read-only
		STATUS					 current
		DESCRIPTION			 " -- "
		::=  { sfn9avgripEntry  100 }


	plsfn9Prb98RIPAvg		 OBJECT-TYPE
		SYNTAX					 Integer32( -2147483648 .. 2147483647 )
		MAX-ACCESS			 read-only
		STATUS					 current
		DESCRIPTION			 " -- "
		::=  { sfn9avgripEntry  101 }


	plsfn9Prb99RIPAvg		 OBJECT-TYPE
		SYNTAX					 Integer32( -2147483648 .. 2147483647 )
		MAX-ACCESS			 read-only
		STATUS					 current
		DESCRIPTION			 " -- "
		::=  { sfn9avgripEntry  102 }


	sfn7avgripTable		 OBJECT-TYPE
		SYNTAX					 SEQUENCE  OF	 Sfn7avgripEntry
		MAX-ACCESS			 not-accessible
		STATUS					 current
		DESCRIPTION			 " -- "
		::=  { plrelatedOriginCounter  12 }


	sfn7avgripEntry		 OBJECT-TYPE
		SYNTAX					 Sfn7avgripEntry
		MAX-ACCESS			 not-accessible
		STATUS					 current
		DESCRIPTION			 " -- "
		INDEX						{ sfn7avgripLcId }
		::=  { sfn7avgripTable  1 }


	Sfn7avgripEntry		 ::=  SEQUENCE {
		sfn7avgripLcId					Integer32,
		sfn7avgripRowStatus					RowStatus,
		plsfn7Prb00RIPAvg					Integer32,
		plsfn7Prb01RIPAvg					Integer32,
		plsfn7Prb02RIPAvg					Integer32,
		plsfn7Prb03RIPAvg					Integer32,
		plsfn7Prb04RIPAvg					Integer32,
		plsfn7Prb05RIPAvg					Integer32,
		plsfn7Prb06RIPAvg					Integer32,
		plsfn7Prb07RIPAvg					Integer32,
		plsfn7Prb08RIPAvg					Integer32,
		plsfn7Prb09RIPAvg					Integer32,
		plsfn7Prb10RIPAvg					Integer32,
		plsfn7Prb11RIPAvg					Integer32,
		plsfn7Prb12RIPAvg					Integer32,
		plsfn7Prb13RIPAvg					Integer32,
		plsfn7Prb14RIPAvg					Integer32,
		plsfn7Prb15RIPAvg					Integer32,
		plsfn7Prb16RIPAvg					Integer32,
		plsfn7Prb17RIPAvg					Integer32,
		plsfn7Prb18RIPAvg					Integer32,
		plsfn7Prb19RIPAvg					Integer32,
		plsfn7Prb20RIPAvg					Integer32,
		plsfn7Prb21RIPAvg					Integer32,
		plsfn7Prb22RIPAvg					Integer32,
		plsfn7Prb23RIPAvg					Integer32,
		plsfn7Prb24RIPAvg					Integer32,
		plsfn7Prb25RIPAvg					Integer32,
		plsfn7Prb26RIPAvg					Integer32,
		plsfn7Prb27RIPAvg					Integer32,
		plsfn7Prb28RIPAvg					Integer32,
		plsfn7Prb29RIPAvg					Integer32,
		plsfn7Prb30RIPAvg					Integer32,
		plsfn7Prb31RIPAvg					Integer32,
		plsfn7Prb32RIPAvg					Integer32,
		plsfn7Prb33RIPAvg					Integer32,
		plsfn7Prb34RIPAvg					Integer32,
		plsfn7Prb35RIPAvg					Integer32,
		plsfn7Prb36RIPAvg					Integer32,
		plsfn7Prb37RIPAvg					Integer32,
		plsfn7Prb38RIPAvg					Integer32,
		plsfn7Prb39RIPAvg					Integer32,
		plsfn7Prb40RIPAvg					Integer32,
		plsfn7Prb41RIPAvg					Integer32,
		plsfn7Prb42RIPAvg					Integer32,
		plsfn7Prb43RIPAvg					Integer32,
		plsfn7Prb44RIPAvg					Integer32,
		plsfn7Prb45RIPAvg					Integer32,
		plsfn7Prb46RIPAvg					Integer32,
		plsfn7Prb47RIPAvg					Integer32,
		plsfn7Prb48RIPAvg					Integer32,
		plsfn7Prb49RIPAvg					Integer32,
		plsfn7Prb50RIPAvg					Integer32,
		plsfn7Prb51RIPAvg					Integer32,
		plsfn7Prb52RIPAvg					Integer32,
		plsfn7Prb53RIPAvg					Integer32,
		plsfn7Prb54RIPAvg					Integer32,
		plsfn7Prb55RIPAvg					Integer32,
		plsfn7Prb56RIPAvg					Integer32,
		plsfn7Prb57RIPAvg					Integer32,
		plsfn7Prb58RIPAvg					Integer32,
		plsfn7Prb59RIPAvg					Integer32,
		plsfn7Prb60RIPAvg					Integer32,
		plsfn7Prb61RIPAvg					Integer32,
		plsfn7Prb62RIPAvg					Integer32,
		plsfn7Prb63RIPAvg					Integer32,
		plsfn7Prb64RIPAvg					Integer32,
		plsfn7Prb65RIPAvg					Integer32,
		plsfn7Prb66RIPAvg					Integer32,
		plsfn7Prb67RIPAvg					Integer32,
		plsfn7Prb68RIPAvg					Integer32,
		plsfn7Prb69RIPAvg					Integer32,
		plsfn7Prb70RIPAvg					Integer32,
		plsfn7Prb71RIPAvg					Integer32,
		plsfn7Prb72RIPAvg					Integer32,
		plsfn7Prb73RIPAvg					Integer32,
		plsfn7Prb74RIPAvg					Integer32,
		plsfn7Prb75RIPAvg					Integer32,
		plsfn7Prb76RIPAvg					Integer32,
		plsfn7Prb77RIPAvg					Integer32,
		plsfn7Prb78RIPAvg					Integer32,
		plsfn7Prb79RIPAvg					Integer32,
		plsfn7Prb80RIPAvg					Integer32,
		plsfn7Prb81RIPAvg					Integer32,
		plsfn7Prb82RIPAvg					Integer32,
		plsfn7Prb83RIPAvg					Integer32,
		plsfn7Prb84RIPAvg					Integer32,
		plsfn7Prb85RIPAvg					Integer32,
		plsfn7Prb86RIPAvg					Integer32,
		plsfn7Prb87RIPAvg					Integer32,
		plsfn7Prb88RIPAvg					Integer32,
		plsfn7Prb89RIPAvg					Integer32,
		plsfn7Prb90RIPAvg					Integer32,
		plsfn7Prb91RIPAvg					Integer32,
		plsfn7Prb92RIPAvg					Integer32,
		plsfn7Prb93RIPAvg					Integer32,
		plsfn7Prb94RIPAvg					Integer32,
		plsfn7Prb95RIPAvg					Integer32,
		plsfn7Prb96RIPAvg					Integer32,
		plsfn7Prb97RIPAvg					Integer32,
		plsfn7Prb98RIPAvg					Integer32,
		plsfn7Prb99RIPAvg					Integer32
		}


	sfn7avgripLcId		 OBJECT-TYPE
		SYNTAX					 Integer32( 0 .. 23 )
		MAX-ACCESS			 not-accessible
		STATUS					 current
		DESCRIPTION			 " -- "
		::=  { sfn7avgripEntry  1 }


	sfn7avgripRowStatus		 OBJECT-TYPE
		SYNTAX					 RowStatus
		MAX-ACCESS			 read-only
		STATUS					 current
		DESCRIPTION			 " -- "
		::=  { sfn7avgripEntry  2 }


	plsfn7Prb00RIPAvg		 OBJECT-TYPE
		SYNTAX					 Integer32( -2147483648 .. 2147483647 )
		MAX-ACCESS			 read-only
		STATUS					 current
		DESCRIPTION			 " -- "
		::=  { sfn7avgripEntry  3 }


	plsfn7Prb01RIPAvg		 OBJECT-TYPE
		SYNTAX					 Integer32( -2147483648 .. 2147483647 )
		MAX-ACCESS			 read-only
		STATUS					 current
		DESCRIPTION			 " -- "
		::=  { sfn7avgripEntry  4 }


	plsfn7Prb02RIPAvg		 OBJECT-TYPE
		SYNTAX					 Integer32( -2147483648 .. 2147483647 )
		MAX-ACCESS			 read-only
		STATUS					 current
		DESCRIPTION			 " -- "
		::=  { sfn7avgripEntry  5 }


	plsfn7Prb03RIPAvg		 OBJECT-TYPE
		SYNTAX					 Integer32( -2147483648 .. 2147483647 )
		MAX-ACCESS			 read-only
		STATUS					 current
		DESCRIPTION			 " -- "
		::=  { sfn7avgripEntry  6 }


	plsfn7Prb04RIPAvg		 OBJECT-TYPE
		SYNTAX					 Integer32( -2147483648 .. 2147483647 )
		MAX-ACCESS			 read-only
		STATUS					 current
		DESCRIPTION			 " -- "
		::=  { sfn7avgripEntry  7 }


	plsfn7Prb05RIPAvg		 OBJECT-TYPE
		SYNTAX					 Integer32( -2147483648 .. 2147483647 )
		MAX-ACCESS			 read-only
		STATUS					 current
		DESCRIPTION			 " -- "
		::=  { sfn7avgripEntry  8 }


	plsfn7Prb06RIPAvg		 OBJECT-TYPE
		SYNTAX					 Integer32( -2147483648 .. 2147483647 )
		MAX-ACCESS			 read-only
		STATUS					 current
		DESCRIPTION			 " -- "
		::=  { sfn7avgripEntry  9 }


	plsfn7Prb07RIPAvg		 OBJECT-TYPE
		SYNTAX					 Integer32( -2147483648 .. 2147483647 )
		MAX-ACCESS			 read-only
		STATUS					 current
		DESCRIPTION			 " -- "
		::=  { sfn7avgripEntry  10 }


	plsfn7Prb08RIPAvg		 OBJECT-TYPE
		SYNTAX					 Integer32( -2147483648 .. 2147483647 )
		MAX-ACCESS			 read-only
		STATUS					 current
		DESCRIPTION			 " -- "
		::=  { sfn7avgripEntry  11 }


	plsfn7Prb09RIPAvg		 OBJECT-TYPE
		SYNTAX					 Integer32( -2147483648 .. 2147483647 )
		MAX-ACCESS			 read-only
		STATUS					 current
		DESCRIPTION			 " -- "
		::=  { sfn7avgripEntry  12 }


	plsfn7Prb10RIPAvg		 OBJECT-TYPE
		SYNTAX					 Integer32( -2147483648 .. 2147483647 )
		MAX-ACCESS			 read-only
		STATUS					 current
		DESCRIPTION			 " -- "
		::=  { sfn7avgripEntry  13 }


	plsfn7Prb11RIPAvg		 OBJECT-TYPE
		SYNTAX					 Integer32( -2147483648 .. 2147483647 )
		MAX-ACCESS			 read-only
		STATUS					 current
		DESCRIPTION			 " -- "
		::=  { sfn7avgripEntry  14 }


	plsfn7Prb12RIPAvg		 OBJECT-TYPE
		SYNTAX					 Integer32( -2147483648 .. 2147483647 )
		MAX-ACCESS			 read-only
		STATUS					 current
		DESCRIPTION			 " -- "
		::=  { sfn7avgripEntry  15 }


	plsfn7Prb13RIPAvg		 OBJECT-TYPE
		SYNTAX					 Integer32( -2147483648 .. 2147483647 )
		MAX-ACCESS			 read-only
		STATUS					 current
		DESCRIPTION			 " -- "
		::=  { sfn7avgripEntry  16 }


	plsfn7Prb14RIPAvg		 OBJECT-TYPE
		SYNTAX					 Integer32( -2147483648 .. 2147483647 )
		MAX-ACCESS			 read-only
		STATUS					 current
		DESCRIPTION			 " -- "
		::=  { sfn7avgripEntry  17 }


	plsfn7Prb15RIPAvg		 OBJECT-TYPE
		SYNTAX					 Integer32( -2147483648 .. 2147483647 )
		MAX-ACCESS			 read-only
		STATUS					 current
		DESCRIPTION			 " -- "
		::=  { sfn7avgripEntry  18 }


	plsfn7Prb16RIPAvg		 OBJECT-TYPE
		SYNTAX					 Integer32( -2147483648 .. 2147483647 )
		MAX-ACCESS			 read-only
		STATUS					 current
		DESCRIPTION			 " -- "
		::=  { sfn7avgripEntry  19 }


	plsfn7Prb17RIPAvg		 OBJECT-TYPE
		SYNTAX					 Integer32( -2147483648 .. 2147483647 )
		MAX-ACCESS			 read-only
		STATUS					 current
		DESCRIPTION			 " -- "
		::=  { sfn7avgripEntry  20 }


	plsfn7Prb18RIPAvg		 OBJECT-TYPE
		SYNTAX					 Integer32( -2147483648 .. 2147483647 )
		MAX-ACCESS			 read-only
		STATUS					 current
		DESCRIPTION			 " -- "
		::=  { sfn7avgripEntry  21 }


	plsfn7Prb19RIPAvg		 OBJECT-TYPE
		SYNTAX					 Integer32( -2147483648 .. 2147483647 )
		MAX-ACCESS			 read-only
		STATUS					 current
		DESCRIPTION			 " -- "
		::=  { sfn7avgripEntry  22 }


	plsfn7Prb20RIPAvg		 OBJECT-TYPE
		SYNTAX					 Integer32( -2147483648 .. 2147483647 )
		MAX-ACCESS			 read-only
		STATUS					 current
		DESCRIPTION			 " -- "
		::=  { sfn7avgripEntry  23 }


	plsfn7Prb21RIPAvg		 OBJECT-TYPE
		SYNTAX					 Integer32( -2147483648 .. 2147483647 )
		MAX-ACCESS			 read-only
		STATUS					 current
		DESCRIPTION			 " -- "
		::=  { sfn7avgripEntry  24 }


	plsfn7Prb22RIPAvg		 OBJECT-TYPE
		SYNTAX					 Integer32( -2147483648 .. 2147483647 )
		MAX-ACCESS			 read-only
		STATUS					 current
		DESCRIPTION			 " -- "
		::=  { sfn7avgripEntry  25 }


	plsfn7Prb23RIPAvg		 OBJECT-TYPE
		SYNTAX					 Integer32( -2147483648 .. 2147483647 )
		MAX-ACCESS			 read-only
		STATUS					 current
		DESCRIPTION			 " -- "
		::=  { sfn7avgripEntry  26 }


	plsfn7Prb24RIPAvg		 OBJECT-TYPE
		SYNTAX					 Integer32( -2147483648 .. 2147483647 )
		MAX-ACCESS			 read-only
		STATUS					 current
		DESCRIPTION			 " -- "
		::=  { sfn7avgripEntry  27 }


	plsfn7Prb25RIPAvg		 OBJECT-TYPE
		SYNTAX					 Integer32( -2147483648 .. 2147483647 )
		MAX-ACCESS			 read-only
		STATUS					 current
		DESCRIPTION			 " -- "
		::=  { sfn7avgripEntry  28 }


	plsfn7Prb26RIPAvg		 OBJECT-TYPE
		SYNTAX					 Integer32( -2147483648 .. 2147483647 )
		MAX-ACCESS			 read-only
		STATUS					 current
		DESCRIPTION			 " -- "
		::=  { sfn7avgripEntry  29 }


	plsfn7Prb27RIPAvg		 OBJECT-TYPE
		SYNTAX					 Integer32( -2147483648 .. 2147483647 )
		MAX-ACCESS			 read-only
		STATUS					 current
		DESCRIPTION			 " -- "
		::=  { sfn7avgripEntry  30 }


	plsfn7Prb28RIPAvg		 OBJECT-TYPE
		SYNTAX					 Integer32( -2147483648 .. 2147483647 )
		MAX-ACCESS			 read-only
		STATUS					 current
		DESCRIPTION			 " -- "
		::=  { sfn7avgripEntry  31 }


	plsfn7Prb29RIPAvg		 OBJECT-TYPE
		SYNTAX					 Integer32( -2147483648 .. 2147483647 )
		MAX-ACCESS			 read-only
		STATUS					 current
		DESCRIPTION			 " -- "
		::=  { sfn7avgripEntry  32 }


	plsfn7Prb30RIPAvg		 OBJECT-TYPE
		SYNTAX					 Integer32( -2147483648 .. 2147483647 )
		MAX-ACCESS			 read-only
		STATUS					 current
		DESCRIPTION			 " -- "
		::=  { sfn7avgripEntry  33 }


	plsfn7Prb31RIPAvg		 OBJECT-TYPE
		SYNTAX					 Integer32( -2147483648 .. 2147483647 )
		MAX-ACCESS			 read-only
		STATUS					 current
		DESCRIPTION			 " -- "
		::=  { sfn7avgripEntry  34 }


	plsfn7Prb32RIPAvg		 OBJECT-TYPE
		SYNTAX					 Integer32( -2147483648 .. 2147483647 )
		MAX-ACCESS			 read-only
		STATUS					 current
		DESCRIPTION			 " -- "
		::=  { sfn7avgripEntry  35 }


	plsfn7Prb33RIPAvg		 OBJECT-TYPE
		SYNTAX					 Integer32( -2147483648 .. 2147483647 )
		MAX-ACCESS			 read-only
		STATUS					 current
		DESCRIPTION			 " -- "
		::=  { sfn7avgripEntry  36 }


	plsfn7Prb34RIPAvg		 OBJECT-TYPE
		SYNTAX					 Integer32( -2147483648 .. 2147483647 )
		MAX-ACCESS			 read-only
		STATUS					 current
		DESCRIPTION			 " -- "
		::=  { sfn7avgripEntry  37 }


	plsfn7Prb35RIPAvg		 OBJECT-TYPE
		SYNTAX					 Integer32( -2147483648 .. 2147483647 )
		MAX-ACCESS			 read-only
		STATUS					 current
		DESCRIPTION			 " -- "
		::=  { sfn7avgripEntry  38 }


	plsfn7Prb36RIPAvg		 OBJECT-TYPE
		SYNTAX					 Integer32( -2147483648 .. 2147483647 )
		MAX-ACCESS			 read-only
		STATUS					 current
		DESCRIPTION			 " -- "
		::=  { sfn7avgripEntry  39 }


	plsfn7Prb37RIPAvg		 OBJECT-TYPE
		SYNTAX					 Integer32( -2147483648 .. 2147483647 )
		MAX-ACCESS			 read-only
		STATUS					 current
		DESCRIPTION			 " -- "
		::=  { sfn7avgripEntry  40 }


	plsfn7Prb38RIPAvg		 OBJECT-TYPE
		SYNTAX					 Integer32( -2147483648 .. 2147483647 )
		MAX-ACCESS			 read-only
		STATUS					 current
		DESCRIPTION			 " -- "
		::=  { sfn7avgripEntry  41 }


	plsfn7Prb39RIPAvg		 OBJECT-TYPE
		SYNTAX					 Integer32( -2147483648 .. 2147483647 )
		MAX-ACCESS			 read-only
		STATUS					 current
		DESCRIPTION			 " -- "
		::=  { sfn7avgripEntry  42 }


	plsfn7Prb40RIPAvg		 OBJECT-TYPE
		SYNTAX					 Integer32( -2147483648 .. 2147483647 )
		MAX-ACCESS			 read-only
		STATUS					 current
		DESCRIPTION			 " -- "
		::=  { sfn7avgripEntry  43 }


	plsfn7Prb41RIPAvg		 OBJECT-TYPE
		SYNTAX					 Integer32( -2147483648 .. 2147483647 )
		MAX-ACCESS			 read-only
		STATUS					 current
		DESCRIPTION			 " -- "
		::=  { sfn7avgripEntry  44 }


	plsfn7Prb42RIPAvg		 OBJECT-TYPE
		SYNTAX					 Integer32( -2147483648 .. 2147483647 )
		MAX-ACCESS			 read-only
		STATUS					 current
		DESCRIPTION			 " -- "
		::=  { sfn7avgripEntry  45 }


	plsfn7Prb43RIPAvg		 OBJECT-TYPE
		SYNTAX					 Integer32( -2147483648 .. 2147483647 )
		MAX-ACCESS			 read-only
		STATUS					 current
		DESCRIPTION			 " -- "
		::=  { sfn7avgripEntry  46 }


	plsfn7Prb44RIPAvg		 OBJECT-TYPE
		SYNTAX					 Integer32( -2147483648 .. 2147483647 )
		MAX-ACCESS			 read-only
		STATUS					 current
		DESCRIPTION			 " -- "
		::=  { sfn7avgripEntry  47 }


	plsfn7Prb45RIPAvg		 OBJECT-TYPE
		SYNTAX					 Integer32( -2147483648 .. 2147483647 )
		MAX-ACCESS			 read-only
		STATUS					 current
		DESCRIPTION			 " -- "
		::=  { sfn7avgripEntry  48 }


	plsfn7Prb46RIPAvg		 OBJECT-TYPE
		SYNTAX					 Integer32( -2147483648 .. 2147483647 )
		MAX-ACCESS			 read-only
		STATUS					 current
		DESCRIPTION			 " -- "
		::=  { sfn7avgripEntry  49 }


	plsfn7Prb47RIPAvg		 OBJECT-TYPE
		SYNTAX					 Integer32( -2147483648 .. 2147483647 )
		MAX-ACCESS			 read-only
		STATUS					 current
		DESCRIPTION			 " -- "
		::=  { sfn7avgripEntry  50 }


	plsfn7Prb48RIPAvg		 OBJECT-TYPE
		SYNTAX					 Integer32( -2147483648 .. 2147483647 )
		MAX-ACCESS			 read-only
		STATUS					 current
		DESCRIPTION			 " -- "
		::=  { sfn7avgripEntry  51 }


	plsfn7Prb49RIPAvg		 OBJECT-TYPE
		SYNTAX					 Integer32( -2147483648 .. 2147483647 )
		MAX-ACCESS			 read-only
		STATUS					 current
		DESCRIPTION			 " -- "
		::=  { sfn7avgripEntry  52 }


	plsfn7Prb50RIPAvg		 OBJECT-TYPE
		SYNTAX					 Integer32( -2147483648 .. 2147483647 )
		MAX-ACCESS			 read-only
		STATUS					 current
		DESCRIPTION			 " -- "
		::=  { sfn7avgripEntry  53 }


	plsfn7Prb51RIPAvg		 OBJECT-TYPE
		SYNTAX					 Integer32( -2147483648 .. 2147483647 )
		MAX-ACCESS			 read-only
		STATUS					 current
		DESCRIPTION			 " -- "
		::=  { sfn7avgripEntry  54 }


	plsfn7Prb52RIPAvg		 OBJECT-TYPE
		SYNTAX					 Integer32( -2147483648 .. 2147483647 )
		MAX-ACCESS			 read-only
		STATUS					 current
		DESCRIPTION			 " -- "
		::=  { sfn7avgripEntry  55 }


	plsfn7Prb53RIPAvg		 OBJECT-TYPE
		SYNTAX					 Integer32( -2147483648 .. 2147483647 )
		MAX-ACCESS			 read-only
		STATUS					 current
		DESCRIPTION			 " -- "
		::=  { sfn7avgripEntry  56 }


	plsfn7Prb54RIPAvg		 OBJECT-TYPE
		SYNTAX					 Integer32( -2147483648 .. 2147483647 )
		MAX-ACCESS			 read-only
		STATUS					 current
		DESCRIPTION			 " -- "
		::=  { sfn7avgripEntry  57 }


	plsfn7Prb55RIPAvg		 OBJECT-TYPE
		SYNTAX					 Integer32( -2147483648 .. 2147483647 )
		MAX-ACCESS			 read-only
		STATUS					 current
		DESCRIPTION			 " -- "
		::=  { sfn7avgripEntry  58 }


	plsfn7Prb56RIPAvg		 OBJECT-TYPE
		SYNTAX					 Integer32( -2147483648 .. 2147483647 )
		MAX-ACCESS			 read-only
		STATUS					 current
		DESCRIPTION			 " -- "
		::=  { sfn7avgripEntry  59 }


	plsfn7Prb57RIPAvg		 OBJECT-TYPE
		SYNTAX					 Integer32( -2147483648 .. 2147483647 )
		MAX-ACCESS			 read-only
		STATUS					 current
		DESCRIPTION			 " -- "
		::=  { sfn7avgripEntry  60 }


	plsfn7Prb58RIPAvg		 OBJECT-TYPE
		SYNTAX					 Integer32( -2147483648 .. 2147483647 )
		MAX-ACCESS			 read-only
		STATUS					 current
		DESCRIPTION			 " -- "
		::=  { sfn7avgripEntry  61 }


	plsfn7Prb59RIPAvg		 OBJECT-TYPE
		SYNTAX					 Integer32( -2147483648 .. 2147483647 )
		MAX-ACCESS			 read-only
		STATUS					 current
		DESCRIPTION			 " -- "
		::=  { sfn7avgripEntry  62 }


	plsfn7Prb60RIPAvg		 OBJECT-TYPE
		SYNTAX					 Integer32( -2147483648 .. 2147483647 )
		MAX-ACCESS			 read-only
		STATUS					 current
		DESCRIPTION			 " -- "
		::=  { sfn7avgripEntry  63 }


	plsfn7Prb61RIPAvg		 OBJECT-TYPE
		SYNTAX					 Integer32( -2147483648 .. 2147483647 )
		MAX-ACCESS			 read-only
		STATUS					 current
		DESCRIPTION			 " -- "
		::=  { sfn7avgripEntry  64 }


	plsfn7Prb62RIPAvg		 OBJECT-TYPE
		SYNTAX					 Integer32( -2147483648 .. 2147483647 )
		MAX-ACCESS			 read-only
		STATUS					 current
		DESCRIPTION			 " -- "
		::=  { sfn7avgripEntry  65 }


	plsfn7Prb63RIPAvg		 OBJECT-TYPE
		SYNTAX					 Integer32( -2147483648 .. 2147483647 )
		MAX-ACCESS			 read-only
		STATUS					 current
		DESCRIPTION			 " -- "
		::=  { sfn7avgripEntry  66 }


	plsfn7Prb64RIPAvg		 OBJECT-TYPE
		SYNTAX					 Integer32( -2147483648 .. 2147483647 )
		MAX-ACCESS			 read-only
		STATUS					 current
		DESCRIPTION			 " -- "
		::=  { sfn7avgripEntry  67 }


	plsfn7Prb65RIPAvg		 OBJECT-TYPE
		SYNTAX					 Integer32( -2147483648 .. 2147483647 )
		MAX-ACCESS			 read-only
		STATUS					 current
		DESCRIPTION			 " -- "
		::=  { sfn7avgripEntry  68 }


	plsfn7Prb66RIPAvg		 OBJECT-TYPE
		SYNTAX					 Integer32( -2147483648 .. 2147483647 )
		MAX-ACCESS			 read-only
		STATUS					 current
		DESCRIPTION			 " -- "
		::=  { sfn7avgripEntry  69 }


	plsfn7Prb67RIPAvg		 OBJECT-TYPE
		SYNTAX					 Integer32( -2147483648 .. 2147483647 )
		MAX-ACCESS			 read-only
		STATUS					 current
		DESCRIPTION			 " -- "
		::=  { sfn7avgripEntry  70 }


	plsfn7Prb68RIPAvg		 OBJECT-TYPE
		SYNTAX					 Integer32( -2147483648 .. 2147483647 )
		MAX-ACCESS			 read-only
		STATUS					 current
		DESCRIPTION			 " -- "
		::=  { sfn7avgripEntry  71 }


	plsfn7Prb69RIPAvg		 OBJECT-TYPE
		SYNTAX					 Integer32( -2147483648 .. 2147483647 )
		MAX-ACCESS			 read-only
		STATUS					 current
		DESCRIPTION			 " -- "
		::=  { sfn7avgripEntry  72 }


	plsfn7Prb70RIPAvg		 OBJECT-TYPE
		SYNTAX					 Integer32( -2147483648 .. 2147483647 )
		MAX-ACCESS			 read-only
		STATUS					 current
		DESCRIPTION			 " -- "
		::=  { sfn7avgripEntry  73 }


	plsfn7Prb71RIPAvg		 OBJECT-TYPE
		SYNTAX					 Integer32( -2147483648 .. 2147483647 )
		MAX-ACCESS			 read-only
		STATUS					 current
		DESCRIPTION			 " -- "
		::=  { sfn7avgripEntry  74 }


	plsfn7Prb72RIPAvg		 OBJECT-TYPE
		SYNTAX					 Integer32( -2147483648 .. 2147483647 )
		MAX-ACCESS			 read-only
		STATUS					 current
		DESCRIPTION			 " -- "
		::=  { sfn7avgripEntry  75 }


	plsfn7Prb73RIPAvg		 OBJECT-TYPE
		SYNTAX					 Integer32( -2147483648 .. 2147483647 )
		MAX-ACCESS			 read-only
		STATUS					 current
		DESCRIPTION			 " -- "
		::=  { sfn7avgripEntry  76 }


	plsfn7Prb74RIPAvg		 OBJECT-TYPE
		SYNTAX					 Integer32( -2147483648 .. 2147483647 )
		MAX-ACCESS			 read-only
		STATUS					 current
		DESCRIPTION			 " -- "
		::=  { sfn7avgripEntry  77 }


	plsfn7Prb75RIPAvg		 OBJECT-TYPE
		SYNTAX					 Integer32( -2147483648 .. 2147483647 )
		MAX-ACCESS			 read-only
		STATUS					 current
		DESCRIPTION			 " -- "
		::=  { sfn7avgripEntry  78 }


	plsfn7Prb76RIPAvg		 OBJECT-TYPE
		SYNTAX					 Integer32( -2147483648 .. 2147483647 )
		MAX-ACCESS			 read-only
		STATUS					 current
		DESCRIPTION			 " -- "
		::=  { sfn7avgripEntry  79 }


	plsfn7Prb77RIPAvg		 OBJECT-TYPE
		SYNTAX					 Integer32( -2147483648 .. 2147483647 )
		MAX-ACCESS			 read-only
		STATUS					 current
		DESCRIPTION			 " -- "
		::=  { sfn7avgripEntry  80 }


	plsfn7Prb78RIPAvg		 OBJECT-TYPE
		SYNTAX					 Integer32( -2147483648 .. 2147483647 )
		MAX-ACCESS			 read-only
		STATUS					 current
		DESCRIPTION			 " -- "
		::=  { sfn7avgripEntry  81 }


	plsfn7Prb79RIPAvg		 OBJECT-TYPE
		SYNTAX					 Integer32( -2147483648 .. 2147483647 )
		MAX-ACCESS			 read-only
		STATUS					 current
		DESCRIPTION			 " -- "
		::=  { sfn7avgripEntry  82 }


	plsfn7Prb80RIPAvg		 OBJECT-TYPE
		SYNTAX					 Integer32( -2147483648 .. 2147483647 )
		MAX-ACCESS			 read-only
		STATUS					 current
		DESCRIPTION			 " -- "
		::=  { sfn7avgripEntry  83 }


	plsfn7Prb81RIPAvg		 OBJECT-TYPE
		SYNTAX					 Integer32( -2147483648 .. 2147483647 )
		MAX-ACCESS			 read-only
		STATUS					 current
		DESCRIPTION			 " -- "
		::=  { sfn7avgripEntry  84 }


	plsfn7Prb82RIPAvg		 OBJECT-TYPE
		SYNTAX					 Integer32( -2147483648 .. 2147483647 )
		MAX-ACCESS			 read-only
		STATUS					 current
		DESCRIPTION			 " -- "
		::=  { sfn7avgripEntry  85 }


	plsfn7Prb83RIPAvg		 OBJECT-TYPE
		SYNTAX					 Integer32( -2147483648 .. 2147483647 )
		MAX-ACCESS			 read-only
		STATUS					 current
		DESCRIPTION			 " -- "
		::=  { sfn7avgripEntry  86 }


	plsfn7Prb84RIPAvg		 OBJECT-TYPE
		SYNTAX					 Integer32( -2147483648 .. 2147483647 )
		MAX-ACCESS			 read-only
		STATUS					 current
		DESCRIPTION			 " -- "
		::=  { sfn7avgripEntry  87 }


	plsfn7Prb85RIPAvg		 OBJECT-TYPE
		SYNTAX					 Integer32( -2147483648 .. 2147483647 )
		MAX-ACCESS			 read-only
		STATUS					 current
		DESCRIPTION			 " -- "
		::=  { sfn7avgripEntry  88 }


	plsfn7Prb86RIPAvg		 OBJECT-TYPE
		SYNTAX					 Integer32( -2147483648 .. 2147483647 )
		MAX-ACCESS			 read-only
		STATUS					 current
		DESCRIPTION			 " -- "
		::=  { sfn7avgripEntry  89 }


	plsfn7Prb87RIPAvg		 OBJECT-TYPE
		SYNTAX					 Integer32( -2147483648 .. 2147483647 )
		MAX-ACCESS			 read-only
		STATUS					 current
		DESCRIPTION			 " -- "
		::=  { sfn7avgripEntry  90 }


	plsfn7Prb88RIPAvg		 OBJECT-TYPE
		SYNTAX					 Integer32( -2147483648 .. 2147483647 )
		MAX-ACCESS			 read-only
		STATUS					 current
		DESCRIPTION			 " -- "
		::=  { sfn7avgripEntry  91 }


	plsfn7Prb89RIPAvg		 OBJECT-TYPE
		SYNTAX					 Integer32( -2147483648 .. 2147483647 )
		MAX-ACCESS			 read-only
		STATUS					 current
		DESCRIPTION			 " -- "
		::=  { sfn7avgripEntry  92 }


	plsfn7Prb90RIPAvg		 OBJECT-TYPE
		SYNTAX					 Integer32( -2147483648 .. 2147483647 )
		MAX-ACCESS			 read-only
		STATUS					 current
		DESCRIPTION			 " -- "
		::=  { sfn7avgripEntry  93 }


	plsfn7Prb91RIPAvg		 OBJECT-TYPE
		SYNTAX					 Integer32( -2147483648 .. 2147483647 )
		MAX-ACCESS			 read-only
		STATUS					 current
		DESCRIPTION			 " -- "
		::=  { sfn7avgripEntry  94 }


	plsfn7Prb92RIPAvg		 OBJECT-TYPE
		SYNTAX					 Integer32( -2147483648 .. 2147483647 )
		MAX-ACCESS			 read-only
		STATUS					 current
		DESCRIPTION			 " -- "
		::=  { sfn7avgripEntry  95 }


	plsfn7Prb93RIPAvg		 OBJECT-TYPE
		SYNTAX					 Integer32( -2147483648 .. 2147483647 )
		MAX-ACCESS			 read-only
		STATUS					 current
		DESCRIPTION			 " -- "
		::=  { sfn7avgripEntry  96 }


	plsfn7Prb94RIPAvg		 OBJECT-TYPE
		SYNTAX					 Integer32( -2147483648 .. 2147483647 )
		MAX-ACCESS			 read-only
		STATUS					 current
		DESCRIPTION			 " -- "
		::=  { sfn7avgripEntry  97 }


	plsfn7Prb95RIPAvg		 OBJECT-TYPE
		SYNTAX					 Integer32( -2147483648 .. 2147483647 )
		MAX-ACCESS			 read-only
		STATUS					 current
		DESCRIPTION			 " -- "
		::=  { sfn7avgripEntry  98 }


	plsfn7Prb96RIPAvg		 OBJECT-TYPE
		SYNTAX					 Integer32( -2147483648 .. 2147483647 )
		MAX-ACCESS			 read-only
		STATUS					 current
		DESCRIPTION			 " -- "
		::=  { sfn7avgripEntry  99 }


	plsfn7Prb97RIPAvg		 OBJECT-TYPE
		SYNTAX					 Integer32( -2147483648 .. 2147483647 )
		MAX-ACCESS			 read-only
		STATUS					 current
		DESCRIPTION			 " -- "
		::=  { sfn7avgripEntry  100 }


	plsfn7Prb98RIPAvg		 OBJECT-TYPE
		SYNTAX					 Integer32( -2147483648 .. 2147483647 )
		MAX-ACCESS			 read-only
		STATUS					 current
		DESCRIPTION			 " -- "
		::=  { sfn7avgripEntry  101 }


	plsfn7Prb99RIPAvg		 OBJECT-TYPE
		SYNTAX					 Integer32( -2147483648 .. 2147483647 )
		MAX-ACCESS			 read-only
		STATUS					 current
		DESCRIPTION			 " -- "
		::=  { sfn7avgripEntry  102 }


	sfn7maxripTable		 OBJECT-TYPE
		SYNTAX					 SEQUENCE  OF	 Sfn7maxripEntry
		MAX-ACCESS			 not-accessible
		STATUS					 current
		DESCRIPTION			 " -- "
		::=  { plrelatedOriginCounter  13 }


	sfn7maxripEntry		 OBJECT-TYPE
		SYNTAX					 Sfn7maxripEntry
		MAX-ACCESS			 not-accessible
		STATUS					 current
		DESCRIPTION			 " -- "
		INDEX						{ sfn7maxripLcId }
		::=  { sfn7maxripTable  1 }


	Sfn7maxripEntry		 ::=  SEQUENCE {
		sfn7maxripLcId					Integer32,
		sfn7maxripRowStatus					RowStatus,
		plsfn7PrbG1RIPMax					Integer32,
		plsfn7PrbG2RIPMax					Integer32,
		plsfn7PrbG3RIPMax					Integer32,
		plsfn7PrbG4RIPMax					Integer32,
		plsfn7PrbG5RIPMax					Integer32,
		plsfn7PrbG6RIPMax					Integer32,
		plsfn7PrbG7RIPMax					Integer32,
		plsfn7PrbG8RIPMax					Integer32,
		plsfn7PrbG9RIPMax					Integer32,
		plsfn7PrbG10RIPMax					Integer32,
		plsfn7PrbG11RIPMax					Integer32,
		plsfn7PrbG12RIPMax					Integer32,
		plsfn7PrbG13RIPMax					Integer32,
		plsfn7PrbG14RIPMax					Integer32,
		plsfn7PrbG15RIPMax					Integer32,
		plsfn7PrbG16RIPMax					Integer32,
		plsfn7PrbG17RIPMax					Integer32,
		plsfn7PrbG18RIPMax					Integer32,
		plsfn7PrbG19RIPMax					Integer32,
		plsfn7PrbG20RIPMax					Integer32
		}


	sfn7maxripLcId		 OBJECT-TYPE
		SYNTAX					 Integer32( 0 .. 23 )
		MAX-ACCESS			 not-accessible
		STATUS					 current
		DESCRIPTION			 " -- "
		::=  { sfn7maxripEntry  1 }


	sfn7maxripRowStatus		 OBJECT-TYPE
		SYNTAX					 RowStatus
		MAX-ACCESS			 read-only
		STATUS					 current
		DESCRIPTION			 " -- "
		::=  { sfn7maxripEntry  2 }


	plsfn7PrbG1RIPMax		 OBJECT-TYPE
		SYNTAX					 Integer32( -2147483648 .. 2147483647 )
		MAX-ACCESS			 read-only
		STATUS					 current
		DESCRIPTION			 " -- "
		::=  { sfn7maxripEntry  3 }


	plsfn7PrbG2RIPMax		 OBJECT-TYPE
		SYNTAX					 Integer32( -2147483648 .. 2147483647 )
		MAX-ACCESS			 read-only
		STATUS					 current
		DESCRIPTION			 " -- "
		::=  { sfn7maxripEntry  4 }


	plsfn7PrbG3RIPMax		 OBJECT-TYPE
		SYNTAX					 Integer32( -2147483648 .. 2147483647 )
		MAX-ACCESS			 read-only
		STATUS					 current
		DESCRIPTION			 " -- "
		::=  { sfn7maxripEntry  5 }


	plsfn7PrbG4RIPMax		 OBJECT-TYPE
		SYNTAX					 Integer32( -2147483648 .. 2147483647 )
		MAX-ACCESS			 read-only
		STATUS					 current
		DESCRIPTION			 " -- "
		::=  { sfn7maxripEntry  6 }


	plsfn7PrbG5RIPMax		 OBJECT-TYPE
		SYNTAX					 Integer32( -2147483648 .. 2147483647 )
		MAX-ACCESS			 read-only
		STATUS					 current
		DESCRIPTION			 " -- "
		::=  { sfn7maxripEntry  7 }


	plsfn7PrbG6RIPMax		 OBJECT-TYPE
		SYNTAX					 Integer32( -2147483648 .. 2147483647 )
		MAX-ACCESS			 read-only
		STATUS					 current
		DESCRIPTION			 " -- "
		::=  { sfn7maxripEntry  8 }


	plsfn7PrbG7RIPMax		 OBJECT-TYPE
		SYNTAX					 Integer32( -2147483648 .. 2147483647 )
		MAX-ACCESS			 read-only
		STATUS					 current
		DESCRIPTION			 " -- "
		::=  { sfn7maxripEntry  9 }


	plsfn7PrbG8RIPMax		 OBJECT-TYPE
		SYNTAX					 Integer32( -2147483648 .. 2147483647 )
		MAX-ACCESS			 read-only
		STATUS					 current
		DESCRIPTION			 " -- "
		::=  { sfn7maxripEntry  10 }


	plsfn7PrbG9RIPMax		 OBJECT-TYPE
		SYNTAX					 Integer32( -2147483648 .. 2147483647 )
		MAX-ACCESS			 read-only
		STATUS					 current
		DESCRIPTION			 " -- "
		::=  { sfn7maxripEntry  11 }


	plsfn7PrbG10RIPMax		 OBJECT-TYPE
		SYNTAX					 Integer32( -2147483648 .. 2147483647 )
		MAX-ACCESS			 read-only
		STATUS					 current
		DESCRIPTION			 " -- "
		::=  { sfn7maxripEntry  12 }


	plsfn7PrbG11RIPMax		 OBJECT-TYPE
		SYNTAX					 Integer32( -2147483648 .. 2147483647 )
		MAX-ACCESS			 read-only
		STATUS					 current
		DESCRIPTION			 " -- "
		::=  { sfn7maxripEntry  13 }


	plsfn7PrbG12RIPMax		 OBJECT-TYPE
		SYNTAX					 Integer32( -2147483648 .. 2147483647 )
		MAX-ACCESS			 read-only
		STATUS					 current
		DESCRIPTION			 " -- "
		::=  { sfn7maxripEntry  14 }


	plsfn7PrbG13RIPMax		 OBJECT-TYPE
		SYNTAX					 Integer32( -2147483648 .. 2147483647 )
		MAX-ACCESS			 read-only
		STATUS					 current
		DESCRIPTION			 " -- "
		::=  { sfn7maxripEntry  15 }


	plsfn7PrbG14RIPMax		 OBJECT-TYPE
		SYNTAX					 Integer32( -2147483648 .. 2147483647 )
		MAX-ACCESS			 read-only
		STATUS					 current
		DESCRIPTION			 " -- "
		::=  { sfn7maxripEntry  16 }


	plsfn7PrbG15RIPMax		 OBJECT-TYPE
		SYNTAX					 Integer32( -2147483648 .. 2147483647 )
		MAX-ACCESS			 read-only
		STATUS					 current
		DESCRIPTION			 " -- "
		::=  { sfn7maxripEntry  17 }


	plsfn7PrbG16RIPMax		 OBJECT-TYPE
		SYNTAX					 Integer32( -2147483648 .. 2147483647 )
		MAX-ACCESS			 read-only
		STATUS					 current
		DESCRIPTION			 " -- "
		::=  { sfn7maxripEntry  18 }


	plsfn7PrbG17RIPMax		 OBJECT-TYPE
		SYNTAX					 Integer32( -2147483648 .. 2147483647 )
		MAX-ACCESS			 read-only
		STATUS					 current
		DESCRIPTION			 " -- "
		::=  { sfn7maxripEntry  19 }


	plsfn7PrbG18RIPMax		 OBJECT-TYPE
		SYNTAX					 Integer32( -2147483648 .. 2147483647 )
		MAX-ACCESS			 read-only
		STATUS					 current
		DESCRIPTION			 " -- "
		::=  { sfn7maxripEntry  20 }


	plsfn7PrbG19RIPMax		 OBJECT-TYPE
		SYNTAX					 Integer32( -2147483648 .. 2147483647 )
		MAX-ACCESS			 read-only
		STATUS					 current
		DESCRIPTION			 " -- "
		::=  { sfn7maxripEntry  21 }


	plsfn7PrbG20RIPMax		 OBJECT-TYPE
		SYNTAX					 Integer32( -2147483648 .. 2147483647 )
		MAX-ACCESS			 read-only
		STATUS					 current
		DESCRIPTION			 " -- "
		::=  { sfn7maxripEntry  22 }


	sfn8avgripTable		 OBJECT-TYPE
		SYNTAX					 SEQUENCE  OF	 Sfn8avgripEntry
		MAX-ACCESS			 not-accessible
		STATUS					 current
		DESCRIPTION			 " -- "
		::=  { plrelatedOriginCounter  14 }


	sfn8avgripEntry		 OBJECT-TYPE
		SYNTAX					 Sfn8avgripEntry
		MAX-ACCESS			 not-accessible
		STATUS					 current
		DESCRIPTION			 " -- "
		INDEX						{ sfn8avgripLcId }
		::=  { sfn8avgripTable  1 }


	Sfn8avgripEntry		 ::=  SEQUENCE {
		sfn8avgripLcId					Integer32,
		sfn8avgripRowStatus					RowStatus,
		plsfn8Prb00RIPAvg					Integer32,
		plsfn8Prb01RIPAvg					Integer32,
		plsfn8Prb02RIPAvg					Integer32,
		plsfn8Prb03RIPAvg					Integer32,
		plsfn8Prb04RIPAvg					Integer32,
		plsfn8Prb05RIPAvg					Integer32,
		plsfn8Prb06RIPAvg					Integer32,
		plsfn8Prb07RIPAvg					Integer32,
		plsfn8Prb08RIPAvg					Integer32,
		plsfn8Prb09RIPAvg					Integer32,
		plsfn8Prb10RIPAvg					Integer32,
		plsfn8Prb11RIPAvg					Integer32,
		plsfn8Prb12RIPAvg					Integer32,
		plsfn8Prb13RIPAvg					Integer32,
		plsfn8Prb14RIPAvg					Integer32,
		plsfn8Prb15RIPAvg					Integer32,
		plsfn8Prb16RIPAvg					Integer32,
		plsfn8Prb17RIPAvg					Integer32,
		plsfn8Prb18RIPAvg					Integer32,
		plsfn8Prb19RIPAvg					Integer32,
		plsfn8Prb20RIPAvg					Integer32,
		plsfn8Prb21RIPAvg					Integer32,
		plsfn8Prb22RIPAvg					Integer32,
		plsfn8Prb23RIPAvg					Integer32,
		plsfn8Prb24RIPAvg					Integer32,
		plsfn8Prb25RIPAvg					Integer32,
		plsfn8Prb26RIPAvg					Integer32,
		plsfn8Prb27RIPAvg					Integer32,
		plsfn8Prb28RIPAvg					Integer32,
		plsfn8Prb29RIPAvg					Integer32,
		plsfn8Prb30RIPAvg					Integer32,
		plsfn8Prb31RIPAvg					Integer32,
		plsfn8Prb32RIPAvg					Integer32,
		plsfn8Prb33RIPAvg					Integer32,
		plsfn8Prb34RIPAvg					Integer32,
		plsfn8Prb35RIPAvg					Integer32,
		plsfn8Prb36RIPAvg					Integer32,
		plsfn8Prb37RIPAvg					Integer32,
		plsfn8Prb38RIPAvg					Integer32,
		plsfn8Prb39RIPAvg					Integer32,
		plsfn8Prb40RIPAvg					Integer32,
		plsfn8Prb41RIPAvg					Integer32,
		plsfn8Prb42RIPAvg					Integer32,
		plsfn8Prb43RIPAvg					Integer32,
		plsfn8Prb44RIPAvg					Integer32,
		plsfn8Prb45RIPAvg					Integer32,
		plsfn8Prb46RIPAvg					Integer32,
		plsfn8Prb47RIPAvg					Integer32,
		plsfn8Prb48RIPAvg					Integer32,
		plsfn8Prb49RIPAvg					Integer32,
		plsfn8Prb50RIPAvg					Integer32,
		plsfn8Prb51RIPAvg					Integer32,
		plsfn8Prb52RIPAvg					Integer32,
		plsfn8Prb53RIPAvg					Integer32,
		plsfn8Prb54RIPAvg					Integer32,
		plsfn8Prb55RIPAvg					Integer32,
		plsfn8Prb56RIPAvg					Integer32,
		plsfn8Prb57RIPAvg					Integer32,
		plsfn8Prb58RIPAvg					Integer32,
		plsfn8Prb59RIPAvg					Integer32,
		plsfn8Prb60RIPAvg					Integer32,
		plsfn8Prb61RIPAvg					Integer32,
		plsfn8Prb62RIPAvg					Integer32,
		plsfn8Prb63RIPAvg					Integer32,
		plsfn8Prb64RIPAvg					Integer32,
		plsfn8Prb65RIPAvg					Integer32,
		plsfn8Prb66RIPAvg					Integer32,
		plsfn8Prb67RIPAvg					Integer32,
		plsfn8Prb68RIPAvg					Integer32,
		plsfn8Prb69RIPAvg					Integer32,
		plsfn8Prb70RIPAvg					Integer32,
		plsfn8Prb71RIPAvg					Integer32,
		plsfn8Prb72RIPAvg					Integer32,
		plsfn8Prb73RIPAvg					Integer32,
		plsfn8Prb74RIPAvg					Integer32,
		plsfn8Prb75RIPAvg					Integer32,
		plsfn8Prb76RIPAvg					Integer32,
		plsfn8Prb77RIPAvg					Integer32,
		plsfn8Prb78RIPAvg					Integer32,
		plsfn8Prb79RIPAvg					Integer32,
		plsfn8Prb80RIPAvg					Integer32,
		plsfn8Prb81RIPAvg					Integer32,
		plsfn8Prb82RIPAvg					Integer32,
		plsfn8Prb83RIPAvg					Integer32,
		plsfn8Prb84RIPAvg					Integer32,
		plsfn8Prb85RIPAvg					Integer32,
		plsfn8Prb86RIPAvg					Integer32,
		plsfn8Prb87RIPAvg					Integer32,
		plsfn8Prb88RIPAvg					Integer32,
		plsfn8Prb89RIPAvg					Integer32,
		plsfn8Prb90RIPAvg					Integer32,
		plsfn8Prb91RIPAvg					Integer32,
		plsfn8Prb92RIPAvg					Integer32,
		plsfn8Prb93RIPAvg					Integer32,
		plsfn8Prb94RIPAvg					Integer32,
		plsfn8Prb95RIPAvg					Integer32,
		plsfn8Prb96RIPAvg					Integer32,
		plsfn8Prb97RIPAvg					Integer32,
		plsfn8Prb98RIPAvg					Integer32,
		plsfn8Prb99RIPAvg					Integer32
		}


	sfn8avgripLcId		 OBJECT-TYPE
		SYNTAX					 Integer32( 0 .. 23 )
		MAX-ACCESS			 not-accessible
		STATUS					 current
		DESCRIPTION			 " -- "
		::=  { sfn8avgripEntry  1 }


	sfn8avgripRowStatus		 OBJECT-TYPE
		SYNTAX					 RowStatus
		MAX-ACCESS			 read-only
		STATUS					 current
		DESCRIPTION			 " -- "
		::=  { sfn8avgripEntry  2 }


	plsfn8Prb00RIPAvg		 OBJECT-TYPE
		SYNTAX					 Integer32( -2147483648 .. 2147483647 )
		MAX-ACCESS			 read-only
		STATUS					 current
		DESCRIPTION			 " -- "
		::=  { sfn8avgripEntry  3 }


	plsfn8Prb01RIPAvg		 OBJECT-TYPE
		SYNTAX					 Integer32( -2147483648 .. 2147483647 )
		MAX-ACCESS			 read-only
		STATUS					 current
		DESCRIPTION			 " -- "
		::=  { sfn8avgripEntry  4 }


	plsfn8Prb02RIPAvg		 OBJECT-TYPE
		SYNTAX					 Integer32( -2147483648 .. 2147483647 )
		MAX-ACCESS			 read-only
		STATUS					 current
		DESCRIPTION			 " -- "
		::=  { sfn8avgripEntry  5 }


	plsfn8Prb03RIPAvg		 OBJECT-TYPE
		SYNTAX					 Integer32( -2147483648 .. 2147483647 )
		MAX-ACCESS			 read-only
		STATUS					 current
		DESCRIPTION			 " -- "
		::=  { sfn8avgripEntry  6 }


	plsfn8Prb04RIPAvg		 OBJECT-TYPE
		SYNTAX					 Integer32( -2147483648 .. 2147483647 )
		MAX-ACCESS			 read-only
		STATUS					 current
		DESCRIPTION			 " -- "
		::=  { sfn8avgripEntry  7 }


	plsfn8Prb05RIPAvg		 OBJECT-TYPE
		SYNTAX					 Integer32( -2147483648 .. 2147483647 )
		MAX-ACCESS			 read-only
		STATUS					 current
		DESCRIPTION			 " -- "
		::=  { sfn8avgripEntry  8 }


	plsfn8Prb06RIPAvg		 OBJECT-TYPE
		SYNTAX					 Integer32( -2147483648 .. 2147483647 )
		MAX-ACCESS			 read-only
		STATUS					 current
		DESCRIPTION			 " -- "
		::=  { sfn8avgripEntry  9 }


	plsfn8Prb07RIPAvg		 OBJECT-TYPE
		SYNTAX					 Integer32( -2147483648 .. 2147483647 )
		MAX-ACCESS			 read-only
		STATUS					 current
		DESCRIPTION			 " -- "
		::=  { sfn8avgripEntry  10 }


	plsfn8Prb08RIPAvg		 OBJECT-TYPE
		SYNTAX					 Integer32( -2147483648 .. 2147483647 )
		MAX-ACCESS			 read-only
		STATUS					 current
		DESCRIPTION			 " -- "
		::=  { sfn8avgripEntry  11 }


	plsfn8Prb09RIPAvg		 OBJECT-TYPE
		SYNTAX					 Integer32( -2147483648 .. 2147483647 )
		MAX-ACCESS			 read-only
		STATUS					 current
		DESCRIPTION			 " -- "
		::=  { sfn8avgripEntry  12 }


	plsfn8Prb10RIPAvg		 OBJECT-TYPE
		SYNTAX					 Integer32( -2147483648 .. 2147483647 )
		MAX-ACCESS			 read-only
		STATUS					 current
		DESCRIPTION			 " -- "
		::=  { sfn8avgripEntry  13 }


	plsfn8Prb11RIPAvg		 OBJECT-TYPE
		SYNTAX					 Integer32( -2147483648 .. 2147483647 )
		MAX-ACCESS			 read-only
		STATUS					 current
		DESCRIPTION			 " -- "
		::=  { sfn8avgripEntry  14 }


	plsfn8Prb12RIPAvg		 OBJECT-TYPE
		SYNTAX					 Integer32( -2147483648 .. 2147483647 )
		MAX-ACCESS			 read-only
		STATUS					 current
		DESCRIPTION			 " -- "
		::=  { sfn8avgripEntry  15 }


	plsfn8Prb13RIPAvg		 OBJECT-TYPE
		SYNTAX					 Integer32( -2147483648 .. 2147483647 )
		MAX-ACCESS			 read-only
		STATUS					 current
		DESCRIPTION			 " -- "
		::=  { sfn8avgripEntry  16 }


	plsfn8Prb14RIPAvg		 OBJECT-TYPE
		SYNTAX					 Integer32( -2147483648 .. 2147483647 )
		MAX-ACCESS			 read-only
		STATUS					 current
		DESCRIPTION			 " -- "
		::=  { sfn8avgripEntry  17 }


	plsfn8Prb15RIPAvg		 OBJECT-TYPE
		SYNTAX					 Integer32( -2147483648 .. 2147483647 )
		MAX-ACCESS			 read-only
		STATUS					 current
		DESCRIPTION			 " -- "
		::=  { sfn8avgripEntry  18 }


	plsfn8Prb16RIPAvg		 OBJECT-TYPE
		SYNTAX					 Integer32( -2147483648 .. 2147483647 )
		MAX-ACCESS			 read-only
		STATUS					 current
		DESCRIPTION			 " -- "
		::=  { sfn8avgripEntry  19 }


	plsfn8Prb17RIPAvg		 OBJECT-TYPE
		SYNTAX					 Integer32( -2147483648 .. 2147483647 )
		MAX-ACCESS			 read-only
		STATUS					 current
		DESCRIPTION			 " -- "
		::=  { sfn8avgripEntry  20 }


	plsfn8Prb18RIPAvg		 OBJECT-TYPE
		SYNTAX					 Integer32( -2147483648 .. 2147483647 )
		MAX-ACCESS			 read-only
		STATUS					 current
		DESCRIPTION			 " -- "
		::=  { sfn8avgripEntry  21 }


	plsfn8Prb19RIPAvg		 OBJECT-TYPE
		SYNTAX					 Integer32( -2147483648 .. 2147483647 )
		MAX-ACCESS			 read-only
		STATUS					 current
		DESCRIPTION			 " -- "
		::=  { sfn8avgripEntry  22 }


	plsfn8Prb20RIPAvg		 OBJECT-TYPE
		SYNTAX					 Integer32( -2147483648 .. 2147483647 )
		MAX-ACCESS			 read-only
		STATUS					 current
		DESCRIPTION			 " -- "
		::=  { sfn8avgripEntry  23 }


	plsfn8Prb21RIPAvg		 OBJECT-TYPE
		SYNTAX					 Integer32( -2147483648 .. 2147483647 )
		MAX-ACCESS			 read-only
		STATUS					 current
		DESCRIPTION			 " -- "
		::=  { sfn8avgripEntry  24 }


	plsfn8Prb22RIPAvg		 OBJECT-TYPE
		SYNTAX					 Integer32( -2147483648 .. 2147483647 )
		MAX-ACCESS			 read-only
		STATUS					 current
		DESCRIPTION			 " -- "
		::=  { sfn8avgripEntry  25 }


	plsfn8Prb23RIPAvg		 OBJECT-TYPE
		SYNTAX					 Integer32( -2147483648 .. 2147483647 )
		MAX-ACCESS			 read-only
		STATUS					 current
		DESCRIPTION			 " -- "
		::=  { sfn8avgripEntry  26 }


	plsfn8Prb24RIPAvg		 OBJECT-TYPE
		SYNTAX					 Integer32( -2147483648 .. 2147483647 )
		MAX-ACCESS			 read-only
		STATUS					 current
		DESCRIPTION			 " -- "
		::=  { sfn8avgripEntry  27 }


	plsfn8Prb25RIPAvg		 OBJECT-TYPE
		SYNTAX					 Integer32( -2147483648 .. 2147483647 )
		MAX-ACCESS			 read-only
		STATUS					 current
		DESCRIPTION			 " -- "
		::=  { sfn8avgripEntry  28 }


	plsfn8Prb26RIPAvg		 OBJECT-TYPE
		SYNTAX					 Integer32( -2147483648 .. 2147483647 )
		MAX-ACCESS			 read-only
		STATUS					 current
		DESCRIPTION			 " -- "
		::=  { sfn8avgripEntry  29 }


	plsfn8Prb27RIPAvg		 OBJECT-TYPE
		SYNTAX					 Integer32( -2147483648 .. 2147483647 )
		MAX-ACCESS			 read-only
		STATUS					 current
		DESCRIPTION			 " -- "
		::=  { sfn8avgripEntry  30 }


	plsfn8Prb28RIPAvg		 OBJECT-TYPE
		SYNTAX					 Integer32( -2147483648 .. 2147483647 )
		MAX-ACCESS			 read-only
		STATUS					 current
		DESCRIPTION			 " -- "
		::=  { sfn8avgripEntry  31 }


	plsfn8Prb29RIPAvg		 OBJECT-TYPE
		SYNTAX					 Integer32( -2147483648 .. 2147483647 )
		MAX-ACCESS			 read-only
		STATUS					 current
		DESCRIPTION			 " -- "
		::=  { sfn8avgripEntry  32 }


	plsfn8Prb30RIPAvg		 OBJECT-TYPE
		SYNTAX					 Integer32( -2147483648 .. 2147483647 )
		MAX-ACCESS			 read-only
		STATUS					 current
		DESCRIPTION			 " -- "
		::=  { sfn8avgripEntry  33 }


	plsfn8Prb31RIPAvg		 OBJECT-TYPE
		SYNTAX					 Integer32( -2147483648 .. 2147483647 )
		MAX-ACCESS			 read-only
		STATUS					 current
		DESCRIPTION			 " -- "
		::=  { sfn8avgripEntry  34 }


	plsfn8Prb32RIPAvg		 OBJECT-TYPE
		SYNTAX					 Integer32( -2147483648 .. 2147483647 )
		MAX-ACCESS			 read-only
		STATUS					 current
		DESCRIPTION			 " -- "
		::=  { sfn8avgripEntry  35 }


	plsfn8Prb33RIPAvg		 OBJECT-TYPE
		SYNTAX					 Integer32( -2147483648 .. 2147483647 )
		MAX-ACCESS			 read-only
		STATUS					 current
		DESCRIPTION			 " -- "
		::=  { sfn8avgripEntry  36 }


	plsfn8Prb34RIPAvg		 OBJECT-TYPE
		SYNTAX					 Integer32( -2147483648 .. 2147483647 )
		MAX-ACCESS			 read-only
		STATUS					 current
		DESCRIPTION			 " -- "
		::=  { sfn8avgripEntry  37 }


	plsfn8Prb35RIPAvg		 OBJECT-TYPE
		SYNTAX					 Integer32( -2147483648 .. 2147483647 )
		MAX-ACCESS			 read-only
		STATUS					 current
		DESCRIPTION			 " -- "
		::=  { sfn8avgripEntry  38 }


	plsfn8Prb36RIPAvg		 OBJECT-TYPE
		SYNTAX					 Integer32( -2147483648 .. 2147483647 )
		MAX-ACCESS			 read-only
		STATUS					 current
		DESCRIPTION			 " -- "
		::=  { sfn8avgripEntry  39 }


	plsfn8Prb37RIPAvg		 OBJECT-TYPE
		SYNTAX					 Integer32( -2147483648 .. 2147483647 )
		MAX-ACCESS			 read-only
		STATUS					 current
		DESCRIPTION			 " -- "
		::=  { sfn8avgripEntry  40 }


	plsfn8Prb38RIPAvg		 OBJECT-TYPE
		SYNTAX					 Integer32( -2147483648 .. 2147483647 )
		MAX-ACCESS			 read-only
		STATUS					 current
		DESCRIPTION			 " -- "
		::=  { sfn8avgripEntry  41 }


	plsfn8Prb39RIPAvg		 OBJECT-TYPE
		SYNTAX					 Integer32( -2147483648 .. 2147483647 )
		MAX-ACCESS			 read-only
		STATUS					 current
		DESCRIPTION			 " -- "
		::=  { sfn8avgripEntry  42 }


	plsfn8Prb40RIPAvg		 OBJECT-TYPE
		SYNTAX					 Integer32( -2147483648 .. 2147483647 )
		MAX-ACCESS			 read-only
		STATUS					 current
		DESCRIPTION			 " -- "
		::=  { sfn8avgripEntry  43 }


	plsfn8Prb41RIPAvg		 OBJECT-TYPE
		SYNTAX					 Integer32( -2147483648 .. 2147483647 )
		MAX-ACCESS			 read-only
		STATUS					 current
		DESCRIPTION			 " -- "
		::=  { sfn8avgripEntry  44 }


	plsfn8Prb42RIPAvg		 OBJECT-TYPE
		SYNTAX					 Integer32( -2147483648 .. 2147483647 )
		MAX-ACCESS			 read-only
		STATUS					 current
		DESCRIPTION			 " -- "
		::=  { sfn8avgripEntry  45 }


	plsfn8Prb43RIPAvg		 OBJECT-TYPE
		SYNTAX					 Integer32( -2147483648 .. 2147483647 )
		MAX-ACCESS			 read-only
		STATUS					 current
		DESCRIPTION			 " -- "
		::=  { sfn8avgripEntry  46 }


	plsfn8Prb44RIPAvg		 OBJECT-TYPE
		SYNTAX					 Integer32( -2147483648 .. 2147483647 )
		MAX-ACCESS			 read-only
		STATUS					 current
		DESCRIPTION			 " -- "
		::=  { sfn8avgripEntry  47 }


	plsfn8Prb45RIPAvg		 OBJECT-TYPE
		SYNTAX					 Integer32( -2147483648 .. 2147483647 )
		MAX-ACCESS			 read-only
		STATUS					 current
		DESCRIPTION			 " -- "
		::=  { sfn8avgripEntry  48 }


	plsfn8Prb46RIPAvg		 OBJECT-TYPE
		SYNTAX					 Integer32( -2147483648 .. 2147483647 )
		MAX-ACCESS			 read-only
		STATUS					 current
		DESCRIPTION			 " -- "
		::=  { sfn8avgripEntry  49 }


	plsfn8Prb47RIPAvg		 OBJECT-TYPE
		SYNTAX					 Integer32( -2147483648 .. 2147483647 )
		MAX-ACCESS			 read-only
		STATUS					 current
		DESCRIPTION			 " -- "
		::=  { sfn8avgripEntry  50 }


	plsfn8Prb48RIPAvg		 OBJECT-TYPE
		SYNTAX					 Integer32( -2147483648 .. 2147483647 )
		MAX-ACCESS			 read-only
		STATUS					 current
		DESCRIPTION			 " -- "
		::=  { sfn8avgripEntry  51 }


	plsfn8Prb49RIPAvg		 OBJECT-TYPE
		SYNTAX					 Integer32( -2147483648 .. 2147483647 )
		MAX-ACCESS			 read-only
		STATUS					 current
		DESCRIPTION			 " -- "
		::=  { sfn8avgripEntry  52 }


	plsfn8Prb50RIPAvg		 OBJECT-TYPE
		SYNTAX					 Integer32( -2147483648 .. 2147483647 )
		MAX-ACCESS			 read-only
		STATUS					 current
		DESCRIPTION			 " -- "
		::=  { sfn8avgripEntry  53 }


	plsfn8Prb51RIPAvg		 OBJECT-TYPE
		SYNTAX					 Integer32( -2147483648 .. 2147483647 )
		MAX-ACCESS			 read-only
		STATUS					 current
		DESCRIPTION			 " -- "
		::=  { sfn8avgripEntry  54 }


	plsfn8Prb52RIPAvg		 OBJECT-TYPE
		SYNTAX					 Integer32( -2147483648 .. 2147483647 )
		MAX-ACCESS			 read-only
		STATUS					 current
		DESCRIPTION			 " -- "
		::=  { sfn8avgripEntry  55 }


	plsfn8Prb53RIPAvg		 OBJECT-TYPE
		SYNTAX					 Integer32( -2147483648 .. 2147483647 )
		MAX-ACCESS			 read-only
		STATUS					 current
		DESCRIPTION			 " -- "
		::=  { sfn8avgripEntry  56 }


	plsfn8Prb54RIPAvg		 OBJECT-TYPE
		SYNTAX					 Integer32( -2147483648 .. 2147483647 )
		MAX-ACCESS			 read-only
		STATUS					 current
		DESCRIPTION			 " -- "
		::=  { sfn8avgripEntry  57 }


	plsfn8Prb55RIPAvg		 OBJECT-TYPE
		SYNTAX					 Integer32( -2147483648 .. 2147483647 )
		MAX-ACCESS			 read-only
		STATUS					 current
		DESCRIPTION			 " -- "
		::=  { sfn8avgripEntry  58 }


	plsfn8Prb56RIPAvg		 OBJECT-TYPE
		SYNTAX					 Integer32( -2147483648 .. 2147483647 )
		MAX-ACCESS			 read-only
		STATUS					 current
		DESCRIPTION			 " -- "
		::=  { sfn8avgripEntry  59 }


	plsfn8Prb57RIPAvg		 OBJECT-TYPE
		SYNTAX					 Integer32( -2147483648 .. 2147483647 )
		MAX-ACCESS			 read-only
		STATUS					 current
		DESCRIPTION			 " -- "
		::=  { sfn8avgripEntry  60 }


	plsfn8Prb58RIPAvg		 OBJECT-TYPE
		SYNTAX					 Integer32( -2147483648 .. 2147483647 )
		MAX-ACCESS			 read-only
		STATUS					 current
		DESCRIPTION			 " -- "
		::=  { sfn8avgripEntry  61 }


	plsfn8Prb59RIPAvg		 OBJECT-TYPE
		SYNTAX					 Integer32( -2147483648 .. 2147483647 )
		MAX-ACCESS			 read-only
		STATUS					 current
		DESCRIPTION			 " -- "
		::=  { sfn8avgripEntry  62 }


	plsfn8Prb60RIPAvg		 OBJECT-TYPE
		SYNTAX					 Integer32( -2147483648 .. 2147483647 )
		MAX-ACCESS			 read-only
		STATUS					 current
		DESCRIPTION			 " -- "
		::=  { sfn8avgripEntry  63 }


	plsfn8Prb61RIPAvg		 OBJECT-TYPE
		SYNTAX					 Integer32( -2147483648 .. 2147483647 )
		MAX-ACCESS			 read-only
		STATUS					 current
		DESCRIPTION			 " -- "
		::=  { sfn8avgripEntry  64 }


	plsfn8Prb62RIPAvg		 OBJECT-TYPE
		SYNTAX					 Integer32( -2147483648 .. 2147483647 )
		MAX-ACCESS			 read-only
		STATUS					 current
		DESCRIPTION			 " -- "
		::=  { sfn8avgripEntry  65 }


	plsfn8Prb63RIPAvg		 OBJECT-TYPE
		SYNTAX					 Integer32( -2147483648 .. 2147483647 )
		MAX-ACCESS			 read-only
		STATUS					 current
		DESCRIPTION			 " -- "
		::=  { sfn8avgripEntry  66 }


	plsfn8Prb64RIPAvg		 OBJECT-TYPE
		SYNTAX					 Integer32( -2147483648 .. 2147483647 )
		MAX-ACCESS			 read-only
		STATUS					 current
		DESCRIPTION			 " -- "
		::=  { sfn8avgripEntry  67 }


	plsfn8Prb65RIPAvg		 OBJECT-TYPE
		SYNTAX					 Integer32( -2147483648 .. 2147483647 )
		MAX-ACCESS			 read-only
		STATUS					 current
		DESCRIPTION			 " -- "
		::=  { sfn8avgripEntry  68 }


	plsfn8Prb66RIPAvg		 OBJECT-TYPE
		SYNTAX					 Integer32( -2147483648 .. 2147483647 )
		MAX-ACCESS			 read-only
		STATUS					 current
		DESCRIPTION			 " -- "
		::=  { sfn8avgripEntry  69 }


	plsfn8Prb67RIPAvg		 OBJECT-TYPE
		SYNTAX					 Integer32( -2147483648 .. 2147483647 )
		MAX-ACCESS			 read-only
		STATUS					 current
		DESCRIPTION			 " -- "
		::=  { sfn8avgripEntry  70 }


	plsfn8Prb68RIPAvg		 OBJECT-TYPE
		SYNTAX					 Integer32( -2147483648 .. 2147483647 )
		MAX-ACCESS			 read-only
		STATUS					 current
		DESCRIPTION			 " -- "
		::=  { sfn8avgripEntry  71 }


	plsfn8Prb69RIPAvg		 OBJECT-TYPE
		SYNTAX					 Integer32( -2147483648 .. 2147483647 )
		MAX-ACCESS			 read-only
		STATUS					 current
		DESCRIPTION			 " -- "
		::=  { sfn8avgripEntry  72 }


	plsfn8Prb70RIPAvg		 OBJECT-TYPE
		SYNTAX					 Integer32( -2147483648 .. 2147483647 )
		MAX-ACCESS			 read-only
		STATUS					 current
		DESCRIPTION			 " -- "
		::=  { sfn8avgripEntry  73 }


	plsfn8Prb71RIPAvg		 OBJECT-TYPE
		SYNTAX					 Integer32( -2147483648 .. 2147483647 )
		MAX-ACCESS			 read-only
		STATUS					 current
		DESCRIPTION			 " -- "
		::=  { sfn8avgripEntry  74 }


	plsfn8Prb72RIPAvg		 OBJECT-TYPE
		SYNTAX					 Integer32( -2147483648 .. 2147483647 )
		MAX-ACCESS			 read-only
		STATUS					 current
		DESCRIPTION			 " -- "
		::=  { sfn8avgripEntry  75 }


	plsfn8Prb73RIPAvg		 OBJECT-TYPE
		SYNTAX					 Integer32( -2147483648 .. 2147483647 )
		MAX-ACCESS			 read-only
		STATUS					 current
		DESCRIPTION			 " -- "
		::=  { sfn8avgripEntry  76 }


	plsfn8Prb74RIPAvg		 OBJECT-TYPE
		SYNTAX					 Integer32( -2147483648 .. 2147483647 )
		MAX-ACCESS			 read-only
		STATUS					 current
		DESCRIPTION			 " -- "
		::=  { sfn8avgripEntry  77 }


	plsfn8Prb75RIPAvg		 OBJECT-TYPE
		SYNTAX					 Integer32( -2147483648 .. 2147483647 )
		MAX-ACCESS			 read-only
		STATUS					 current
		DESCRIPTION			 " -- "
		::=  { sfn8avgripEntry  78 }


	plsfn8Prb76RIPAvg		 OBJECT-TYPE
		SYNTAX					 Integer32( -2147483648 .. 2147483647 )
		MAX-ACCESS			 read-only
		STATUS					 current
		DESCRIPTION			 " -- "
		::=  { sfn8avgripEntry  79 }


	plsfn8Prb77RIPAvg		 OBJECT-TYPE
		SYNTAX					 Integer32( -2147483648 .. 2147483647 )
		MAX-ACCESS			 read-only
		STATUS					 current
		DESCRIPTION			 " -- "
		::=  { sfn8avgripEntry  80 }


	plsfn8Prb78RIPAvg		 OBJECT-TYPE
		SYNTAX					 Integer32( -2147483648 .. 2147483647 )
		MAX-ACCESS			 read-only
		STATUS					 current
		DESCRIPTION			 " -- "
		::=  { sfn8avgripEntry  81 }


	plsfn8Prb79RIPAvg		 OBJECT-TYPE
		SYNTAX					 Integer32( -2147483648 .. 2147483647 )
		MAX-ACCESS			 read-only
		STATUS					 current
		DESCRIPTION			 " -- "
		::=  { sfn8avgripEntry  82 }


	plsfn8Prb80RIPAvg		 OBJECT-TYPE
		SYNTAX					 Integer32( -2147483648 .. 2147483647 )
		MAX-ACCESS			 read-only
		STATUS					 current
		DESCRIPTION			 " -- "
		::=  { sfn8avgripEntry  83 }


	plsfn8Prb81RIPAvg		 OBJECT-TYPE
		SYNTAX					 Integer32( -2147483648 .. 2147483647 )
		MAX-ACCESS			 read-only
		STATUS					 current
		DESCRIPTION			 " -- "
		::=  { sfn8avgripEntry  84 }


	plsfn8Prb82RIPAvg		 OBJECT-TYPE
		SYNTAX					 Integer32( -2147483648 .. 2147483647 )
		MAX-ACCESS			 read-only
		STATUS					 current
		DESCRIPTION			 " -- "
		::=  { sfn8avgripEntry  85 }


	plsfn8Prb83RIPAvg		 OBJECT-TYPE
		SYNTAX					 Integer32( -2147483648 .. 2147483647 )
		MAX-ACCESS			 read-only
		STATUS					 current
		DESCRIPTION			 " -- "
		::=  { sfn8avgripEntry  86 }


	plsfn8Prb84RIPAvg		 OBJECT-TYPE
		SYNTAX					 Integer32( -2147483648 .. 2147483647 )
		MAX-ACCESS			 read-only
		STATUS					 current
		DESCRIPTION			 " -- "
		::=  { sfn8avgripEntry  87 }


	plsfn8Prb85RIPAvg		 OBJECT-TYPE
		SYNTAX					 Integer32( -2147483648 .. 2147483647 )
		MAX-ACCESS			 read-only
		STATUS					 current
		DESCRIPTION			 " -- "
		::=  { sfn8avgripEntry  88 }


	plsfn8Prb86RIPAvg		 OBJECT-TYPE
		SYNTAX					 Integer32( -2147483648 .. 2147483647 )
		MAX-ACCESS			 read-only
		STATUS					 current
		DESCRIPTION			 " -- "
		::=  { sfn8avgripEntry  89 }


	plsfn8Prb87RIPAvg		 OBJECT-TYPE
		SYNTAX					 Integer32( -2147483648 .. 2147483647 )
		MAX-ACCESS			 read-only
		STATUS					 current
		DESCRIPTION			 " -- "
		::=  { sfn8avgripEntry  90 }


	plsfn8Prb88RIPAvg		 OBJECT-TYPE
		SYNTAX					 Integer32( -2147483648 .. 2147483647 )
		MAX-ACCESS			 read-only
		STATUS					 current
		DESCRIPTION			 " -- "
		::=  { sfn8avgripEntry  91 }


	plsfn8Prb89RIPAvg		 OBJECT-TYPE
		SYNTAX					 Integer32( -2147483648 .. 2147483647 )
		MAX-ACCESS			 read-only
		STATUS					 current
		DESCRIPTION			 " -- "
		::=  { sfn8avgripEntry  92 }


	plsfn8Prb90RIPAvg		 OBJECT-TYPE
		SYNTAX					 Integer32( -2147483648 .. 2147483647 )
		MAX-ACCESS			 read-only
		STATUS					 current
		DESCRIPTION			 " -- "
		::=  { sfn8avgripEntry  93 }


	plsfn8Prb91RIPAvg		 OBJECT-TYPE
		SYNTAX					 Integer32( -2147483648 .. 2147483647 )
		MAX-ACCESS			 read-only
		STATUS					 current
		DESCRIPTION			 " -- "
		::=  { sfn8avgripEntry  94 }


	plsfn8Prb92RIPAvg		 OBJECT-TYPE
		SYNTAX					 Integer32( -2147483648 .. 2147483647 )
		MAX-ACCESS			 read-only
		STATUS					 current
		DESCRIPTION			 " -- "
		::=  { sfn8avgripEntry  95 }


	plsfn8Prb93RIPAvg		 OBJECT-TYPE
		SYNTAX					 Integer32( -2147483648 .. 2147483647 )
		MAX-ACCESS			 read-only
		STATUS					 current
		DESCRIPTION			 " -- "
		::=  { sfn8avgripEntry  96 }


	plsfn8Prb94RIPAvg		 OBJECT-TYPE
		SYNTAX					 Integer32( -2147483648 .. 2147483647 )
		MAX-ACCESS			 read-only
		STATUS					 current
		DESCRIPTION			 " -- "
		::=  { sfn8avgripEntry  97 }


	plsfn8Prb95RIPAvg		 OBJECT-TYPE
		SYNTAX					 Integer32( -2147483648 .. 2147483647 )
		MAX-ACCESS			 read-only
		STATUS					 current
		DESCRIPTION			 " -- "
		::=  { sfn8avgripEntry  98 }


	plsfn8Prb96RIPAvg		 OBJECT-TYPE
		SYNTAX					 Integer32( -2147483648 .. 2147483647 )
		MAX-ACCESS			 read-only
		STATUS					 current
		DESCRIPTION			 " -- "
		::=  { sfn8avgripEntry  99 }


	plsfn8Prb97RIPAvg		 OBJECT-TYPE
		SYNTAX					 Integer32( -2147483648 .. 2147483647 )
		MAX-ACCESS			 read-only
		STATUS					 current
		DESCRIPTION			 " -- "
		::=  { sfn8avgripEntry  100 }


	plsfn8Prb98RIPAvg		 OBJECT-TYPE
		SYNTAX					 Integer32( -2147483648 .. 2147483647 )
		MAX-ACCESS			 read-only
		STATUS					 current
		DESCRIPTION			 " -- "
		::=  { sfn8avgripEntry  101 }


	plsfn8Prb99RIPAvg		 OBJECT-TYPE
		SYNTAX					 Integer32( -2147483648 .. 2147483647 )
		MAX-ACCESS			 read-only
		STATUS					 current
		DESCRIPTION			 " -- "
		::=  { sfn8avgripEntry  102 }


	sfn8maxripTable		 OBJECT-TYPE
		SYNTAX					 SEQUENCE  OF	 Sfn8maxripEntry
		MAX-ACCESS			 not-accessible
		STATUS					 current
		DESCRIPTION			 " -- "
		::=  { plrelatedOriginCounter  15 }


	sfn8maxripEntry		 OBJECT-TYPE
		SYNTAX					 Sfn8maxripEntry
		MAX-ACCESS			 not-accessible
		STATUS					 current
		DESCRIPTION			 " -- "
		INDEX						{ sfn8maxripLcId }
		::=  { sfn8maxripTable  1 }


	Sfn8maxripEntry		 ::=  SEQUENCE {
		sfn8maxripLcId					Integer32,
		sfn8maxripRowStatus					RowStatus,
		plsfn8PrbG1RIPMax					Integer32,
		plsfn8PrbG2RIPMax					Integer32,
		plsfn8PrbG3RIPMax					Integer32,
		plsfn8PrbG4RIPMax					Integer32,
		plsfn8PrbG5RIPMax					Integer32,
		plsfn8PrbG6RIPMax					Integer32,
		plsfn8PrbG7RIPMax					Integer32,
		plsfn8PrbG8RIPMax					Integer32,
		plsfn8PrbG9RIPMax					Integer32,
		plsfn8PrbG10RIPMax					Integer32,
		plsfn8PrbG11RIPMax					Integer32,
		plsfn8PrbG12RIPMax					Integer32,
		plsfn8PrbG13RIPMax					Integer32,
		plsfn8PrbG14RIPMax					Integer32,
		plsfn8PrbG15RIPMax					Integer32,
		plsfn8PrbG16RIPMax					Integer32,
		plsfn8PrbG17RIPMax					Integer32,
		plsfn8PrbG18RIPMax					Integer32,
		plsfn8PrbG19RIPMax					Integer32,
		plsfn8PrbG20RIPMax					Integer32
		}


	sfn8maxripLcId		 OBJECT-TYPE
		SYNTAX					 Integer32( 0 .. 23 )
		MAX-ACCESS			 not-accessible
		STATUS					 current
		DESCRIPTION			 " -- "
		::=  { sfn8maxripEntry  1 }


	sfn8maxripRowStatus		 OBJECT-TYPE
		SYNTAX					 RowStatus
		MAX-ACCESS			 read-only
		STATUS					 current
		DESCRIPTION			 " -- "
		::=  { sfn8maxripEntry  2 }


	plsfn8PrbG1RIPMax		 OBJECT-TYPE
		SYNTAX					 Integer32( -2147483648 .. 2147483647 )
		MAX-ACCESS			 read-only
		STATUS					 current
		DESCRIPTION			 " -- "
		::=  { sfn8maxripEntry  3 }


	plsfn8PrbG2RIPMax		 OBJECT-TYPE
		SYNTAX					 Integer32( -2147483648 .. 2147483647 )
		MAX-ACCESS			 read-only
		STATUS					 current
		DESCRIPTION			 " -- "
		::=  { sfn8maxripEntry  4 }


	plsfn8PrbG3RIPMax		 OBJECT-TYPE
		SYNTAX					 Integer32( -2147483648 .. 2147483647 )
		MAX-ACCESS			 read-only
		STATUS					 current
		DESCRIPTION			 " -- "
		::=  { sfn8maxripEntry  5 }


	plsfn8PrbG4RIPMax		 OBJECT-TYPE
		SYNTAX					 Integer32( -2147483648 .. 2147483647 )
		MAX-ACCESS			 read-only
		STATUS					 current
		DESCRIPTION			 " -- "
		::=  { sfn8maxripEntry  6 }


	plsfn8PrbG5RIPMax		 OBJECT-TYPE
		SYNTAX					 Integer32( -2147483648 .. 2147483647 )
		MAX-ACCESS			 read-only
		STATUS					 current
		DESCRIPTION			 " -- "
		::=  { sfn8maxripEntry  7 }


	plsfn8PrbG6RIPMax		 OBJECT-TYPE
		SYNTAX					 Integer32( -2147483648 .. 2147483647 )
		MAX-ACCESS			 read-only
		STATUS					 current
		DESCRIPTION			 " -- "
		::=  { sfn8maxripEntry  8 }


	plsfn8PrbG7RIPMax		 OBJECT-TYPE
		SYNTAX					 Integer32( -2147483648 .. 2147483647 )
		MAX-ACCESS			 read-only
		STATUS					 current
		DESCRIPTION			 " -- "
		::=  { sfn8maxripEntry  9 }


	plsfn8PrbG8RIPMax		 OBJECT-TYPE
		SYNTAX					 Integer32( -2147483648 .. 2147483647 )
		MAX-ACCESS			 read-only
		STATUS					 current
		DESCRIPTION			 " -- "
		::=  { sfn8maxripEntry  10 }


	plsfn8PrbG9RIPMax		 OBJECT-TYPE
		SYNTAX					 Integer32( -2147483648 .. 2147483647 )
		MAX-ACCESS			 read-only
		STATUS					 current
		DESCRIPTION			 " -- "
		::=  { sfn8maxripEntry  11 }


	plsfn8PrbG10RIPMax		 OBJECT-TYPE
		SYNTAX					 Integer32( -2147483648 .. 2147483647 )
		MAX-ACCESS			 read-only
		STATUS					 current
		DESCRIPTION			 " -- "
		::=  { sfn8maxripEntry  12 }


	plsfn8PrbG11RIPMax		 OBJECT-TYPE
		SYNTAX					 Integer32( -2147483648 .. 2147483647 )
		MAX-ACCESS			 read-only
		STATUS					 current
		DESCRIPTION			 " -- "
		::=  { sfn8maxripEntry  13 }


	plsfn8PrbG12RIPMax		 OBJECT-TYPE
		SYNTAX					 Integer32( -2147483648 .. 2147483647 )
		MAX-ACCESS			 read-only
		STATUS					 current
		DESCRIPTION			 " -- "
		::=  { sfn8maxripEntry  14 }


	plsfn8PrbG13RIPMax		 OBJECT-TYPE
		SYNTAX					 Integer32( -2147483648 .. 2147483647 )
		MAX-ACCESS			 read-only
		STATUS					 current
		DESCRIPTION			 " -- "
		::=  { sfn8maxripEntry  15 }


	plsfn8PrbG14RIPMax		 OBJECT-TYPE
		SYNTAX					 Integer32( -2147483648 .. 2147483647 )
		MAX-ACCESS			 read-only
		STATUS					 current
		DESCRIPTION			 " -- "
		::=  { sfn8maxripEntry  16 }


	plsfn8PrbG15RIPMax		 OBJECT-TYPE
		SYNTAX					 Integer32( -2147483648 .. 2147483647 )
		MAX-ACCESS			 read-only
		STATUS					 current
		DESCRIPTION			 " -- "
		::=  { sfn8maxripEntry  17 }


	plsfn8PrbG16RIPMax		 OBJECT-TYPE
		SYNTAX					 Integer32( -2147483648 .. 2147483647 )
		MAX-ACCESS			 read-only
		STATUS					 current
		DESCRIPTION			 " -- "
		::=  { sfn8maxripEntry  18 }


	plsfn8PrbG17RIPMax		 OBJECT-TYPE
		SYNTAX					 Integer32( -2147483648 .. 2147483647 )
		MAX-ACCESS			 read-only
		STATUS					 current
		DESCRIPTION			 " -- "
		::=  { sfn8maxripEntry  19 }


	plsfn8PrbG18RIPMax		 OBJECT-TYPE
		SYNTAX					 Integer32( -2147483648 .. 2147483647 )
		MAX-ACCESS			 read-only
		STATUS					 current
		DESCRIPTION			 " -- "
		::=  { sfn8maxripEntry  20 }


	plsfn8PrbG19RIPMax		 OBJECT-TYPE
		SYNTAX					 Integer32( -2147483648 .. 2147483647 )
		MAX-ACCESS			 read-only
		STATUS					 current
		DESCRIPTION			 " -- "
		::=  { sfn8maxripEntry  21 }


	plsfn8PrbG20RIPMax		 OBJECT-TYPE
		SYNTAX					 Integer32( -2147483648 .. 2147483647 )
		MAX-ACCESS			 read-only
		STATUS					 current
		DESCRIPTION			 " -- "
		::=  { sfn8maxripEntry  22 }


	plTransPowerTable		 OBJECT-TYPE
		SYNTAX					 SEQUENCE  OF	 PlTransPowerEntry
		MAX-ACCESS			 not-accessible
		STATUS					 current
		DESCRIPTION			 " -- "
		::=  { plrelatedOriginCounter  16 }


	plTransPowerEntry		 OBJECT-TYPE
		SYNTAX					 PlTransPowerEntry
		MAX-ACCESS			 not-accessible
		STATUS					 current
		DESCRIPTION			 " -- "
		INDEX						{ plTransPowerLcId }
		::=  { plTransPowerTable  1 }


	PlTransPowerEntry		 ::=  SEQUENCE {
		plTransPowerLcId					Integer32,
		plTransPowerRowStatus					RowStatus,
		plCellTransPowerMax					Integer32,
		plCellTransPowerAvg					Integer32
		}


	plTransPowerLcId		 OBJECT-TYPE
		SYNTAX					 Integer32( 0 .. 23 )
		MAX-ACCESS			 not-accessible
		STATUS					 current
		DESCRIPTION			 " -- "
		::=  { plTransPowerEntry  1 }


	plTransPowerRowStatus		 OBJECT-TYPE
		SYNTAX					 RowStatus
		MAX-ACCESS			 read-only
		STATUS					 current
		DESCRIPTION			 " -- "
		::=  { plTransPowerEntry  2 }


	plCellTransPowerMax		 OBJECT-TYPE
		SYNTAX					 Integer32( -2147483648 .. 2147483647 )
		MAX-ACCESS			 read-only
		STATUS					 current
		DESCRIPTION			 " -- "
		::=  { plTransPowerEntry  3 }


	plCellTransPowerAvg		 OBJECT-TYPE
		SYNTAX					 Integer32( -2147483648 .. 2147483647 )
		MAX-ACCESS			 read-only
		STATUS					 current
		DESCRIPTION			 " -- "
		::=  { plTransPowerEntry  4 }


	cellavgripperprbTable		 OBJECT-TYPE
		SYNTAX					 SEQUENCE  OF	 CellavgripperprbEntry
		MAX-ACCESS			 not-accessible
		STATUS					 current
		DESCRIPTION			 " -- "
		::=  { plrelatedOriginCounter  17 }


	cellavgripperprbEntry		 OBJECT-TYPE
		SYNTAX					 CellavgripperprbEntry
		MAX-ACCESS			 not-accessible
		STATUS					 current
		DESCRIPTION			 " -- "
		INDEX						{ cellavgripperprbLcId }
		::=  { cellavgripperprbTable  1 }


	CellavgripperprbEntry		 ::=  SEQUENCE {
		cellavgripperprbLcId					Integer32,
		cellavgripperprbRowStatus					RowStatus,
		phyULMeanNLPRB00					Integer32,
		phyULMeanNLPRB01					Integer32,
		phyULMeanNLPRB02					Integer32,
		phyULMeanNLPRB03					Integer32,
		phyULMeanNLPRB04					Integer32,
		phyULMeanNLPRB05					Integer32,
		phyULMeanNLPRB06					Integer32,
		phyULMeanNLPRB07					Integer32,
		phyULMeanNLPRB08					Integer32,
		phyULMeanNLPRB09					Integer32,
		phyULMeanNLPRB10					Integer32,
		phyULMeanNLPRB11					Integer32,
		phyULMeanNLPRB12					Integer32,
		phyULMeanNLPRB13					Integer32,
		phyULMeanNLPRB14					Integer32,
		phyULMeanNLPRB15					Integer32,
		phyULMeanNLPRB16					Integer32,
		phyULMeanNLPRB17					Integer32,
		phyULMeanNLPRB18					Integer32,
		phyULMeanNLPRB19					Integer32,
		phyULMeanNLPRB20					Integer32,
		phyULMeanNLPRB21					Integer32,
		phyULMeanNLPRB22					Integer32,
		phyULMeanNLPRB23					Integer32,
		phyULMeanNLPRB24					Integer32,
		phyULMeanNLPRB25					Integer32,
		phyULMeanNLPRB26					Integer32,
		phyULMeanNLPRB27					Integer32,
		phyULMeanNLPRB28					Integer32,
		phyULMeanNLPRB29					Integer32,
		phyULMeanNLPRB30					Integer32,
		phyULMeanNLPRB31					Integer32,
		phyULMeanNLPRB32					Integer32,
		phyULMeanNLPRB33					Integer32,
		phyULMeanNLPRB34					Integer32,
		phyULMeanNLPRB35					Integer32,
		phyULMeanNLPRB36					Integer32,
		phyULMeanNLPRB37					Integer32,
		phyULMeanNLPRB38					Integer32,
		phyULMeanNLPRB39					Integer32,
		phyULMeanNLPRB40					Integer32,
		phyULMeanNLPRB41					Integer32,
		phyULMeanNLPRB42					Integer32,
		phyULMeanNLPRB43					Integer32,
		phyULMeanNLPRB44					Integer32,
		phyULMeanNLPRB45					Integer32,
		phyULMeanNLPRB46					Integer32,
		phyULMeanNLPRB47					Integer32,
		phyULMeanNLPRB48					Integer32,
		phyULMeanNLPRB49					Integer32,
		phyULMeanNLPRB50					Integer32,
		phyULMeanNLPRB51					Integer32,
		phyULMeanNLPRB52					Integer32,
		phyULMeanNLPRB53					Integer32,
		phyULMeanNLPRB54					Integer32,
		phyULMeanNLPRB55					Integer32,
		phyULMeanNLPRB56					Integer32,
		phyULMeanNLPRB57					Integer32,
		phyULMeanNLPRB58					Integer32,
		phyULMeanNLPRB59					Integer32,
		phyULMeanNLPRB60					Integer32,
		phyULMeanNLPRB61					Integer32,
		phyULMeanNLPRB62					Integer32,
		phyULMeanNLPRB63					Integer32,
		phyULMeanNLPRB64					Integer32,
		phyULMeanNLPRB65					Integer32,
		phyULMeanNLPRB66					Integer32,
		phyULMeanNLPRB67					Integer32,
		phyULMeanNLPRB68					Integer32,
		phyULMeanNLPRB69					Integer32,
		phyULMeanNLPRB70					Integer32,
		phyULMeanNLPRB71					Integer32,
		phyULMeanNLPRB72					Integer32,
		phyULMeanNLPRB73					Integer32,
		phyULMeanNLPRB74					Integer32,
		phyULMeanNLPRB75					Integer32,
		phyULMeanNLPRB76					Integer32,
		phyULMeanNLPRB77					Integer32,
		phyULMeanNLPRB78					Integer32,
		phyULMeanNLPRB79					Integer32,
		phyULMeanNLPRB80					Integer32,
		phyULMeanNLPRB81					Integer32,
		phyULMeanNLPRB82					Integer32,
		phyULMeanNLPRB83					Integer32,
		phyULMeanNLPRB84					Integer32,
		phyULMeanNLPRB85					Integer32,
		phyULMeanNLPRB86					Integer32,
		phyULMeanNLPRB87					Integer32,
		phyULMeanNLPRB88					Integer32,
		phyULMeanNLPRB89					Integer32,
		phyULMeanNLPRB90					Integer32,
		phyULMeanNLPRB91					Integer32,
		phyULMeanNLPRB92					Integer32,
		phyULMeanNLPRB93					Integer32,
		phyULMeanNLPRB94					Integer32,
		phyULMeanNLPRB95					Integer32,
		phyULMeanNLPRB96					Integer32,
		phyULMeanNLPRB97					Integer32,
		phyULMeanNLPRB98					Integer32,
		phyULMeanNLPRB99					Integer32
		}


	cellavgripperprbLcId		 OBJECT-TYPE
		SYNTAX					 Integer32( 0 .. 23 )
		MAX-ACCESS			 not-accessible
		STATUS					 current
		DESCRIPTION			 " -- "
		::=  { cellavgripperprbEntry  1 }


	cellavgripperprbRowStatus		 OBJECT-TYPE
		SYNTAX					 RowStatus
		MAX-ACCESS			 read-only
		STATUS					 current
		DESCRIPTION			 " -- "
		::=  { cellavgripperprbEntry  2 }


	phyULMeanNLPRB00		 OBJECT-TYPE
		SYNTAX					 Integer32( -2147483648 .. 2147483647 )
		MAX-ACCESS			 read-only
		STATUS					 current
		DESCRIPTION			 " -- "
		::=  { cellavgripperprbEntry  3 }


	phyULMeanNLPRB01		 OBJECT-TYPE
		SYNTAX					 Integer32( -2147483648 .. 2147483647 )
		MAX-ACCESS			 read-only
		STATUS					 current
		DESCRIPTION			 " -- "
		::=  { cellavgripperprbEntry  4 }


	phyULMeanNLPRB02		 OBJECT-TYPE
		SYNTAX					 Integer32( -2147483648 .. 2147483647 )
		MAX-ACCESS			 read-only
		STATUS					 current
		DESCRIPTION			 " -- "
		::=  { cellavgripperprbEntry  5 }


	phyULMeanNLPRB03		 OBJECT-TYPE
		SYNTAX					 Integer32( -2147483648 .. 2147483647 )
		MAX-ACCESS			 read-only
		STATUS					 current
		DESCRIPTION			 " -- "
		::=  { cellavgripperprbEntry  6 }


	phyULMeanNLPRB04		 OBJECT-TYPE
		SYNTAX					 Integer32( -2147483648 .. 2147483647 )
		MAX-ACCESS			 read-only
		STATUS					 current
		DESCRIPTION			 " -- "
		::=  { cellavgripperprbEntry  7 }


	phyULMeanNLPRB05		 OBJECT-TYPE
		SYNTAX					 Integer32( -2147483648 .. 2147483647 )
		MAX-ACCESS			 read-only
		STATUS					 current
		DESCRIPTION			 " -- "
		::=  { cellavgripperprbEntry  8 }


	phyULMeanNLPRB06		 OBJECT-TYPE
		SYNTAX					 Integer32( -2147483648 .. 2147483647 )
		MAX-ACCESS			 read-only
		STATUS					 current
		DESCRIPTION			 " -- "
		::=  { cellavgripperprbEntry  9 }


	phyULMeanNLPRB07		 OBJECT-TYPE
		SYNTAX					 Integer32( -2147483648 .. 2147483647 )
		MAX-ACCESS			 read-only
		STATUS					 current
		DESCRIPTION			 " -- "
		::=  { cellavgripperprbEntry  10 }


	phyULMeanNLPRB08		 OBJECT-TYPE
		SYNTAX					 Integer32( -2147483648 .. 2147483647 )
		MAX-ACCESS			 read-only
		STATUS					 current
		DESCRIPTION			 " -- "
		::=  { cellavgripperprbEntry  11 }


	phyULMeanNLPRB09		 OBJECT-TYPE
		SYNTAX					 Integer32( -2147483648 .. 2147483647 )
		MAX-ACCESS			 read-only
		STATUS					 current
		DESCRIPTION			 " -- "
		::=  { cellavgripperprbEntry  12 }


	phyULMeanNLPRB10		 OBJECT-TYPE
		SYNTAX					 Integer32( -2147483648 .. 2147483647 )
		MAX-ACCESS			 read-only
		STATUS					 current
		DESCRIPTION			 " -- "
		::=  { cellavgripperprbEntry  13 }


	phyULMeanNLPRB11		 OBJECT-TYPE
		SYNTAX					 Integer32( -2147483648 .. 2147483647 )
		MAX-ACCESS			 read-only
		STATUS					 current
		DESCRIPTION			 " -- "
		::=  { cellavgripperprbEntry  14 }


	phyULMeanNLPRB12		 OBJECT-TYPE
		SYNTAX					 Integer32( -2147483648 .. 2147483647 )
		MAX-ACCESS			 read-only
		STATUS					 current
		DESCRIPTION			 " -- "
		::=  { cellavgripperprbEntry  15 }


	phyULMeanNLPRB13		 OBJECT-TYPE
		SYNTAX					 Integer32( -2147483648 .. 2147483647 )
		MAX-ACCESS			 read-only
		STATUS					 current
		DESCRIPTION			 " -- "
		::=  { cellavgripperprbEntry  16 }


	phyULMeanNLPRB14		 OBJECT-TYPE
		SYNTAX					 Integer32( -2147483648 .. 2147483647 )
		MAX-ACCESS			 read-only
		STATUS					 current
		DESCRIPTION			 " -- "
		::=  { cellavgripperprbEntry  17 }


	phyULMeanNLPRB15		 OBJECT-TYPE
		SYNTAX					 Integer32( -2147483648 .. 2147483647 )
		MAX-ACCESS			 read-only
		STATUS					 current
		DESCRIPTION			 " -- "
		::=  { cellavgripperprbEntry  18 }


	phyULMeanNLPRB16		 OBJECT-TYPE
		SYNTAX					 Integer32( -2147483648 .. 2147483647 )
		MAX-ACCESS			 read-only
		STATUS					 current
		DESCRIPTION			 " -- "
		::=  { cellavgripperprbEntry  19 }


	phyULMeanNLPRB17		 OBJECT-TYPE
		SYNTAX					 Integer32( -2147483648 .. 2147483647 )
		MAX-ACCESS			 read-only
		STATUS					 current
		DESCRIPTION			 " -- "
		::=  { cellavgripperprbEntry  20 }


	phyULMeanNLPRB18		 OBJECT-TYPE
		SYNTAX					 Integer32( -2147483648 .. 2147483647 )
		MAX-ACCESS			 read-only
		STATUS					 current
		DESCRIPTION			 " -- "
		::=  { cellavgripperprbEntry  21 }


	phyULMeanNLPRB19		 OBJECT-TYPE
		SYNTAX					 Integer32( -2147483648 .. 2147483647 )
		MAX-ACCESS			 read-only
		STATUS					 current
		DESCRIPTION			 " -- "
		::=  { cellavgripperprbEntry  22 }


	phyULMeanNLPRB20		 OBJECT-TYPE
		SYNTAX					 Integer32( -2147483648 .. 2147483647 )
		MAX-ACCESS			 read-only
		STATUS					 current
		DESCRIPTION			 " -- "
		::=  { cellavgripperprbEntry  23 }


	phyULMeanNLPRB21		 OBJECT-TYPE
		SYNTAX					 Integer32( -2147483648 .. 2147483647 )
		MAX-ACCESS			 read-only
		STATUS					 current
		DESCRIPTION			 " -- "
		::=  { cellavgripperprbEntry  24 }


	phyULMeanNLPRB22		 OBJECT-TYPE
		SYNTAX					 Integer32( -2147483648 .. 2147483647 )
		MAX-ACCESS			 read-only
		STATUS					 current
		DESCRIPTION			 " -- "
		::=  { cellavgripperprbEntry  25 }


	phyULMeanNLPRB23		 OBJECT-TYPE
		SYNTAX					 Integer32( -2147483648 .. 2147483647 )
		MAX-ACCESS			 read-only
		STATUS					 current
		DESCRIPTION			 " -- "
		::=  { cellavgripperprbEntry  26 }


	phyULMeanNLPRB24		 OBJECT-TYPE
		SYNTAX					 Integer32( -2147483648 .. 2147483647 )
		MAX-ACCESS			 read-only
		STATUS					 current
		DESCRIPTION			 " -- "
		::=  { cellavgripperprbEntry  27 }


	phyULMeanNLPRB25		 OBJECT-TYPE
		SYNTAX					 Integer32( -2147483648 .. 2147483647 )
		MAX-ACCESS			 read-only
		STATUS					 current
		DESCRIPTION			 " -- "
		::=  { cellavgripperprbEntry  28 }


	phyULMeanNLPRB26		 OBJECT-TYPE
		SYNTAX					 Integer32( -2147483648 .. 2147483647 )
		MAX-ACCESS			 read-only
		STATUS					 current
		DESCRIPTION			 " -- "
		::=  { cellavgripperprbEntry  29 }


	phyULMeanNLPRB27		 OBJECT-TYPE
		SYNTAX					 Integer32( -2147483648 .. 2147483647 )
		MAX-ACCESS			 read-only
		STATUS					 current
		DESCRIPTION			 " -- "
		::=  { cellavgripperprbEntry  30 }


	phyULMeanNLPRB28		 OBJECT-TYPE
		SYNTAX					 Integer32( -2147483648 .. 2147483647 )
		MAX-ACCESS			 read-only
		STATUS					 current
		DESCRIPTION			 " -- "
		::=  { cellavgripperprbEntry  31 }


	phyULMeanNLPRB29		 OBJECT-TYPE
		SYNTAX					 Integer32( -2147483648 .. 2147483647 )
		MAX-ACCESS			 read-only
		STATUS					 current
		DESCRIPTION			 " -- "
		::=  { cellavgripperprbEntry  32 }


	phyULMeanNLPRB30		 OBJECT-TYPE
		SYNTAX					 Integer32( -2147483648 .. 2147483647 )
		MAX-ACCESS			 read-only
		STATUS					 current
		DESCRIPTION			 " -- "
		::=  { cellavgripperprbEntry  33 }


	phyULMeanNLPRB31		 OBJECT-TYPE
		SYNTAX					 Integer32( -2147483648 .. 2147483647 )
		MAX-ACCESS			 read-only
		STATUS					 current
		DESCRIPTION			 " -- "
		::=  { cellavgripperprbEntry  34 }


	phyULMeanNLPRB32		 OBJECT-TYPE
		SYNTAX					 Integer32( -2147483648 .. 2147483647 )
		MAX-ACCESS			 read-only
		STATUS					 current
		DESCRIPTION			 " -- "
		::=  { cellavgripperprbEntry  35 }


	phyULMeanNLPRB33		 OBJECT-TYPE
		SYNTAX					 Integer32( -2147483648 .. 2147483647 )
		MAX-ACCESS			 read-only
		STATUS					 current
		DESCRIPTION			 " -- "
		::=  { cellavgripperprbEntry  36 }


	phyULMeanNLPRB34		 OBJECT-TYPE
		SYNTAX					 Integer32( -2147483648 .. 2147483647 )
		MAX-ACCESS			 read-only
		STATUS					 current
		DESCRIPTION			 " -- "
		::=  { cellavgripperprbEntry  37 }


	phyULMeanNLPRB35		 OBJECT-TYPE
		SYNTAX					 Integer32( -2147483648 .. 2147483647 )
		MAX-ACCESS			 read-only
		STATUS					 current
		DESCRIPTION			 " -- "
		::=  { cellavgripperprbEntry  38 }


	phyULMeanNLPRB36		 OBJECT-TYPE
		SYNTAX					 Integer32( -2147483648 .. 2147483647 )
		MAX-ACCESS			 read-only
		STATUS					 current
		DESCRIPTION			 " -- "
		::=  { cellavgripperprbEntry  39 }


	phyULMeanNLPRB37		 OBJECT-TYPE
		SYNTAX					 Integer32( -2147483648 .. 2147483647 )
		MAX-ACCESS			 read-only
		STATUS					 current
		DESCRIPTION			 " -- "
		::=  { cellavgripperprbEntry  40 }


	phyULMeanNLPRB38		 OBJECT-TYPE
		SYNTAX					 Integer32( -2147483648 .. 2147483647 )
		MAX-ACCESS			 read-only
		STATUS					 current
		DESCRIPTION			 " -- "
		::=  { cellavgripperprbEntry  41 }


	phyULMeanNLPRB39		 OBJECT-TYPE
		SYNTAX					 Integer32( -2147483648 .. 2147483647 )
		MAX-ACCESS			 read-only
		STATUS					 current
		DESCRIPTION			 " -- "
		::=  { cellavgripperprbEntry  42 }


	phyULMeanNLPRB40		 OBJECT-TYPE
		SYNTAX					 Integer32( -2147483648 .. 2147483647 )
		MAX-ACCESS			 read-only
		STATUS					 current
		DESCRIPTION			 " -- "
		::=  { cellavgripperprbEntry  43 }


	phyULMeanNLPRB41		 OBJECT-TYPE
		SYNTAX					 Integer32( -2147483648 .. 2147483647 )
		MAX-ACCESS			 read-only
		STATUS					 current
		DESCRIPTION			 " -- "
		::=  { cellavgripperprbEntry  44 }


	phyULMeanNLPRB42		 OBJECT-TYPE
		SYNTAX					 Integer32( -2147483648 .. 2147483647 )
		MAX-ACCESS			 read-only
		STATUS					 current
		DESCRIPTION			 " -- "
		::=  { cellavgripperprbEntry  45 }


	phyULMeanNLPRB43		 OBJECT-TYPE
		SYNTAX					 Integer32( -2147483648 .. 2147483647 )
		MAX-ACCESS			 read-only
		STATUS					 current
		DESCRIPTION			 " -- "
		::=  { cellavgripperprbEntry  46 }


	phyULMeanNLPRB44		 OBJECT-TYPE
		SYNTAX					 Integer32( -2147483648 .. 2147483647 )
		MAX-ACCESS			 read-only
		STATUS					 current
		DESCRIPTION			 " -- "
		::=  { cellavgripperprbEntry  47 }


	phyULMeanNLPRB45		 OBJECT-TYPE
		SYNTAX					 Integer32( -2147483648 .. 2147483647 )
		MAX-ACCESS			 read-only
		STATUS					 current
		DESCRIPTION			 " -- "
		::=  { cellavgripperprbEntry  48 }


	phyULMeanNLPRB46		 OBJECT-TYPE
		SYNTAX					 Integer32( -2147483648 .. 2147483647 )
		MAX-ACCESS			 read-only
		STATUS					 current
		DESCRIPTION			 " -- "
		::=  { cellavgripperprbEntry  49 }


	phyULMeanNLPRB47		 OBJECT-TYPE
		SYNTAX					 Integer32( -2147483648 .. 2147483647 )
		MAX-ACCESS			 read-only
		STATUS					 current
		DESCRIPTION			 " -- "
		::=  { cellavgripperprbEntry  50 }


	phyULMeanNLPRB48		 OBJECT-TYPE
		SYNTAX					 Integer32( -2147483648 .. 2147483647 )
		MAX-ACCESS			 read-only
		STATUS					 current
		DESCRIPTION			 " -- "
		::=  { cellavgripperprbEntry  51 }


	phyULMeanNLPRB49		 OBJECT-TYPE
		SYNTAX					 Integer32( -2147483648 .. 2147483647 )
		MAX-ACCESS			 read-only
		STATUS					 current
		DESCRIPTION			 " -- "
		::=  { cellavgripperprbEntry  52 }


	phyULMeanNLPRB50		 OBJECT-TYPE
		SYNTAX					 Integer32( -2147483648 .. 2147483647 )
		MAX-ACCESS			 read-only
		STATUS					 current
		DESCRIPTION			 " -- "
		::=  { cellavgripperprbEntry  53 }


	phyULMeanNLPRB51		 OBJECT-TYPE
		SYNTAX					 Integer32( -2147483648 .. 2147483647 )
		MAX-ACCESS			 read-only
		STATUS					 current
		DESCRIPTION			 " -- "
		::=  { cellavgripperprbEntry  54 }


	phyULMeanNLPRB52		 OBJECT-TYPE
		SYNTAX					 Integer32( -2147483648 .. 2147483647 )
		MAX-ACCESS			 read-only
		STATUS					 current
		DESCRIPTION			 " -- "
		::=  { cellavgripperprbEntry  55 }


	phyULMeanNLPRB53		 OBJECT-TYPE
		SYNTAX					 Integer32( -2147483648 .. 2147483647 )
		MAX-ACCESS			 read-only
		STATUS					 current
		DESCRIPTION			 " -- "
		::=  { cellavgripperprbEntry  56 }


	phyULMeanNLPRB54		 OBJECT-TYPE
		SYNTAX					 Integer32( -2147483648 .. 2147483647 )
		MAX-ACCESS			 read-only
		STATUS					 current
		DESCRIPTION			 " -- "
		::=  { cellavgripperprbEntry  57 }


	phyULMeanNLPRB55		 OBJECT-TYPE
		SYNTAX					 Integer32( -2147483648 .. 2147483647 )
		MAX-ACCESS			 read-only
		STATUS					 current
		DESCRIPTION			 " -- "
		::=  { cellavgripperprbEntry  58 }


	phyULMeanNLPRB56		 OBJECT-TYPE
		SYNTAX					 Integer32( -2147483648 .. 2147483647 )
		MAX-ACCESS			 read-only
		STATUS					 current
		DESCRIPTION			 " -- "
		::=  { cellavgripperprbEntry  59 }


	phyULMeanNLPRB57		 OBJECT-TYPE
		SYNTAX					 Integer32( -2147483648 .. 2147483647 )
		MAX-ACCESS			 read-only
		STATUS					 current
		DESCRIPTION			 " -- "
		::=  { cellavgripperprbEntry  60 }


	phyULMeanNLPRB58		 OBJECT-TYPE
		SYNTAX					 Integer32( -2147483648 .. 2147483647 )
		MAX-ACCESS			 read-only
		STATUS					 current
		DESCRIPTION			 " -- "
		::=  { cellavgripperprbEntry  61 }


	phyULMeanNLPRB59		 OBJECT-TYPE
		SYNTAX					 Integer32( -2147483648 .. 2147483647 )
		MAX-ACCESS			 read-only
		STATUS					 current
		DESCRIPTION			 " -- "
		::=  { cellavgripperprbEntry  62 }


	phyULMeanNLPRB60		 OBJECT-TYPE
		SYNTAX					 Integer32( -2147483648 .. 2147483647 )
		MAX-ACCESS			 read-only
		STATUS					 current
		DESCRIPTION			 " -- "
		::=  { cellavgripperprbEntry  63 }


	phyULMeanNLPRB61		 OBJECT-TYPE
		SYNTAX					 Integer32( -2147483648 .. 2147483647 )
		MAX-ACCESS			 read-only
		STATUS					 current
		DESCRIPTION			 " -- "
		::=  { cellavgripperprbEntry  64 }


	phyULMeanNLPRB62		 OBJECT-TYPE
		SYNTAX					 Integer32( -2147483648 .. 2147483647 )
		MAX-ACCESS			 read-only
		STATUS					 current
		DESCRIPTION			 " -- "
		::=  { cellavgripperprbEntry  65 }


	phyULMeanNLPRB63		 OBJECT-TYPE
		SYNTAX					 Integer32( -2147483648 .. 2147483647 )
		MAX-ACCESS			 read-only
		STATUS					 current
		DESCRIPTION			 " -- "
		::=  { cellavgripperprbEntry  66 }


	phyULMeanNLPRB64		 OBJECT-TYPE
		SYNTAX					 Integer32( -2147483648 .. 2147483647 )
		MAX-ACCESS			 read-only
		STATUS					 current
		DESCRIPTION			 " -- "
		::=  { cellavgripperprbEntry  67 }


	phyULMeanNLPRB65		 OBJECT-TYPE
		SYNTAX					 Integer32( -2147483648 .. 2147483647 )
		MAX-ACCESS			 read-only
		STATUS					 current
		DESCRIPTION			 " -- "
		::=  { cellavgripperprbEntry  68 }


	phyULMeanNLPRB66		 OBJECT-TYPE
		SYNTAX					 Integer32( -2147483648 .. 2147483647 )
		MAX-ACCESS			 read-only
		STATUS					 current
		DESCRIPTION			 " -- "
		::=  { cellavgripperprbEntry  69 }


	phyULMeanNLPRB67		 OBJECT-TYPE
		SYNTAX					 Integer32( -2147483648 .. 2147483647 )
		MAX-ACCESS			 read-only
		STATUS					 current
		DESCRIPTION			 " -- "
		::=  { cellavgripperprbEntry  70 }


	phyULMeanNLPRB68		 OBJECT-TYPE
		SYNTAX					 Integer32( -2147483648 .. 2147483647 )
		MAX-ACCESS			 read-only
		STATUS					 current
		DESCRIPTION			 " -- "
		::=  { cellavgripperprbEntry  71 }


	phyULMeanNLPRB69		 OBJECT-TYPE
		SYNTAX					 Integer32( -2147483648 .. 2147483647 )
		MAX-ACCESS			 read-only
		STATUS					 current
		DESCRIPTION			 " -- "
		::=  { cellavgripperprbEntry  72 }


	phyULMeanNLPRB70		 OBJECT-TYPE
		SYNTAX					 Integer32( -2147483648 .. 2147483647 )
		MAX-ACCESS			 read-only
		STATUS					 current
		DESCRIPTION			 " -- "
		::=  { cellavgripperprbEntry  73 }


	phyULMeanNLPRB71		 OBJECT-TYPE
		SYNTAX					 Integer32( -2147483648 .. 2147483647 )
		MAX-ACCESS			 read-only
		STATUS					 current
		DESCRIPTION			 " -- "
		::=  { cellavgripperprbEntry  74 }


	phyULMeanNLPRB72		 OBJECT-TYPE
		SYNTAX					 Integer32( -2147483648 .. 2147483647 )
		MAX-ACCESS			 read-only
		STATUS					 current
		DESCRIPTION			 " -- "
		::=  { cellavgripperprbEntry  75 }


	phyULMeanNLPRB73		 OBJECT-TYPE
		SYNTAX					 Integer32( -2147483648 .. 2147483647 )
		MAX-ACCESS			 read-only
		STATUS					 current
		DESCRIPTION			 " -- "
		::=  { cellavgripperprbEntry  76 }


	phyULMeanNLPRB74		 OBJECT-TYPE
		SYNTAX					 Integer32( -2147483648 .. 2147483647 )
		MAX-ACCESS			 read-only
		STATUS					 current
		DESCRIPTION			 " -- "
		::=  { cellavgripperprbEntry  77 }


	phyULMeanNLPRB75		 OBJECT-TYPE
		SYNTAX					 Integer32( -2147483648 .. 2147483647 )
		MAX-ACCESS			 read-only
		STATUS					 current
		DESCRIPTION			 " -- "
		::=  { cellavgripperprbEntry  78 }


	phyULMeanNLPRB76		 OBJECT-TYPE
		SYNTAX					 Integer32( -2147483648 .. 2147483647 )
		MAX-ACCESS			 read-only
		STATUS					 current
		DESCRIPTION			 " -- "
		::=  { cellavgripperprbEntry  79 }


	phyULMeanNLPRB77		 OBJECT-TYPE
		SYNTAX					 Integer32( -2147483648 .. 2147483647 )
		MAX-ACCESS			 read-only
		STATUS					 current
		DESCRIPTION			 " -- "
		::=  { cellavgripperprbEntry  80 }


	phyULMeanNLPRB78		 OBJECT-TYPE
		SYNTAX					 Integer32( -2147483648 .. 2147483647 )
		MAX-ACCESS			 read-only
		STATUS					 current
		DESCRIPTION			 " -- "
		::=  { cellavgripperprbEntry  81 }


	phyULMeanNLPRB79		 OBJECT-TYPE
		SYNTAX					 Integer32( -2147483648 .. 2147483647 )
		MAX-ACCESS			 read-only
		STATUS					 current
		DESCRIPTION			 " -- "
		::=  { cellavgripperprbEntry  82 }


	phyULMeanNLPRB80		 OBJECT-TYPE
		SYNTAX					 Integer32( -2147483648 .. 2147483647 )
		MAX-ACCESS			 read-only
		STATUS					 current
		DESCRIPTION			 " -- "
		::=  { cellavgripperprbEntry  83 }


	phyULMeanNLPRB81		 OBJECT-TYPE
		SYNTAX					 Integer32( -2147483648 .. 2147483647 )
		MAX-ACCESS			 read-only
		STATUS					 current
		DESCRIPTION			 " -- "
		::=  { cellavgripperprbEntry  84 }


	phyULMeanNLPRB82		 OBJECT-TYPE
		SYNTAX					 Integer32( -2147483648 .. 2147483647 )
		MAX-ACCESS			 read-only
		STATUS					 current
		DESCRIPTION			 " -- "
		::=  { cellavgripperprbEntry  85 }


	phyULMeanNLPRB83		 OBJECT-TYPE
		SYNTAX					 Integer32( -2147483648 .. 2147483647 )
		MAX-ACCESS			 read-only
		STATUS					 current
		DESCRIPTION			 " -- "
		::=  { cellavgripperprbEntry  86 }


	phyULMeanNLPRB84		 OBJECT-TYPE
		SYNTAX					 Integer32( -2147483648 .. 2147483647 )
		MAX-ACCESS			 read-only
		STATUS					 current
		DESCRIPTION			 " -- "
		::=  { cellavgripperprbEntry  87 }


	phyULMeanNLPRB85		 OBJECT-TYPE
		SYNTAX					 Integer32( -2147483648 .. 2147483647 )
		MAX-ACCESS			 read-only
		STATUS					 current
		DESCRIPTION			 " -- "
		::=  { cellavgripperprbEntry  88 }


	phyULMeanNLPRB86		 OBJECT-TYPE
		SYNTAX					 Integer32( -2147483648 .. 2147483647 )
		MAX-ACCESS			 read-only
		STATUS					 current
		DESCRIPTION			 " -- "
		::=  { cellavgripperprbEntry  89 }


	phyULMeanNLPRB87		 OBJECT-TYPE
		SYNTAX					 Integer32( -2147483648 .. 2147483647 )
		MAX-ACCESS			 read-only
		STATUS					 current
		DESCRIPTION			 " -- "
		::=  { cellavgripperprbEntry  90 }


	phyULMeanNLPRB88		 OBJECT-TYPE
		SYNTAX					 Integer32( -2147483648 .. 2147483647 )
		MAX-ACCESS			 read-only
		STATUS					 current
		DESCRIPTION			 " -- "
		::=  { cellavgripperprbEntry  91 }


	phyULMeanNLPRB89		 OBJECT-TYPE
		SYNTAX					 Integer32( -2147483648 .. 2147483647 )
		MAX-ACCESS			 read-only
		STATUS					 current
		DESCRIPTION			 " -- "
		::=  { cellavgripperprbEntry  92 }


	phyULMeanNLPRB90		 OBJECT-TYPE
		SYNTAX					 Integer32( -2147483648 .. 2147483647 )
		MAX-ACCESS			 read-only
		STATUS					 current
		DESCRIPTION			 " -- "
		::=  { cellavgripperprbEntry  93 }


	phyULMeanNLPRB91		 OBJECT-TYPE
		SYNTAX					 Integer32( -2147483648 .. 2147483647 )
		MAX-ACCESS			 read-only
		STATUS					 current
		DESCRIPTION			 " -- "
		::=  { cellavgripperprbEntry  94 }


	phyULMeanNLPRB92		 OBJECT-TYPE
		SYNTAX					 Integer32( -2147483648 .. 2147483647 )
		MAX-ACCESS			 read-only
		STATUS					 current
		DESCRIPTION			 " -- "
		::=  { cellavgripperprbEntry  95 }


	phyULMeanNLPRB93		 OBJECT-TYPE
		SYNTAX					 Integer32( -2147483648 .. 2147483647 )
		MAX-ACCESS			 read-only
		STATUS					 current
		DESCRIPTION			 " -- "
		::=  { cellavgripperprbEntry  96 }


	phyULMeanNLPRB94		 OBJECT-TYPE
		SYNTAX					 Integer32( -2147483648 .. 2147483647 )
		MAX-ACCESS			 read-only
		STATUS					 current
		DESCRIPTION			 " -- "
		::=  { cellavgripperprbEntry  97 }


	phyULMeanNLPRB95		 OBJECT-TYPE
		SYNTAX					 Integer32( -2147483648 .. 2147483647 )
		MAX-ACCESS			 read-only
		STATUS					 current
		DESCRIPTION			 " -- "
		::=  { cellavgripperprbEntry  98 }


	phyULMeanNLPRB96		 OBJECT-TYPE
		SYNTAX					 Integer32( -2147483648 .. 2147483647 )
		MAX-ACCESS			 read-only
		STATUS					 current
		DESCRIPTION			 " -- "
		::=  { cellavgripperprbEntry  99 }


	phyULMeanNLPRB97		 OBJECT-TYPE
		SYNTAX					 Integer32( -2147483648 .. 2147483647 )
		MAX-ACCESS			 read-only
		STATUS					 current
		DESCRIPTION			 " -- "
		::=  { cellavgripperprbEntry  100 }


	phyULMeanNLPRB98		 OBJECT-TYPE
		SYNTAX					 Integer32( -2147483648 .. 2147483647 )
		MAX-ACCESS			 read-only
		STATUS					 current
		DESCRIPTION			 " -- "
		::=  { cellavgripperprbEntry  101 }


	phyULMeanNLPRB99		 OBJECT-TYPE
		SYNTAX					 Integer32( -2147483648 .. 2147483647 )
		MAX-ACCESS			 read-only
		STATUS					 current
		DESCRIPTION			 " -- "
		::=  { cellavgripperprbEntry  102 }


	cellmaxripperprbTable		 OBJECT-TYPE
		SYNTAX					 SEQUENCE  OF	 CellmaxripperprbEntry
		MAX-ACCESS			 not-accessible
		STATUS					 current
		DESCRIPTION			 " -- "
		::=  { plrelatedOriginCounter  18 }


	cellmaxripperprbEntry		 OBJECT-TYPE
		SYNTAX					 CellmaxripperprbEntry
		MAX-ACCESS			 not-accessible
		STATUS					 current
		DESCRIPTION			 " -- "
		INDEX						{ cellmaxripperprbLcId }
		::=  { cellmaxripperprbTable  1 }


	CellmaxripperprbEntry		 ::=  SEQUENCE {
		cellmaxripperprbLcId					Integer32,
		cellmaxripperprbRowStatus					RowStatus,
		phyULMaxNLPRB00					Integer32,
		phyULMaxNLPRB01					Integer32,
		phyULMaxNLPRB02					Integer32,
		phyULMaxNLPRB03					Integer32,
		phyULMaxNLPRB04					Integer32,
		phyULMaxNLPRB05					Integer32,
		phyULMaxNLPRB06					Integer32,
		phyULMaxNLPRB07					Integer32,
		phyULMaxNLPRB08					Integer32,
		phyULMaxNLPRB09					Integer32,
		phyULMaxNLPRB10					Integer32,
		phyULMaxNLPRB11					Integer32,
		phyULMaxNLPRB12					Integer32,
		phyULMaxNLPRB13					Integer32,
		phyULMaxNLPRB14					Integer32,
		phyULMaxNLPRB15					Integer32,
		phyULMaxNLPRB16					Integer32,
		phyULMaxNLPRB17					Integer32,
		phyULMaxNLPRB18					Integer32,
		phyULMaxNLPRB19					Integer32,
		phyULMaxNLPRB20					Integer32,
		phyULMaxNLPRB21					Integer32,
		phyULMaxNLPRB22					Integer32,
		phyULMaxNLPRB23					Integer32,
		phyULMaxNLPRB24					Integer32,
		phyULMaxNLPRB25					Integer32,
		phyULMaxNLPRB26					Integer32,
		phyULMaxNLPRB27					Integer32,
		phyULMaxNLPRB28					Integer32,
		phyULMaxNLPRB29					Integer32,
		phyULMaxNLPRB30					Integer32,
		phyULMaxNLPRB31					Integer32,
		phyULMaxNLPRB32					Integer32,
		phyULMaxNLPRB33					Integer32,
		phyULMaxNLPRB34					Integer32,
		phyULMaxNLPRB35					Integer32,
		phyULMaxNLPRB36					Integer32,
		phyULMaxNLPRB37					Integer32,
		phyULMaxNLPRB38					Integer32,
		phyULMaxNLPRB39					Integer32,
		phyULMaxNLPRB40					Integer32,
		phyULMaxNLPRB41					Integer32,
		phyULMaxNLPRB42					Integer32,
		phyULMaxNLPRB43					Integer32,
		phyULMaxNLPRB44					Integer32,
		phyULMaxNLPRB45					Integer32,
		phyULMaxNLPRB46					Integer32,
		phyULMaxNLPRB47					Integer32,
		phyULMaxNLPRB48					Integer32,
		phyULMaxNLPRB49					Integer32,
		phyULMaxNLPRB50					Integer32,
		phyULMaxNLPRB51					Integer32,
		phyULMaxNLPRB52					Integer32,
		phyULMaxNLPRB53					Integer32,
		phyULMaxNLPRB54					Integer32,
		phyULMaxNLPRB55					Integer32,
		phyULMaxNLPRB56					Integer32,
		phyULMaxNLPRB57					Integer32,
		phyULMaxNLPRB58					Integer32,
		phyULMaxNLPRB59					Integer32,
		phyULMaxNLPRB60					Integer32,
		phyULMaxNLPRB61					Integer32,
		phyULMaxNLPRB62					Integer32,
		phyULMaxNLPRB63					Integer32,
		phyULMaxNLPRB64					Integer32,
		phyULMaxNLPRB65					Integer32,
		phyULMaxNLPRB66					Integer32,
		phyULMaxNLPRB67					Integer32,
		phyULMaxNLPRB68					Integer32,
		phyULMaxNLPRB69					Integer32,
		phyULMaxNLPRB70					Integer32,
		phyULMaxNLPRB71					Integer32,
		phyULMaxNLPRB72					Integer32,
		phyULMaxNLPRB73					Integer32,
		phyULMaxNLPRB74					Integer32,
		phyULMaxNLPRB75					Integer32,
		phyULMaxNLPRB76					Integer32,
		phyULMaxNLPRB77					Integer32,
		phyULMaxNLPRB78					Integer32,
		phyULMaxNLPRB79					Integer32,
		phyULMaxNLPRB80					Integer32,
		phyULMaxNLPRB81					Integer32,
		phyULMaxNLPRB82					Integer32,
		phyULMaxNLPRB83					Integer32,
		phyULMaxNLPRB84					Integer32,
		phyULMaxNLPRB85					Integer32,
		phyULMaxNLPRB86					Integer32,
		phyULMaxNLPRB87					Integer32,
		phyULMaxNLPRB88					Integer32,
		phyULMaxNLPRB89					Integer32,
		phyULMaxNLPRB90					Integer32,
		phyULMaxNLPRB91					Integer32,
		phyULMaxNLPRB92					Integer32,
		phyULMaxNLPRB93					Integer32,
		phyULMaxNLPRB94					Integer32,
		phyULMaxNLPRB95					Integer32,
		phyULMaxNLPRB96					Integer32,
		phyULMaxNLPRB97					Integer32,
		phyULMaxNLPRB98					Integer32,
		phyULMaxNLPRB99					Integer32
		}


	cellmaxripperprbLcId		 OBJECT-TYPE
		SYNTAX					 Integer32( 0 .. 23 )
		MAX-ACCESS			 not-accessible
		STATUS					 current
		DESCRIPTION			 " -- "
		::=  { cellmaxripperprbEntry  1 }


	cellmaxripperprbRowStatus		 OBJECT-TYPE
		SYNTAX					 RowStatus
		MAX-ACCESS			 read-only
		STATUS					 current
		DESCRIPTION			 " -- "
		::=  { cellmaxripperprbEntry  2 }


	phyULMaxNLPRB00		 OBJECT-TYPE
		SYNTAX					 Integer32( -2147483648 .. 2147483647 )
		MAX-ACCESS			 read-only
		STATUS					 current
		DESCRIPTION			 " -- "
		::=  { cellmaxripperprbEntry  3 }


	phyULMaxNLPRB01		 OBJECT-TYPE
		SYNTAX					 Integer32( -2147483648 .. 2147483647 )
		MAX-ACCESS			 read-only
		STATUS					 current
		DESCRIPTION			 " -- "
		::=  { cellmaxripperprbEntry  4 }


	phyULMaxNLPRB02		 OBJECT-TYPE
		SYNTAX					 Integer32( -2147483648 .. 2147483647 )
		MAX-ACCESS			 read-only
		STATUS					 current
		DESCRIPTION			 " -- "
		::=  { cellmaxripperprbEntry  5 }


	phyULMaxNLPRB03		 OBJECT-TYPE
		SYNTAX					 Integer32( -2147483648 .. 2147483647 )
		MAX-ACCESS			 read-only
		STATUS					 current
		DESCRIPTION			 " -- "
		::=  { cellmaxripperprbEntry  6 }


	phyULMaxNLPRB04		 OBJECT-TYPE
		SYNTAX					 Integer32( -2147483648 .. 2147483647 )
		MAX-ACCESS			 read-only
		STATUS					 current
		DESCRIPTION			 " -- "
		::=  { cellmaxripperprbEntry  7 }


	phyULMaxNLPRB05		 OBJECT-TYPE
		SYNTAX					 Integer32( -2147483648 .. 2147483647 )
		MAX-ACCESS			 read-only
		STATUS					 current
		DESCRIPTION			 " -- "
		::=  { cellmaxripperprbEntry  8 }


	phyULMaxNLPRB06		 OBJECT-TYPE
		SYNTAX					 Integer32( -2147483648 .. 2147483647 )
		MAX-ACCESS			 read-only
		STATUS					 current
		DESCRIPTION			 " -- "
		::=  { cellmaxripperprbEntry  9 }


	phyULMaxNLPRB07		 OBJECT-TYPE
		SYNTAX					 Integer32( -2147483648 .. 2147483647 )
		MAX-ACCESS			 read-only
		STATUS					 current
		DESCRIPTION			 " -- "
		::=  { cellmaxripperprbEntry  10 }


	phyULMaxNLPRB08		 OBJECT-TYPE
		SYNTAX					 Integer32( -2147483648 .. 2147483647 )
		MAX-ACCESS			 read-only
		STATUS					 current
		DESCRIPTION			 " -- "
		::=  { cellmaxripperprbEntry  11 }


	phyULMaxNLPRB09		 OBJECT-TYPE
		SYNTAX					 Integer32( -2147483648 .. 2147483647 )
		MAX-ACCESS			 read-only
		STATUS					 current
		DESCRIPTION			 " -- "
		::=  { cellmaxripperprbEntry  12 }


	phyULMaxNLPRB10		 OBJECT-TYPE
		SYNTAX					 Integer32( -2147483648 .. 2147483647 )
		MAX-ACCESS			 read-only
		STATUS					 current
		DESCRIPTION			 " -- "
		::=  { cellmaxripperprbEntry  13 }


	phyULMaxNLPRB11		 OBJECT-TYPE
		SYNTAX					 Integer32( -2147483648 .. 2147483647 )
		MAX-ACCESS			 read-only
		STATUS					 current
		DESCRIPTION			 " -- "
		::=  { cellmaxripperprbEntry  14 }


	phyULMaxNLPRB12		 OBJECT-TYPE
		SYNTAX					 Integer32( -2147483648 .. 2147483647 )
		MAX-ACCESS			 read-only
		STATUS					 current
		DESCRIPTION			 " -- "
		::=  { cellmaxripperprbEntry  15 }


	phyULMaxNLPRB13		 OBJECT-TYPE
		SYNTAX					 Integer32( -2147483648 .. 2147483647 )
		MAX-ACCESS			 read-only
		STATUS					 current
		DESCRIPTION			 " -- "
		::=  { cellmaxripperprbEntry  16 }


	phyULMaxNLPRB14		 OBJECT-TYPE
		SYNTAX					 Integer32( -2147483648 .. 2147483647 )
		MAX-ACCESS			 read-only
		STATUS					 current
		DESCRIPTION			 " -- "
		::=  { cellmaxripperprbEntry  17 }


	phyULMaxNLPRB15		 OBJECT-TYPE
		SYNTAX					 Integer32( -2147483648 .. 2147483647 )
		MAX-ACCESS			 read-only
		STATUS					 current
		DESCRIPTION			 " -- "
		::=  { cellmaxripperprbEntry  18 }


	phyULMaxNLPRB16		 OBJECT-TYPE
		SYNTAX					 Integer32( -2147483648 .. 2147483647 )
		MAX-ACCESS			 read-only
		STATUS					 current
		DESCRIPTION			 " -- "
		::=  { cellmaxripperprbEntry  19 }


	phyULMaxNLPRB17		 OBJECT-TYPE
		SYNTAX					 Integer32( -2147483648 .. 2147483647 )
		MAX-ACCESS			 read-only
		STATUS					 current
		DESCRIPTION			 " -- "
		::=  { cellmaxripperprbEntry  20 }


	phyULMaxNLPRB18		 OBJECT-TYPE
		SYNTAX					 Integer32( -2147483648 .. 2147483647 )
		MAX-ACCESS			 read-only
		STATUS					 current
		DESCRIPTION			 " -- "
		::=  { cellmaxripperprbEntry  21 }


	phyULMaxNLPRB19		 OBJECT-TYPE
		SYNTAX					 Integer32( -2147483648 .. 2147483647 )
		MAX-ACCESS			 read-only
		STATUS					 current
		DESCRIPTION			 " -- "
		::=  { cellmaxripperprbEntry  22 }


	phyULMaxNLPRB20		 OBJECT-TYPE
		SYNTAX					 Integer32( -2147483648 .. 2147483647 )
		MAX-ACCESS			 read-only
		STATUS					 current
		DESCRIPTION			 " -- "
		::=  { cellmaxripperprbEntry  23 }


	phyULMaxNLPRB21		 OBJECT-TYPE
		SYNTAX					 Integer32( -2147483648 .. 2147483647 )
		MAX-ACCESS			 read-only
		STATUS					 current
		DESCRIPTION			 " -- "
		::=  { cellmaxripperprbEntry  24 }


	phyULMaxNLPRB22		 OBJECT-TYPE
		SYNTAX					 Integer32( -2147483648 .. 2147483647 )
		MAX-ACCESS			 read-only
		STATUS					 current
		DESCRIPTION			 " -- "
		::=  { cellmaxripperprbEntry  25 }


	phyULMaxNLPRB23		 OBJECT-TYPE
		SYNTAX					 Integer32( -2147483648 .. 2147483647 )
		MAX-ACCESS			 read-only
		STATUS					 current
		DESCRIPTION			 " -- "
		::=  { cellmaxripperprbEntry  26 }


	phyULMaxNLPRB24		 OBJECT-TYPE
		SYNTAX					 Integer32( -2147483648 .. 2147483647 )
		MAX-ACCESS			 read-only
		STATUS					 current
		DESCRIPTION			 " -- "
		::=  { cellmaxripperprbEntry  27 }


	phyULMaxNLPRB25		 OBJECT-TYPE
		SYNTAX					 Integer32( -2147483648 .. 2147483647 )
		MAX-ACCESS			 read-only
		STATUS					 current
		DESCRIPTION			 " -- "
		::=  { cellmaxripperprbEntry  28 }


	phyULMaxNLPRB26		 OBJECT-TYPE
		SYNTAX					 Integer32( -2147483648 .. 2147483647 )
		MAX-ACCESS			 read-only
		STATUS					 current
		DESCRIPTION			 " -- "
		::=  { cellmaxripperprbEntry  29 }


	phyULMaxNLPRB27		 OBJECT-TYPE
		SYNTAX					 Integer32( -2147483648 .. 2147483647 )
		MAX-ACCESS			 read-only
		STATUS					 current
		DESCRIPTION			 " -- "
		::=  { cellmaxripperprbEntry  30 }


	phyULMaxNLPRB28		 OBJECT-TYPE
		SYNTAX					 Integer32( -2147483648 .. 2147483647 )
		MAX-ACCESS			 read-only
		STATUS					 current
		DESCRIPTION			 " -- "
		::=  { cellmaxripperprbEntry  31 }


	phyULMaxNLPRB29		 OBJECT-TYPE
		SYNTAX					 Integer32( -2147483648 .. 2147483647 )
		MAX-ACCESS			 read-only
		STATUS					 current
		DESCRIPTION			 " -- "
		::=  { cellmaxripperprbEntry  32 }


	phyULMaxNLPRB30		 OBJECT-TYPE
		SYNTAX					 Integer32( -2147483648 .. 2147483647 )
		MAX-ACCESS			 read-only
		STATUS					 current
		DESCRIPTION			 " -- "
		::=  { cellmaxripperprbEntry  33 }


	phyULMaxNLPRB31		 OBJECT-TYPE
		SYNTAX					 Integer32( -2147483648 .. 2147483647 )
		MAX-ACCESS			 read-only
		STATUS					 current
		DESCRIPTION			 " -- "
		::=  { cellmaxripperprbEntry  34 }


	phyULMaxNLPRB32		 OBJECT-TYPE
		SYNTAX					 Integer32( -2147483648 .. 2147483647 )
		MAX-ACCESS			 read-only
		STATUS					 current
		DESCRIPTION			 " -- "
		::=  { cellmaxripperprbEntry  35 }


	phyULMaxNLPRB33		 OBJECT-TYPE
		SYNTAX					 Integer32( -2147483648 .. 2147483647 )
		MAX-ACCESS			 read-only
		STATUS					 current
		DESCRIPTION			 " -- "
		::=  { cellmaxripperprbEntry  36 }


	phyULMaxNLPRB34		 OBJECT-TYPE
		SYNTAX					 Integer32( -2147483648 .. 2147483647 )
		MAX-ACCESS			 read-only
		STATUS					 current
		DESCRIPTION			 " -- "
		::=  { cellmaxripperprbEntry  37 }


	phyULMaxNLPRB35		 OBJECT-TYPE
		SYNTAX					 Integer32( -2147483648 .. 2147483647 )
		MAX-ACCESS			 read-only
		STATUS					 current
		DESCRIPTION			 " -- "
		::=  { cellmaxripperprbEntry  38 }


	phyULMaxNLPRB36		 OBJECT-TYPE
		SYNTAX					 Integer32( -2147483648 .. 2147483647 )
		MAX-ACCESS			 read-only
		STATUS					 current
		DESCRIPTION			 " -- "
		::=  { cellmaxripperprbEntry  39 }


	phyULMaxNLPRB37		 OBJECT-TYPE
		SYNTAX					 Integer32( -2147483648 .. 2147483647 )
		MAX-ACCESS			 read-only
		STATUS					 current
		DESCRIPTION			 " -- "
		::=  { cellmaxripperprbEntry  40 }


	phyULMaxNLPRB38		 OBJECT-TYPE
		SYNTAX					 Integer32( -2147483648 .. 2147483647 )
		MAX-ACCESS			 read-only
		STATUS					 current
		DESCRIPTION			 " -- "
		::=  { cellmaxripperprbEntry  41 }


	phyULMaxNLPRB39		 OBJECT-TYPE
		SYNTAX					 Integer32( -2147483648 .. 2147483647 )
		MAX-ACCESS			 read-only
		STATUS					 current
		DESCRIPTION			 " -- "
		::=  { cellmaxripperprbEntry  42 }


	phyULMaxNLPRB40		 OBJECT-TYPE
		SYNTAX					 Integer32( -2147483648 .. 2147483647 )
		MAX-ACCESS			 read-only
		STATUS					 current
		DESCRIPTION			 " -- "
		::=  { cellmaxripperprbEntry  43 }


	phyULMaxNLPRB41		 OBJECT-TYPE
		SYNTAX					 Integer32( -2147483648 .. 2147483647 )
		MAX-ACCESS			 read-only
		STATUS					 current
		DESCRIPTION			 " -- "
		::=  { cellmaxripperprbEntry  44 }


	phyULMaxNLPRB42		 OBJECT-TYPE
		SYNTAX					 Integer32( -2147483648 .. 2147483647 )
		MAX-ACCESS			 read-only
		STATUS					 current
		DESCRIPTION			 " -- "
		::=  { cellmaxripperprbEntry  45 }


	phyULMaxNLPRB43		 OBJECT-TYPE
		SYNTAX					 Integer32( -2147483648 .. 2147483647 )
		MAX-ACCESS			 read-only
		STATUS					 current
		DESCRIPTION			 " -- "
		::=  { cellmaxripperprbEntry  46 }


	phyULMaxNLPRB44		 OBJECT-TYPE
		SYNTAX					 Integer32( -2147483648 .. 2147483647 )
		MAX-ACCESS			 read-only
		STATUS					 current
		DESCRIPTION			 " -- "
		::=  { cellmaxripperprbEntry  47 }


	phyULMaxNLPRB45		 OBJECT-TYPE
		SYNTAX					 Integer32( -2147483648 .. 2147483647 )
		MAX-ACCESS			 read-only
		STATUS					 current
		DESCRIPTION			 " -- "
		::=  { cellmaxripperprbEntry  48 }


	phyULMaxNLPRB46		 OBJECT-TYPE
		SYNTAX					 Integer32( -2147483648 .. 2147483647 )
		MAX-ACCESS			 read-only
		STATUS					 current
		DESCRIPTION			 " -- "
		::=  { cellmaxripperprbEntry  49 }


	phyULMaxNLPRB47		 OBJECT-TYPE
		SYNTAX					 Integer32( -2147483648 .. 2147483647 )
		MAX-ACCESS			 read-only
		STATUS					 current
		DESCRIPTION			 " -- "
		::=  { cellmaxripperprbEntry  50 }


	phyULMaxNLPRB48		 OBJECT-TYPE
		SYNTAX					 Integer32( -2147483648 .. 2147483647 )
		MAX-ACCESS			 read-only
		STATUS					 current
		DESCRIPTION			 " -- "
		::=  { cellmaxripperprbEntry  51 }


	phyULMaxNLPRB49		 OBJECT-TYPE
		SYNTAX					 Integer32( -2147483648 .. 2147483647 )
		MAX-ACCESS			 read-only
		STATUS					 current
		DESCRIPTION			 " -- "
		::=  { cellmaxripperprbEntry  52 }


	phyULMaxNLPRB50		 OBJECT-TYPE
		SYNTAX					 Integer32( -2147483648 .. 2147483647 )
		MAX-ACCESS			 read-only
		STATUS					 current
		DESCRIPTION			 " -- "
		::=  { cellmaxripperprbEntry  53 }


	phyULMaxNLPRB51		 OBJECT-TYPE
		SYNTAX					 Integer32( -2147483648 .. 2147483647 )
		MAX-ACCESS			 read-only
		STATUS					 current
		DESCRIPTION			 " -- "
		::=  { cellmaxripperprbEntry  54 }


	phyULMaxNLPRB52		 OBJECT-TYPE
		SYNTAX					 Integer32( -2147483648 .. 2147483647 )
		MAX-ACCESS			 read-only
		STATUS					 current
		DESCRIPTION			 " -- "
		::=  { cellmaxripperprbEntry  55 }


	phyULMaxNLPRB53		 OBJECT-TYPE
		SYNTAX					 Integer32( -2147483648 .. 2147483647 )
		MAX-ACCESS			 read-only
		STATUS					 current
		DESCRIPTION			 " -- "
		::=  { cellmaxripperprbEntry  56 }


	phyULMaxNLPRB54		 OBJECT-TYPE
		SYNTAX					 Integer32( -2147483648 .. 2147483647 )
		MAX-ACCESS			 read-only
		STATUS					 current
		DESCRIPTION			 " -- "
		::=  { cellmaxripperprbEntry  57 }


	phyULMaxNLPRB55		 OBJECT-TYPE
		SYNTAX					 Integer32( -2147483648 .. 2147483647 )
		MAX-ACCESS			 read-only
		STATUS					 current
		DESCRIPTION			 " -- "
		::=  { cellmaxripperprbEntry  58 }


	phyULMaxNLPRB56		 OBJECT-TYPE
		SYNTAX					 Integer32( -2147483648 .. 2147483647 )
		MAX-ACCESS			 read-only
		STATUS					 current
		DESCRIPTION			 " -- "
		::=  { cellmaxripperprbEntry  59 }


	phyULMaxNLPRB57		 OBJECT-TYPE
		SYNTAX					 Integer32( -2147483648 .. 2147483647 )
		MAX-ACCESS			 read-only
		STATUS					 current
		DESCRIPTION			 " -- "
		::=  { cellmaxripperprbEntry  60 }


	phyULMaxNLPRB58		 OBJECT-TYPE
		SYNTAX					 Integer32( -2147483648 .. 2147483647 )
		MAX-ACCESS			 read-only
		STATUS					 current
		DESCRIPTION			 " -- "
		::=  { cellmaxripperprbEntry  61 }


	phyULMaxNLPRB59		 OBJECT-TYPE
		SYNTAX					 Integer32( -2147483648 .. 2147483647 )
		MAX-ACCESS			 read-only
		STATUS					 current
		DESCRIPTION			 " -- "
		::=  { cellmaxripperprbEntry  62 }


	phyULMaxNLPRB60		 OBJECT-TYPE
		SYNTAX					 Integer32( -2147483648 .. 2147483647 )
		MAX-ACCESS			 read-only
		STATUS					 current
		DESCRIPTION			 " -- "
		::=  { cellmaxripperprbEntry  63 }


	phyULMaxNLPRB61		 OBJECT-TYPE
		SYNTAX					 Integer32( -2147483648 .. 2147483647 )
		MAX-ACCESS			 read-only
		STATUS					 current
		DESCRIPTION			 " -- "
		::=  { cellmaxripperprbEntry  64 }


	phyULMaxNLPRB62		 OBJECT-TYPE
		SYNTAX					 Integer32( -2147483648 .. 2147483647 )
		MAX-ACCESS			 read-only
		STATUS					 current
		DESCRIPTION			 " -- "
		::=  { cellmaxripperprbEntry  65 }


	phyULMaxNLPRB63		 OBJECT-TYPE
		SYNTAX					 Integer32( -2147483648 .. 2147483647 )
		MAX-ACCESS			 read-only
		STATUS					 current
		DESCRIPTION			 " -- "
		::=  { cellmaxripperprbEntry  66 }


	phyULMaxNLPRB64		 OBJECT-TYPE
		SYNTAX					 Integer32( -2147483648 .. 2147483647 )
		MAX-ACCESS			 read-only
		STATUS					 current
		DESCRIPTION			 " -- "
		::=  { cellmaxripperprbEntry  67 }


	phyULMaxNLPRB65		 OBJECT-TYPE
		SYNTAX					 Integer32( -2147483648 .. 2147483647 )
		MAX-ACCESS			 read-only
		STATUS					 current
		DESCRIPTION			 " -- "
		::=  { cellmaxripperprbEntry  68 }


	phyULMaxNLPRB66		 OBJECT-TYPE
		SYNTAX					 Integer32( -2147483648 .. 2147483647 )
		MAX-ACCESS			 read-only
		STATUS					 current
		DESCRIPTION			 " -- "
		::=  { cellmaxripperprbEntry  69 }


	phyULMaxNLPRB67		 OBJECT-TYPE
		SYNTAX					 Integer32( -2147483648 .. 2147483647 )
		MAX-ACCESS			 read-only
		STATUS					 current
		DESCRIPTION			 " -- "
		::=  { cellmaxripperprbEntry  70 }


	phyULMaxNLPRB68		 OBJECT-TYPE
		SYNTAX					 Integer32( -2147483648 .. 2147483647 )
		MAX-ACCESS			 read-only
		STATUS					 current
		DESCRIPTION			 " -- "
		::=  { cellmaxripperprbEntry  71 }


	phyULMaxNLPRB69		 OBJECT-TYPE
		SYNTAX					 Integer32( -2147483648 .. 2147483647 )
		MAX-ACCESS			 read-only
		STATUS					 current
		DESCRIPTION			 " -- "
		::=  { cellmaxripperprbEntry  72 }


	phyULMaxNLPRB70		 OBJECT-TYPE
		SYNTAX					 Integer32( -2147483648 .. 2147483647 )
		MAX-ACCESS			 read-only
		STATUS					 current
		DESCRIPTION			 " -- "
		::=  { cellmaxripperprbEntry  73 }


	phyULMaxNLPRB71		 OBJECT-TYPE
		SYNTAX					 Integer32( -2147483648 .. 2147483647 )
		MAX-ACCESS			 read-only
		STATUS					 current
		DESCRIPTION			 " -- "
		::=  { cellmaxripperprbEntry  74 }


	phyULMaxNLPRB72		 OBJECT-TYPE
		SYNTAX					 Integer32( -2147483648 .. 2147483647 )
		MAX-ACCESS			 read-only
		STATUS					 current
		DESCRIPTION			 " -- "
		::=  { cellmaxripperprbEntry  75 }


	phyULMaxNLPRB73		 OBJECT-TYPE
		SYNTAX					 Integer32( -2147483648 .. 2147483647 )
		MAX-ACCESS			 read-only
		STATUS					 current
		DESCRIPTION			 " -- "
		::=  { cellmaxripperprbEntry  76 }


	phyULMaxNLPRB74		 OBJECT-TYPE
		SYNTAX					 Integer32( -2147483648 .. 2147483647 )
		MAX-ACCESS			 read-only
		STATUS					 current
		DESCRIPTION			 " -- "
		::=  { cellmaxripperprbEntry  77 }


	phyULMaxNLPRB75		 OBJECT-TYPE
		SYNTAX					 Integer32( -2147483648 .. 2147483647 )
		MAX-ACCESS			 read-only
		STATUS					 current
		DESCRIPTION			 " -- "
		::=  { cellmaxripperprbEntry  78 }


	phyULMaxNLPRB76		 OBJECT-TYPE
		SYNTAX					 Integer32( -2147483648 .. 2147483647 )
		MAX-ACCESS			 read-only
		STATUS					 current
		DESCRIPTION			 " -- "
		::=  { cellmaxripperprbEntry  79 }


	phyULMaxNLPRB77		 OBJECT-TYPE
		SYNTAX					 Integer32( -2147483648 .. 2147483647 )
		MAX-ACCESS			 read-only
		STATUS					 current
		DESCRIPTION			 " -- "
		::=  { cellmaxripperprbEntry  80 }


	phyULMaxNLPRB78		 OBJECT-TYPE
		SYNTAX					 Integer32( -2147483648 .. 2147483647 )
		MAX-ACCESS			 read-only
		STATUS					 current
		DESCRIPTION			 " -- "
		::=  { cellmaxripperprbEntry  81 }


	phyULMaxNLPRB79		 OBJECT-TYPE
		SYNTAX					 Integer32( -2147483648 .. 2147483647 )
		MAX-ACCESS			 read-only
		STATUS					 current
		DESCRIPTION			 " -- "
		::=  { cellmaxripperprbEntry  82 }


	phyULMaxNLPRB80		 OBJECT-TYPE
		SYNTAX					 Integer32( -2147483648 .. 2147483647 )
		MAX-ACCESS			 read-only
		STATUS					 current
		DESCRIPTION			 " -- "
		::=  { cellmaxripperprbEntry  83 }


	phyULMaxNLPRB81		 OBJECT-TYPE
		SYNTAX					 Integer32( -2147483648 .. 2147483647 )
		MAX-ACCESS			 read-only
		STATUS					 current
		DESCRIPTION			 " -- "
		::=  { cellmaxripperprbEntry  84 }


	phyULMaxNLPRB82		 OBJECT-TYPE
		SYNTAX					 Integer32( -2147483648 .. 2147483647 )
		MAX-ACCESS			 read-only
		STATUS					 current
		DESCRIPTION			 " -- "
		::=  { cellmaxripperprbEntry  85 }


	phyULMaxNLPRB83		 OBJECT-TYPE
		SYNTAX					 Integer32( -2147483648 .. 2147483647 )
		MAX-ACCESS			 read-only
		STATUS					 current
		DESCRIPTION			 " -- "
		::=  { cellmaxripperprbEntry  86 }


	phyULMaxNLPRB84		 OBJECT-TYPE
		SYNTAX					 Integer32( -2147483648 .. 2147483647 )
		MAX-ACCESS			 read-only
		STATUS					 current
		DESCRIPTION			 " -- "
		::=  { cellmaxripperprbEntry  87 }


	phyULMaxNLPRB85		 OBJECT-TYPE
		SYNTAX					 Integer32( -2147483648 .. 2147483647 )
		MAX-ACCESS			 read-only
		STATUS					 current
		DESCRIPTION			 " -- "
		::=  { cellmaxripperprbEntry  88 }


	phyULMaxNLPRB86		 OBJECT-TYPE
		SYNTAX					 Integer32( -2147483648 .. 2147483647 )
		MAX-ACCESS			 read-only
		STATUS					 current
		DESCRIPTION			 " -- "
		::=  { cellmaxripperprbEntry  89 }


	phyULMaxNLPRB87		 OBJECT-TYPE
		SYNTAX					 Integer32( -2147483648 .. 2147483647 )
		MAX-ACCESS			 read-only
		STATUS					 current
		DESCRIPTION			 " -- "
		::=  { cellmaxripperprbEntry  90 }


	phyULMaxNLPRB88		 OBJECT-TYPE
		SYNTAX					 Integer32( -2147483648 .. 2147483647 )
		MAX-ACCESS			 read-only
		STATUS					 current
		DESCRIPTION			 " -- "
		::=  { cellmaxripperprbEntry  91 }


	phyULMaxNLPRB89		 OBJECT-TYPE
		SYNTAX					 Integer32( -2147483648 .. 2147483647 )
		MAX-ACCESS			 read-only
		STATUS					 current
		DESCRIPTION			 " -- "
		::=  { cellmaxripperprbEntry  92 }


	phyULMaxNLPRB90		 OBJECT-TYPE
		SYNTAX					 Integer32( -2147483648 .. 2147483647 )
		MAX-ACCESS			 read-only
		STATUS					 current
		DESCRIPTION			 " -- "
		::=  { cellmaxripperprbEntry  93 }


	phyULMaxNLPRB91		 OBJECT-TYPE
		SYNTAX					 Integer32( -2147483648 .. 2147483647 )
		MAX-ACCESS			 read-only
		STATUS					 current
		DESCRIPTION			 " -- "
		::=  { cellmaxripperprbEntry  94 }


	phyULMaxNLPRB92		 OBJECT-TYPE
		SYNTAX					 Integer32( -2147483648 .. 2147483647 )
		MAX-ACCESS			 read-only
		STATUS					 current
		DESCRIPTION			 " -- "
		::=  { cellmaxripperprbEntry  95 }


	phyULMaxNLPRB93		 OBJECT-TYPE
		SYNTAX					 Integer32( -2147483648 .. 2147483647 )
		MAX-ACCESS			 read-only
		STATUS					 current
		DESCRIPTION			 " -- "
		::=  { cellmaxripperprbEntry  96 }


	phyULMaxNLPRB94		 OBJECT-TYPE
		SYNTAX					 Integer32( -2147483648 .. 2147483647 )
		MAX-ACCESS			 read-only
		STATUS					 current
		DESCRIPTION			 " -- "
		::=  { cellmaxripperprbEntry  97 }


	phyULMaxNLPRB95		 OBJECT-TYPE
		SYNTAX					 Integer32( -2147483648 .. 2147483647 )
		MAX-ACCESS			 read-only
		STATUS					 current
		DESCRIPTION			 " -- "
		::=  { cellmaxripperprbEntry  98 }


	phyULMaxNLPRB96		 OBJECT-TYPE
		SYNTAX					 Integer32( -2147483648 .. 2147483647 )
		MAX-ACCESS			 read-only
		STATUS					 current
		DESCRIPTION			 " -- "
		::=  { cellmaxripperprbEntry  99 }


	phyULMaxNLPRB97		 OBJECT-TYPE
		SYNTAX					 Integer32( -2147483648 .. 2147483647 )
		MAX-ACCESS			 read-only
		STATUS					 current
		DESCRIPTION			 " -- "
		::=  { cellmaxripperprbEntry  100 }


	phyULMaxNLPRB98		 OBJECT-TYPE
		SYNTAX					 Integer32( -2147483648 .. 2147483647 )
		MAX-ACCESS			 read-only
		STATUS					 current
		DESCRIPTION			 " -- "
		::=  { cellmaxripperprbEntry  101 }


	phyULMaxNLPRB99		 OBJECT-TYPE
		SYNTAX					 Integer32( -2147483648 .. 2147483647 )
		MAX-ACCESS			 read-only
		STATUS					 current
		DESCRIPTION			 " -- "
		::=  { cellmaxripperprbEntry  102 }


	plThroughputCapacityULTable		 OBJECT-TYPE
		SYNTAX					 SEQUENCE  OF	 PlThroughputCapacityULEntry
		MAX-ACCESS			 not-accessible
		STATUS					 current
		DESCRIPTION			 " -- "
		::=  { plrelatedOriginCounter  19 }


	plThroughputCapacityULEntry		 OBJECT-TYPE
		SYNTAX					 PlThroughputCapacityULEntry
		MAX-ACCESS			 not-accessible
		STATUS					 current
		DESCRIPTION			 " -- "
		INDEX						{ plThroughputCapacityULLcId }
		::=  { plThroughputCapacityULTable  1 }


	PlThroughputCapacityULEntry		 ::=  SEQUENCE {
		plThroughputCapacityULLcId					Integer32,
		plThroughputCapacityULRowStatus					RowStatus,
		plThroughputUL					Counter32
		}


	plThroughputCapacityULLcId		 OBJECT-TYPE
		SYNTAX					 Integer32( 0 .. 23 )
		MAX-ACCESS			 not-accessible
		STATUS					 current
		DESCRIPTION			 " -- "
		::=  { plThroughputCapacityULEntry  1 }


	plThroughputCapacityULRowStatus		 OBJECT-TYPE
		SYNTAX					 RowStatus
		MAX-ACCESS			 read-only
		STATUS					 current
		DESCRIPTION			 " -- "
		::=  { plThroughputCapacityULEntry  2 }


	plThroughputUL		 OBJECT-TYPE
		SYNTAX					 Counter32
		MAX-ACCESS			 read-only
		STATUS					 current
		DESCRIPTION			 " -- "
		::=  { plThroughputCapacityULEntry  3 }


	plThroughputCapacityDLTable		 OBJECT-TYPE
		SYNTAX					 SEQUENCE  OF	 PlThroughputCapacityDLEntry
		MAX-ACCESS			 not-accessible
		STATUS					 current
		DESCRIPTION			 " -- "
		::=  { plrelatedOriginCounter  20 }


	plThroughputCapacityDLEntry		 OBJECT-TYPE
		SYNTAX					 PlThroughputCapacityDLEntry
		MAX-ACCESS			 not-accessible
		STATUS					 current
		DESCRIPTION			 " -- "
		INDEX						{ plThroughputCapacityDLLcId }
		::=  { plThroughputCapacityDLTable  1 }


	PlThroughputCapacityDLEntry		 ::=  SEQUENCE {
		plThroughputCapacityDLLcId					Integer32,
		plThroughputCapacityDLRowStatus					RowStatus,
		plThroughputDL					Counter32
		}


	plThroughputCapacityDLLcId		 OBJECT-TYPE
		SYNTAX					 Integer32( 0 .. 23 )
		MAX-ACCESS			 not-accessible
		STATUS					 current
		DESCRIPTION			 " -- "
		::=  { plThroughputCapacityDLEntry  1 }


	plThroughputCapacityDLRowStatus		 OBJECT-TYPE
		SYNTAX					 RowStatus
		MAX-ACCESS			 read-only
		STATUS					 current
		DESCRIPTION			 " -- "
		::=  { plThroughputCapacityDLEntry  2 }


	plThroughputDL		 OBJECT-TYPE
		SYNTAX					 Counter32
		MAX-ACCESS			 read-only
		STATUS					 current
		DESCRIPTION			 " -- "
		::=  { plThroughputCapacityDLEntry  3 }


	cellavgripTable		 OBJECT-TYPE
		SYNTAX					 SEQUENCE  OF	 CellavgripEntry
		MAX-ACCESS			 not-accessible
		STATUS					 current
		DESCRIPTION			 " -- "
		::=  { plrelatedOriginCounter  21 }


	cellavgripEntry		 OBJECT-TYPE
		SYNTAX					 CellavgripEntry
		MAX-ACCESS			 not-accessible
		STATUS					 current
		DESCRIPTION			 " -- "
		INDEX						{ cellavgripLcId }
		::=  { cellavgripTable  1 }


	CellavgripEntry		 ::=  SEQUENCE {
		cellavgripLcId					Integer32,
		cellavgripRowStatus					RowStatus,
		phyULMeanRIP					Integer32
		}


	cellavgripLcId		 OBJECT-TYPE
		SYNTAX					 Integer32( 0 .. 23 )
		MAX-ACCESS			 not-accessible
		STATUS					 current
		DESCRIPTION			 " -- "
		::=  { cellavgripEntry  1 }


	cellavgripRowStatus		 OBJECT-TYPE
		SYNTAX					 RowStatus
		MAX-ACCESS			 read-only
		STATUS					 current
		DESCRIPTION			 " -- "
		::=  { cellavgripEntry  2 }


	phyULMeanRIP		 OBJECT-TYPE
		SYNTAX					 Integer32( -2147483648 .. 2147483647 )
		MAX-ACCESS			 read-only
		STATUS					 current
		DESCRIPTION			 " -- "
		::=  { cellavgripEntry  3 }


	plrssiIndexTable		 OBJECT-TYPE
		SYNTAX					 SEQUENCE  OF	 PlrssiIndexEntry
		MAX-ACCESS			 not-accessible
		STATUS					 current
		DESCRIPTION			 " -- "
		::=  { plrelatedOriginCounter  22 }


	plrssiIndexEntry		 OBJECT-TYPE
		SYNTAX					 PlrssiIndexEntry
		MAX-ACCESS			 not-accessible
		STATUS					 current
		DESCRIPTION			 " -- "
		INDEX						{ plrssiIndexLcId }
		::=  { plrssiIndexTable  1 }


	PlrssiIndexEntry		 ::=  SEQUENCE {
		plrssiIndexLcId					Integer32,
		plrssiIndexRowStatus					RowStatus,
		plReceivePowerIndex0					Counter32,
		plReceivePowerIndex1					Counter32,
		plReceivePowerIndex2					Counter32,
		plReceivePowerIndex3					Counter32,
		plReceivePowerIndex4					Counter32,
		plReceivePowerIndex5					Counter32,
		plReceivePowerIndex6					Counter32,
		plReceivePowerIndex7					Counter32,
		plReceivePowerIndex8					Counter32,
		plReceivePowerIndex9					Counter32,
		plReceivePowerIndex10					Counter32,
		plReceivePowerIndex11					Counter32,
		plReceivePowerIndex12					Counter32,
		plReceivePowerIndex13					Counter32,
		plReceivePowerIndex14					Counter32,
		plReceivePowerIndex15					Counter32,
		plReceivePowerIndex16					Counter32,
		plReceivePowerIndex17					Counter32,
		plReceivePowerIndex18					Counter32,
		plReceivePowerIndex19					Counter32,
		plReceivePowerIndex20					Counter32,
		plReceivePowerIndex21					Counter32,
		plReceivePowerIndex22					Counter32,
		plReceivePowerIndex23					Counter32,
		plReceivePowerIndex24					Counter32,
		plReceivePowerUserIndex0					Counter32,
		plReceivePowerUserIndex1					Counter32,
		plReceivePowerUserIndex2					Counter32,
		plReceivePowerUserIndex3					Counter32,
		plReceivePowerUserIndex4					Counter32,
		plReceivePowerUserIndex5					Counter32,
		plReceivePowerUserIndex6					Counter32,
		plReceivePowerUserIndex7					Counter32,
		plReceivePowerUserIndex8					Counter32,
		plReceivePowerUserIndex9					Counter32,
		plReceivePowerUserIndex10					Counter32,
		plReceivePowerUserIndex11					Counter32,
		plReceivePowerUserIndex12					Counter32,
		plReceivePowerUserIndex13					Counter32,
		plReceivePowerUserIndex14					Counter32,
		plReceivePowerUserIndex15					Counter32,
		plReceivePowerUserIndex16					Counter32,
		plReceivePowerUserIndex17					Counter32,
		plReceivePowerUserIndex18					Counter32,
		plReceivePowerUserIndex19					Counter32,
		plReceivePowerUserIndex20					Counter32,
		plReceivePowerUserIndex21					Counter32,
		plReceivePowerUserIndex22					Counter32,
		plReceivePowerUserIndex23					Counter32,
		plReceivePowerUserIndex24					Counter32
		}


	plrssiIndexLcId		 OBJECT-TYPE
		SYNTAX					 Integer32( 0 .. 23 )
		MAX-ACCESS			 not-accessible
		STATUS					 current
		DESCRIPTION			 " -- "
		::=  { plrssiIndexEntry  1 }


	plrssiIndexRowStatus		 OBJECT-TYPE
		SYNTAX					 RowStatus
		MAX-ACCESS			 read-only
		STATUS					 current
		DESCRIPTION			 " -- "
		::=  { plrssiIndexEntry  2 }


	plReceivePowerIndex0		 OBJECT-TYPE
		SYNTAX					 Counter32
		MAX-ACCESS			 read-only
		STATUS					 current
		DESCRIPTION			 " -- "
		::=  { plrssiIndexEntry  3 }


	plReceivePowerIndex1		 OBJECT-TYPE
		SYNTAX					 Counter32
		MAX-ACCESS			 read-only
		STATUS					 current
		DESCRIPTION			 " -- "
		::=  { plrssiIndexEntry  4 }


	plReceivePowerIndex2		 OBJECT-TYPE
		SYNTAX					 Counter32
		MAX-ACCESS			 read-only
		STATUS					 current
		DESCRIPTION			 " -- "
		::=  { plrssiIndexEntry  5 }


	plReceivePowerIndex3		 OBJECT-TYPE
		SYNTAX					 Counter32
		MAX-ACCESS			 read-only
		STATUS					 current
		DESCRIPTION			 " -- "
		::=  { plrssiIndexEntry  6 }


	plReceivePowerIndex4		 OBJECT-TYPE
		SYNTAX					 Counter32
		MAX-ACCESS			 read-only
		STATUS					 current
		DESCRIPTION			 " -- "
		::=  { plrssiIndexEntry  7 }


	plReceivePowerIndex5		 OBJECT-TYPE
		SYNTAX					 Counter32
		MAX-ACCESS			 read-only
		STATUS					 current
		DESCRIPTION			 " -- "
		::=  { plrssiIndexEntry  8 }


	plReceivePowerIndex6		 OBJECT-TYPE
		SYNTAX					 Counter32
		MAX-ACCESS			 read-only
		STATUS					 current
		DESCRIPTION			 " -- "
		::=  { plrssiIndexEntry  9 }


	plReceivePowerIndex7		 OBJECT-TYPE
		SYNTAX					 Counter32
		MAX-ACCESS			 read-only
		STATUS					 current
		DESCRIPTION			 " -- "
		::=  { plrssiIndexEntry  10 }


	plReceivePowerIndex8		 OBJECT-TYPE
		SYNTAX					 Counter32
		MAX-ACCESS			 read-only
		STATUS					 current
		DESCRIPTION			 " -- "
		::=  { plrssiIndexEntry  11 }


	plReceivePowerIndex9		 OBJECT-TYPE
		SYNTAX					 Counter32
		MAX-ACCESS			 read-only
		STATUS					 current
		DESCRIPTION			 " -- "
		::=  { plrssiIndexEntry  12 }


	plReceivePowerIndex10		 OBJECT-TYPE
		SYNTAX					 Counter32
		MAX-ACCESS			 read-only
		STATUS					 current
		DESCRIPTION			 " -- "
		::=  { plrssiIndexEntry  13 }


	plReceivePowerIndex11		 OBJECT-TYPE
		SYNTAX					 Counter32
		MAX-ACCESS			 read-only
		STATUS					 current
		DESCRIPTION			 " -- "
		::=  { plrssiIndexEntry  14 }


	plReceivePowerIndex12		 OBJECT-TYPE
		SYNTAX					 Counter32
		MAX-ACCESS			 read-only
		STATUS					 current
		DESCRIPTION			 " -- "
		::=  { plrssiIndexEntry  15 }


	plReceivePowerIndex13		 OBJECT-TYPE
		SYNTAX					 Counter32
		MAX-ACCESS			 read-only
		STATUS					 current
		DESCRIPTION			 " -- "
		::=  { plrssiIndexEntry  16 }


	plReceivePowerIndex14		 OBJECT-TYPE
		SYNTAX					 Counter32
		MAX-ACCESS			 read-only
		STATUS					 current
		DESCRIPTION			 " -- "
		::=  { plrssiIndexEntry  17 }


	plReceivePowerIndex15		 OBJECT-TYPE
		SYNTAX					 Counter32
		MAX-ACCESS			 read-only
		STATUS					 current
		DESCRIPTION			 " -- "
		::=  { plrssiIndexEntry  18 }


	plReceivePowerIndex16		 OBJECT-TYPE
		SYNTAX					 Counter32
		MAX-ACCESS			 read-only
		STATUS					 current
		DESCRIPTION			 " -- "
		::=  { plrssiIndexEntry  19 }


	plReceivePowerIndex17		 OBJECT-TYPE
		SYNTAX					 Counter32
		MAX-ACCESS			 read-only
		STATUS					 current
		DESCRIPTION			 " -- "
		::=  { plrssiIndexEntry  20 }


	plReceivePowerIndex18		 OBJECT-TYPE
		SYNTAX					 Counter32
		MAX-ACCESS			 read-only
		STATUS					 current
		DESCRIPTION			 " -- "
		::=  { plrssiIndexEntry  21 }


	plReceivePowerIndex19		 OBJECT-TYPE
		SYNTAX					 Counter32
		MAX-ACCESS			 read-only
		STATUS					 current
		DESCRIPTION			 " -- "
		::=  { plrssiIndexEntry  22 }


	plReceivePowerIndex20		 OBJECT-TYPE
		SYNTAX					 Counter32
		MAX-ACCESS			 read-only
		STATUS					 current
		DESCRIPTION			 " -- "
		::=  { plrssiIndexEntry  23 }


	plReceivePowerIndex21		 OBJECT-TYPE
		SYNTAX					 Counter32
		MAX-ACCESS			 read-only
		STATUS					 current
		DESCRIPTION			 " -- "
		::=  { plrssiIndexEntry  24 }


	plReceivePowerIndex22		 OBJECT-TYPE
		SYNTAX					 Counter32
		MAX-ACCESS			 read-only
		STATUS					 current
		DESCRIPTION			 " -- "
		::=  { plrssiIndexEntry  25 }


	plReceivePowerIndex23		 OBJECT-TYPE
		SYNTAX					 Counter32
		MAX-ACCESS			 read-only
		STATUS					 current
		DESCRIPTION			 " -- "
		::=  { plrssiIndexEntry  26 }


	plReceivePowerIndex24		 OBJECT-TYPE
		SYNTAX					 Counter32
		MAX-ACCESS			 read-only
		STATUS					 current
		DESCRIPTION			 " -- "
		::=  { plrssiIndexEntry  27 }


	plReceivePowerUserIndex0		 OBJECT-TYPE
		SYNTAX					 Counter32
		MAX-ACCESS			 read-only
		STATUS					 current
		DESCRIPTION			 " -- "
		::=  { plrssiIndexEntry  28 }


	plReceivePowerUserIndex1		 OBJECT-TYPE
		SYNTAX					 Counter32
		MAX-ACCESS			 read-only
		STATUS					 current
		DESCRIPTION			 " -- "
		::=  { plrssiIndexEntry  29 }


	plReceivePowerUserIndex2		 OBJECT-TYPE
		SYNTAX					 Counter32
		MAX-ACCESS			 read-only
		STATUS					 current
		DESCRIPTION			 " -- "
		::=  { plrssiIndexEntry  30 }


	plReceivePowerUserIndex3		 OBJECT-TYPE
		SYNTAX					 Counter32
		MAX-ACCESS			 read-only
		STATUS					 current
		DESCRIPTION			 " -- "
		::=  { plrssiIndexEntry  31 }


	plReceivePowerUserIndex4		 OBJECT-TYPE
		SYNTAX					 Counter32
		MAX-ACCESS			 read-only
		STATUS					 current
		DESCRIPTION			 " -- "
		::=  { plrssiIndexEntry  32 }


	plReceivePowerUserIndex5		 OBJECT-TYPE
		SYNTAX					 Counter32
		MAX-ACCESS			 read-only
		STATUS					 current
		DESCRIPTION			 " -- "
		::=  { plrssiIndexEntry  33 }


	plReceivePowerUserIndex6		 OBJECT-TYPE
		SYNTAX					 Counter32
		MAX-ACCESS			 read-only
		STATUS					 current
		DESCRIPTION			 " -- "
		::=  { plrssiIndexEntry  34 }


	plReceivePowerUserIndex7		 OBJECT-TYPE
		SYNTAX					 Counter32
		MAX-ACCESS			 read-only
		STATUS					 current
		DESCRIPTION			 " -- "
		::=  { plrssiIndexEntry  35 }


	plReceivePowerUserIndex8		 OBJECT-TYPE
		SYNTAX					 Counter32
		MAX-ACCESS			 read-only
		STATUS					 current
		DESCRIPTION			 " -- "
		::=  { plrssiIndexEntry  36 }


	plReceivePowerUserIndex9		 OBJECT-TYPE
		SYNTAX					 Counter32
		MAX-ACCESS			 read-only
		STATUS					 current
		DESCRIPTION			 " -- "
		::=  { plrssiIndexEntry  37 }


	plReceivePowerUserIndex10		 OBJECT-TYPE
		SYNTAX					 Counter32
		MAX-ACCESS			 read-only
		STATUS					 current
		DESCRIPTION			 " -- "
		::=  { plrssiIndexEntry  38 }


	plReceivePowerUserIndex11		 OBJECT-TYPE
		SYNTAX					 Counter32
		MAX-ACCESS			 read-only
		STATUS					 current
		DESCRIPTION			 " -- "
		::=  { plrssiIndexEntry  39 }


	plReceivePowerUserIndex12		 OBJECT-TYPE
		SYNTAX					 Counter32
		MAX-ACCESS			 read-only
		STATUS					 current
		DESCRIPTION			 " -- "
		::=  { plrssiIndexEntry  40 }


	plReceivePowerUserIndex13		 OBJECT-TYPE
		SYNTAX					 Counter32
		MAX-ACCESS			 read-only
		STATUS					 current
		DESCRIPTION			 " -- "
		::=  { plrssiIndexEntry  41 }


	plReceivePowerUserIndex14		 OBJECT-TYPE
		SYNTAX					 Counter32
		MAX-ACCESS			 read-only
		STATUS					 current
		DESCRIPTION			 " -- "
		::=  { plrssiIndexEntry  42 }


	plReceivePowerUserIndex15		 OBJECT-TYPE
		SYNTAX					 Counter32
		MAX-ACCESS			 read-only
		STATUS					 current
		DESCRIPTION			 " -- "
		::=  { plrssiIndexEntry  43 }


	plReceivePowerUserIndex16		 OBJECT-TYPE
		SYNTAX					 Counter32
		MAX-ACCESS			 read-only
		STATUS					 current
		DESCRIPTION			 " -- "
		::=  { plrssiIndexEntry  44 }


	plReceivePowerUserIndex17		 OBJECT-TYPE
		SYNTAX					 Counter32
		MAX-ACCESS			 read-only
		STATUS					 current
		DESCRIPTION			 " -- "
		::=  { plrssiIndexEntry  45 }


	plReceivePowerUserIndex18		 OBJECT-TYPE
		SYNTAX					 Counter32
		MAX-ACCESS			 read-only
		STATUS					 current
		DESCRIPTION			 " -- "
		::=  { plrssiIndexEntry  46 }


	plReceivePowerUserIndex19		 OBJECT-TYPE
		SYNTAX					 Counter32
		MAX-ACCESS			 read-only
		STATUS					 current
		DESCRIPTION			 " -- "
		::=  { plrssiIndexEntry  47 }


	plReceivePowerUserIndex20		 OBJECT-TYPE
		SYNTAX					 Counter32
		MAX-ACCESS			 read-only
		STATUS					 current
		DESCRIPTION			 " -- "
		::=  { plrssiIndexEntry  48 }


	plReceivePowerUserIndex21		 OBJECT-TYPE
		SYNTAX					 Counter32
		MAX-ACCESS			 read-only
		STATUS					 current
		DESCRIPTION			 " -- "
		::=  { plrssiIndexEntry  49 }


	plReceivePowerUserIndex22		 OBJECT-TYPE
		SYNTAX					 Counter32
		MAX-ACCESS			 read-only
		STATUS					 current
		DESCRIPTION			 " -- "
		::=  { plrssiIndexEntry  50 }


	plReceivePowerUserIndex23		 OBJECT-TYPE
		SYNTAX					 Counter32
		MAX-ACCESS			 read-only
		STATUS					 current
		DESCRIPTION			 " -- "
		::=  { plrssiIndexEntry  51 }


	plReceivePowerUserIndex24		 OBJECT-TYPE
		SYNTAX					 Counter32
		MAX-ACCESS			 read-only
		STATUS					 current
		DESCRIPTION			 " -- "
		::=  { plrssiIndexEntry  52 }


	omrelatedOriginCounter		 OBJECT IDENTIFIER
		::=  { pmOriginCounterGrpInfo  6 }


	s1InterfaceIPStatTable		 OBJECT-TYPE
		SYNTAX					 SEQUENCE  OF	 S1InterfaceIPStatEntry
		MAX-ACCESS			 not-accessible
		STATUS					 current
		DESCRIPTION			 " -- "
		::=  { omrelatedOriginCounter  1 }


	s1InterfaceIPStatEntry		 OBJECT-TYPE
		SYNTAX					 S1InterfaceIPStatEntry
		MAX-ACCESS			 not-accessible
		STATUS					 current
		DESCRIPTION			 " -- "
		INDEX						{ s1InterfaceIPStatEthRackNo,s1InterfaceIPStatEthShelfNo,s1InterfaceIPStatEthSlotNo,s1InterfaceIPStatEthPhyPortId }
		::=  { s1InterfaceIPStatTable  1 }


	S1InterfaceIPStatEntry		 ::=  SEQUENCE {
		s1InterfaceIPStatEthRackNo					Integer32,
		s1InterfaceIPStatEthShelfNo					Integer32,
		s1InterfaceIPStatEthSlotNo					Integer32,
		s1InterfaceIPStatEthPhyPortId					Integer32,
		s1InterfaceIPStatRowStatus					RowStatus,
		s1InNbrOctets					Counter32,
		s1OutNbrOctets					Counter32
		}


	s1InterfaceIPStatEthRackNo		 OBJECT-TYPE
		SYNTAX					 Integer32( 0 .. 0 )
		MAX-ACCESS			 not-accessible
		STATUS					 current
		DESCRIPTION			 " -- "
		::=  { s1InterfaceIPStatEntry  1 }


	s1InterfaceIPStatEthShelfNo		 OBJECT-TYPE
		SYNTAX					 Integer32( 0 .. 0 )
		MAX-ACCESS			 not-accessible
		STATUS					 current
		DESCRIPTION			 " -- "
		::=  { s1InterfaceIPStatEntry  2 }


	s1InterfaceIPStatEthSlotNo		 OBJECT-TYPE
		SYNTAX					 Integer32( 0 .. 1 )
		MAX-ACCESS			 not-accessible
		STATUS					 current
		DESCRIPTION			 " -- "
		::=  { s1InterfaceIPStatEntry  3 }


	s1InterfaceIPStatEthPhyPortId		 OBJECT-TYPE
		SYNTAX					 Integer32( 0 .. 1 )
		MAX-ACCESS			 not-accessible
		STATUS					 current
		DESCRIPTION			 " -- "
		::=  { s1InterfaceIPStatEntry  4 }


	s1InterfaceIPStatRowStatus		 OBJECT-TYPE
		SYNTAX					 RowStatus
		MAX-ACCESS			 read-only
		STATUS					 current
		DESCRIPTION			 " -- "
		::=  { s1InterfaceIPStatEntry  5 }


	s1InNbrOctets		 OBJECT-TYPE
		SYNTAX					 Counter32
		MAX-ACCESS			 read-only
		STATUS					 current
		DESCRIPTION			 " -- "
		::=  { s1InterfaceIPStatEntry  6 }


	s1OutNbrOctets		 OBJECT-TYPE
		SYNTAX					 Counter32
		MAX-ACCESS			 read-only
		STATUS					 current
		DESCRIPTION			 " -- "
		::=  { s1InterfaceIPStatEntry  7 }


	s1InterfaceTrafficStat		 OBJECT IDENTIFIER
		::=  { omrelatedOriginCounter  2 }


	s1InNbrOctetsUserPlane		 OBJECT-TYPE
		SYNTAX					 Counter32
		MAX-ACCESS			 read-only
		STATUS					 current
		DESCRIPTION			 " -- "
		::=  { s1InterfaceTrafficStat  1 }


	s1OutNbrOctetsUserPlane		 OBJECT-TYPE
		SYNTAX					 Counter32
		MAX-ACCESS			 read-only
		STATUS					 current
		DESCRIPTION			 " -- "
		::=  { s1InterfaceTrafficStat  2 }


	x2InterfaceTrafficStat		 OBJECT IDENTIFIER
		::=  { omrelatedOriginCounter  3 }


	x2InNbrOctets		 OBJECT-TYPE
		SYNTAX					 Counter32
		MAX-ACCESS			 read-only
		STATUS					 current
		DESCRIPTION			 " -- "
		::=  { x2InterfaceTrafficStat  1 }


	x2OutNbrOctets		 OBJECT-TYPE
		SYNTAX					 Counter32
		MAX-ACCESS			 read-only
		STATUS					 current
		DESCRIPTION			 " -- "
		::=  { x2InterfaceTrafficStat  2 }


	x2InNbrOctetsUserPlane		 OBJECT-TYPE
		SYNTAX					 Counter32
		MAX-ACCESS			 read-only
		STATUS					 current
		DESCRIPTION			 " -- "
		::=  { x2InterfaceTrafficStat  3 }


	x2OutNbrOctetsUserPlane		 OBJECT-TYPE
		SYNTAX					 Counter32
		MAX-ACCESS			 read-only
		STATUS					 current
		DESCRIPTION			 " -- "
		::=  { x2InterfaceTrafficStat  4 }


	cpuUsageStatTable		 OBJECT-TYPE
		SYNTAX					 SEQUENCE  OF	 CpuUsageStatEntry
		MAX-ACCESS			 not-accessible
		STATUS					 current
		DESCRIPTION			 " -- "
		::=  { omrelatedOriginCounter  4 }


	cpuUsageStatEntry		 OBJECT-TYPE
		SYNTAX					 CpuUsageStatEntry
		MAX-ACCESS			 not-accessible
		STATUS					 current
		DESCRIPTION			 " -- "
		INDEX						{ cpuUsageStatProcRackNo,cpuUsageStatProcShelfNo,cpuUsageStatProcSlotNo,cpuUsageStatProcIndexOnBoard }
		::=  { cpuUsageStatTable  1 }


	CpuUsageStatEntry		 ::=  SEQUENCE {
		cpuUsageStatProcRackNo					Integer32,
		cpuUsageStatProcShelfNo					Integer32,
		cpuUsageStatProcSlotNo					Integer32,
		cpuUsageStatProcIndexOnBoard					Integer32,
		cpuUsageStatRowStatus					RowStatus,
		ospPeakCpuUsageRatio					Counter32,
		ospMeanCpuUsageRatio					Counter32
		}


	cpuUsageStatProcRackNo		 OBJECT-TYPE
		SYNTAX					 Integer32( 0 .. 0 )
		MAX-ACCESS			 not-accessible
		STATUS					 current
		DESCRIPTION			 " -- "
		::=  { cpuUsageStatEntry  1 }


	cpuUsageStatProcShelfNo		 OBJECT-TYPE
		SYNTAX					 Integer32( 0 .. 0 )
		MAX-ACCESS			 not-accessible
		STATUS					 current
		DESCRIPTION			 " -- "
		::=  { cpuUsageStatEntry  2 }


	cpuUsageStatProcSlotNo		 OBJECT-TYPE
		SYNTAX					 Integer32( 0 .. 16 )
		MAX-ACCESS			 not-accessible
		STATUS					 current
		DESCRIPTION			 " -- "
		::=  { cpuUsageStatEntry  3 }


	cpuUsageStatProcIndexOnBoard		 OBJECT-TYPE
		SYNTAX					 Integer32( 0 .. 9 )
		MAX-ACCESS			 not-accessible
		STATUS					 current
		DESCRIPTION			 " -- "
		::=  { cpuUsageStatEntry  4 }


	cpuUsageStatRowStatus		 OBJECT-TYPE
		SYNTAX					 RowStatus
		MAX-ACCESS			 read-only
		STATUS					 current
		DESCRIPTION			 " -- "
		::=  { cpuUsageStatEntry  5 }


	ospPeakCpuUsageRatio		 OBJECT-TYPE
		SYNTAX					 Counter32
		MAX-ACCESS			 read-only
		STATUS					 current
		DESCRIPTION			 " -- "
		::=  { cpuUsageStatEntry  6 }


	ospMeanCpuUsageRatio		 OBJECT-TYPE
		SYNTAX					 Counter32
		MAX-ACCESS			 read-only
		STATUS					 current
		DESCRIPTION			 " -- "
		::=  { cpuUsageStatEntry  7 }


	sctpAssoPMDataTable		 OBJECT-TYPE
		SYNTAX					 SEQUENCE  OF	 SctpAssoPMDataEntry
		MAX-ACCESS			 not-accessible
		STATUS					 current
		DESCRIPTION			 " -- "
		::=  { omrelatedOriginCounter  5 }


	sctpAssoPMDataEntry		 OBJECT-TYPE
		SYNTAX					 SctpAssoPMDataEntry
		MAX-ACCESS			 not-accessible
		STATUS					 current
		DESCRIPTION			 " -- "
		INDEX						{ sctpAssoPMDataSctpIndex }
		::=  { sctpAssoPMDataTable  1 }


	SctpAssoPMDataEntry		 ::=  SEQUENCE {
		sctpAssoPMDataSctpIndex					Integer32,
		sctpAssoPMDataRowStatus					RowStatus,
		sigSctpDataChunkSent					Counter32,
		sigSctpDataChunkReceived					Counter32,
		sigSctpDataChunkReSentUl					Counter32,
		sigSctpCongestionDuration					Counter32,
		sigNbrSctpCongestion					Counter32,
		sigSctpUnavailableDuration					Counter32,
		sigNbrSctpUnavailable					Counter32,
		sigSctpDataChunkReSentDl					Counter32,
		sigSctpDataChunkDropUl					Counter32,
		sigSctpDataChunkDropDl					Counter32,
		sigSctpHearbeatReq					Counter32,
		sigSctpHearbeatResp					Counter32
		}


	sctpAssoPMDataSctpIndex		 OBJECT-TYPE
		SYNTAX					 Integer32( 0 .. 81 )
		MAX-ACCESS			 not-accessible
		STATUS					 current
		DESCRIPTION			 " -- "
		::=  { sctpAssoPMDataEntry  1 }


	sctpAssoPMDataRowStatus		 OBJECT-TYPE
		SYNTAX					 RowStatus
		MAX-ACCESS			 read-only
		STATUS					 current
		DESCRIPTION			 " -- "
		::=  { sctpAssoPMDataEntry  2 }


	sigSctpDataChunkSent		 OBJECT-TYPE
		SYNTAX					 Counter32
		MAX-ACCESS			 read-only
		STATUS					 current
		DESCRIPTION			 " -- "
		::=  { sctpAssoPMDataEntry  3 }


	sigSctpDataChunkReceived		 OBJECT-TYPE
		SYNTAX					 Counter32
		MAX-ACCESS			 read-only
		STATUS					 current
		DESCRIPTION			 " -- "
		::=  { sctpAssoPMDataEntry  4 }


	sigSctpDataChunkReSentUl		 OBJECT-TYPE
		SYNTAX					 Counter32
		MAX-ACCESS			 read-only
		STATUS					 current
		DESCRIPTION			 " -- "
		::=  { sctpAssoPMDataEntry  5 }


	sigSctpCongestionDuration		 OBJECT-TYPE
		SYNTAX					 Counter32
		MAX-ACCESS			 read-only
		STATUS					 current
		DESCRIPTION			 " -- "
		::=  { sctpAssoPMDataEntry  6 }


	sigNbrSctpCongestion		 OBJECT-TYPE
		SYNTAX					 Counter32
		MAX-ACCESS			 read-only
		STATUS					 current
		DESCRIPTION			 " -- "
		::=  { sctpAssoPMDataEntry  7 }


	sigSctpUnavailableDuration		 OBJECT-TYPE
		SYNTAX					 Counter32
		MAX-ACCESS			 read-only
		STATUS					 current
		DESCRIPTION			 " -- "
		::=  { sctpAssoPMDataEntry  8 }


	sigNbrSctpUnavailable		 OBJECT-TYPE
		SYNTAX					 Counter32
		MAX-ACCESS			 read-only
		STATUS					 current
		DESCRIPTION			 " -- "
		::=  { sctpAssoPMDataEntry  9 }


	sigSctpDataChunkReSentDl		 OBJECT-TYPE
		SYNTAX					 Counter32
		MAX-ACCESS			 read-only
		STATUS					 current
		DESCRIPTION			 " -- "
		::=  { sctpAssoPMDataEntry  10 }


	sigSctpDataChunkDropUl		 OBJECT-TYPE
		SYNTAX					 Counter32
		MAX-ACCESS			 read-only
		STATUS					 current
		DESCRIPTION			 " -- "
		::=  { sctpAssoPMDataEntry  11 }


	sigSctpDataChunkDropDl		 OBJECT-TYPE
		SYNTAX					 Counter32
		MAX-ACCESS			 read-only
		STATUS					 current
		DESCRIPTION			 " -- "
		::=  { sctpAssoPMDataEntry  12 }


	sigSctpHearbeatReq		 OBJECT-TYPE
		SYNTAX					 Counter32
		MAX-ACCESS			 read-only
		STATUS					 current
		DESCRIPTION			 " -- "
		::=  { sctpAssoPMDataEntry  13 }


	sigSctpHearbeatResp		 OBJECT-TYPE
		SYNTAX					 Counter32
		MAX-ACCESS			 read-only
		STATUS					 current
		DESCRIPTION			 " -- "
		::=  { sctpAssoPMDataEntry  14 }


	ethPortDataStatTable		 OBJECT-TYPE
		SYNTAX					 SEQUENCE  OF	 EthPortDataStatEntry
		MAX-ACCESS			 not-accessible
		STATUS					 current
		DESCRIPTION			 " -- "
		::=  { omrelatedOriginCounter  6 }


	ethPortDataStatEntry		 OBJECT-TYPE
		SYNTAX					 EthPortDataStatEntry
		MAX-ACCESS			 not-accessible
		STATUS					 current
		DESCRIPTION			 " -- "
		INDEX						{ ethPortDataStatEthRackNo,ethPortDataStatEthShelfNo,ethPortDataStatEthSlotNo,ethPortDataStatEthPhyPortId }
		::=  { ethPortDataStatTable  1 }


	EthPortDataStatEntry		 ::=  SEQUENCE {
		ethPortDataStatEthRackNo					Integer32,
		ethPortDataStatEthShelfNo					Integer32,
		ethPortDataStatEthSlotNo					Integer32,
		ethPortDataStatEthPhyPortId					Integer32,
		ethPortDataStatRowStatus					RowStatus,
		eqptMacOctSent					Counter32,
		eqptMacOctRecieved					Counter32
		}


	ethPortDataStatEthRackNo		 OBJECT-TYPE
		SYNTAX					 Integer32( 0 .. 0 )
		MAX-ACCESS			 not-accessible
		STATUS					 current
		DESCRIPTION			 " -- "
		::=  { ethPortDataStatEntry  1 }


	ethPortDataStatEthShelfNo		 OBJECT-TYPE
		SYNTAX					 Integer32( 0 .. 0 )
		MAX-ACCESS			 not-accessible
		STATUS					 current
		DESCRIPTION			 " -- "
		::=  { ethPortDataStatEntry  2 }


	ethPortDataStatEthSlotNo		 OBJECT-TYPE
		SYNTAX					 Integer32( 0 .. 1 )
		MAX-ACCESS			 not-accessible
		STATUS					 current
		DESCRIPTION			 " -- "
		::=  { ethPortDataStatEntry  3 }


	ethPortDataStatEthPhyPortId		 OBJECT-TYPE
		SYNTAX					 Integer32( 0 .. 1 )
		MAX-ACCESS			 not-accessible
		STATUS					 current
		DESCRIPTION			 " -- "
		::=  { ethPortDataStatEntry  4 }


	ethPortDataStatRowStatus		 OBJECT-TYPE
		SYNTAX					 RowStatus
		MAX-ACCESS			 read-only
		STATUS					 current
		DESCRIPTION			 " -- "
		::=  { ethPortDataStatEntry  5 }


	eqptMacOctSent		 OBJECT-TYPE
		SYNTAX					 Counter32
		MAX-ACCESS			 read-only
		STATUS					 current
		DESCRIPTION			 " -- "
		::=  { ethPortDataStatEntry  6 }


	eqptMacOctRecieved		 OBJECT-TYPE
		SYNTAX					 Counter32
		MAX-ACCESS			 read-only
		STATUS					 current
		DESCRIPTION			 " -- "
		::=  { ethPortDataStatEntry  7 }


	enbCpuUsageStat		 OBJECT IDENTIFIER
		::=  { omrelatedOriginCounter  7 }


	enbOSPPeakCpuUsage		 OBJECT-TYPE
		SYNTAX					 Counter32
		MAX-ACCESS			 read-only
		STATUS					 current
		DESCRIPTION			 " -- "
		::=  { enbCpuUsageStat  1 }


	enbOSPMeanCpuUsage		 OBJECT-TYPE
		SYNTAX					 Counter32
		MAX-ACCESS			 read-only
		STATUS					 current
		DESCRIPTION			 " -- "
		::=  { enbCpuUsageStat  2 }


	signalSoftwareCollection		 OBJECT IDENTIFIER
		::=  { omrelatedOriginCounter  8 }


	signaldataPktNumUl		 OBJECT-TYPE
		SYNTAX					 Counter32
		MAX-ACCESS			 read-only
		STATUS					 current
		DESCRIPTION			 " -- "
		::=  { signalSoftwareCollection  1 }


	signaldataByteNumUl		 OBJECT-TYPE
		SYNTAX					 Counter32
		MAX-ACCESS			 read-only
		STATUS					 current
		DESCRIPTION			 " -- "
		::=  { signalSoftwareCollection  2 }


	cellAvailabilityTable		 OBJECT-TYPE
		SYNTAX					 SEQUENCE  OF	 CellAvailabilityEntry
		MAX-ACCESS			 not-accessible
		STATUS					 current
		DESCRIPTION			 " -- "
		::=  { omrelatedOriginCounter  9 }


	cellAvailabilityEntry		 OBJECT-TYPE
		SYNTAX					 CellAvailabilityEntry
		MAX-ACCESS			 not-accessible
		STATUS					 current
		DESCRIPTION			 " -- "
		INDEX						{ cellAvailabilityLcId }
		::=  { cellAvailabilityTable  1 }


	CellAvailabilityEntry		 ::=  SEQUENCE {
		cellAvailabilityLcId					Integer32,
		cellAvailabilityRowStatus					RowStatus,
		cellAvailDur					Counter32,
		cellUnavailDurSys					Counter32,
		cellUnavailDurManual					Counter32,
		cellUnavailDurEnergySaving					Counter32,
		cellUnavailDurS1Fail					Counter32
		}


	cellAvailabilityLcId		 OBJECT-TYPE
		SYNTAX					 Integer32( 0 .. 23 )
		MAX-ACCESS			 not-accessible
		STATUS					 current
		DESCRIPTION			 " -- "
		::=  { cellAvailabilityEntry  1 }


	cellAvailabilityRowStatus		 OBJECT-TYPE
		SYNTAX					 RowStatus
		MAX-ACCESS			 read-only
		STATUS					 current
		DESCRIPTION			 " -- "
		::=  { cellAvailabilityEntry  2 }


	cellAvailDur		 OBJECT-TYPE
		SYNTAX					 Counter32
		MAX-ACCESS			 read-only
		STATUS					 current
		DESCRIPTION			 " -- "
		::=  { cellAvailabilityEntry  3 }


	cellUnavailDurSys		 OBJECT-TYPE
		SYNTAX					 Counter32
		MAX-ACCESS			 read-only
		STATUS					 current
		DESCRIPTION			 " -- "
		::=  { cellAvailabilityEntry  4 }


	cellUnavailDurManual		 OBJECT-TYPE
		SYNTAX					 Counter32
		MAX-ACCESS			 read-only
		STATUS					 current
		DESCRIPTION			 " -- "
		::=  { cellAvailabilityEntry  5 }


	cellUnavailDurEnergySaving		 OBJECT-TYPE
		SYNTAX					 Counter32
		MAX-ACCESS			 read-only
		STATUS					 current
		DESCRIPTION			 " -- "
		::=  { cellAvailabilityEntry  6 }


	cellUnavailDurS1Fail		 OBJECT-TYPE
		SYNTAX					 Counter32
		MAX-ACCESS			 read-only
		STATUS					 current
		DESCRIPTION			 " -- "
		::=  { cellAvailabilityEntry  7 }


	eNBUnavailableDuring		 OBJECT IDENTIFIER
		::=  { omrelatedOriginCounter  10 }


	enbUnavailDur		 OBJECT-TYPE
		SYNTAX					 Counter32
		MAX-ACCESS			 read-only
		STATUS					 current
		DESCRIPTION			 " -- "
		::=  { eNBUnavailableDuring  1 }


	s1QualityStatistic		 OBJECT IDENTIFIER
		::=  { omrelatedOriginCounter  11 }


	s1SentDiagosisTotalPacket		 OBJECT-TYPE
		SYNTAX					 Counter32
		MAX-ACCESS			 read-only
		STATUS					 current
		DESCRIPTION			 " -- "
		::=  { s1QualityStatistic  1 }


	s1ReceivedDiagosisTotalPacket		 OBJECT-TYPE
		SYNTAX					 Counter32
		MAX-ACCESS			 read-only
		STATUS					 current
		DESCRIPTION			 " -- "
		::=  { s1QualityStatistic  2 }


	s1DiagosisPacketTotalDelay		 OBJECT-TYPE
		SYNTAX					 Counter32
		MAX-ACCESS			 read-only
		STATUS					 current
		DESCRIPTION			 " -- "
		::=  { s1QualityStatistic  3 }


	s1DiagosisPacketTotalJitter		 OBJECT-TYPE
		SYNTAX					 Counter32
		MAX-ACCESS			 read-only
		STATUS					 current
		DESCRIPTION			 " -- "
		::=  { s1QualityStatistic  4 }


	mrFileStatistic		 OBJECT IDENTIFIER
		::=  { omrelatedOriginCounter  12 }


	mrMreFileReq		 OBJECT-TYPE
		SYNTAX					 Counter32
		MAX-ACCESS			 read-only
		STATUS					 current
		DESCRIPTION			 " -- "
		::=  { mrFileStatistic  1 }


	mrMreFileSucc		 OBJECT-TYPE
		SYNTAX					 Counter32
		MAX-ACCESS			 read-only
		STATUS					 current
		DESCRIPTION			 " -- "
		::=  { mrFileStatistic  2 }


	mrMrsFileReq		 OBJECT-TYPE
		SYNTAX					 Counter32
		MAX-ACCESS			 read-only
		STATUS					 current
		DESCRIPTION			 " -- "
		::=  { mrFileStatistic  3 }


	mrMrsFileSucc		 OBJECT-TYPE
		SYNTAX					 Counter32
		MAX-ACCESS			 read-only
		STATUS					 current
		DESCRIPTION			 " -- "
		::=  { mrFileStatistic  4 }


	mrMroueFileReq		 OBJECT-TYPE
		SYNTAX					 Counter32
		MAX-ACCESS			 read-only
		STATUS					 current
		DESCRIPTION			 " -- "
		::=  { mrFileStatistic  5 }


	mrMroueFileSucc		 OBJECT-TYPE
		SYNTAX					 Counter32
		MAX-ACCESS			 read-only
		STATUS					 current
		DESCRIPTION			 " -- "
		::=  { mrFileStatistic  6 }


	mrMROPLRFileReq		 OBJECT-TYPE
		SYNTAX					 Counter32
		MAX-ACCESS			 read-only
		STATUS					 current
		DESCRIPTION			 " -- "
		::=  { mrFileStatistic  7 }


	mrMROPLRFileSucc		 OBJECT-TYPE
		SYNTAX					 Counter32
		MAX-ACCESS			 read-only
		STATUS					 current
		DESCRIPTION			 " -- "
		::=  { mrFileStatistic  8 }


	mrMronoueFileReq		 OBJECT-TYPE
		SYNTAX					 Counter32
		MAX-ACCESS			 read-only
		STATUS					 current
		DESCRIPTION			 " -- "
		::=  { mrFileStatistic  9 }


	mrMronoueFileSucc		 OBJECT-TYPE
		SYNTAX					 Counter32
		MAX-ACCESS			 read-only
		STATUS					 current
		DESCRIPTION			 " -- "
		::=  { mrFileStatistic  10 }


	rlcrelatedOriginCounter		 OBJECT IDENTIFIER
		::=  { pmOriginCounterGrpInfo  7 }


	pdcpSduDlDiscRatioTable		 OBJECT-TYPE
		SYNTAX					 SEQUENCE  OF	 PdcpSduDlDiscRatioEntry
		MAX-ACCESS			 not-accessible
		STATUS					 current
		DESCRIPTION			 " -- "
		::=  { rlcrelatedOriginCounter  1 }


	pdcpSduDlDiscRatioEntry		 OBJECT-TYPE
		SYNTAX					 PdcpSduDlDiscRatioEntry
		MAX-ACCESS			 not-accessible
		STATUS					 current
		DESCRIPTION			 " -- "
		INDEX						{ pdcpSduDlDiscRatioLcId }
		::=  { pdcpSduDlDiscRatioTable  1 }


	PdcpSduDlDiscRatioEntry		 ::=  SEQUENCE {
		pdcpSduDlDiscRatioLcId					Integer32,
		pdcpSduDlDiscRatioRowStatus					RowStatus,
		pdcpSduSendTotalDataNumQci1					Counter32,
		pdcpSduSendTotalDataNumQci2					Counter32,
		pdcpSduSendTotalDataNumQci3					Counter32,
		pdcpSduSendTotalDataNumQci4					Counter32,
		pdcpSduSendTotalDataNumQci5					Counter32,
		pdcpSduSendTotalDataNumQci6					Counter32,
		pdcpSduSendTotalDataNumQci7					Counter32,
		pdcpSduSendTotalDataNumQci8					Counter32,
		pdcpSduSendTotalDataNumQci9					Counter32,
		pdcpSduDiscTotalDataNumQci1					Counter32,
		pdcpSduDiscTotalDataNumQci2					Counter32,
		pdcpSduDiscTotalDataNumQci3					Counter32,
		pdcpSduDiscTotalDataNumQci4					Counter32,
		pdcpSduDiscTotalDataNumQci5					Counter32,
		pdcpSduDiscTotalDataNumQci6					Counter32,
		pdcpSduDiscTotalDataNumQci7					Counter32,
		pdcpSduDiscTotalDataNumQci8					Counter32,
		pdcpSduDiscTotalDataNumQci9					Counter32,
		pdcpUpPktDiscardRateDlEnb					Counter32,
		pdcpUpPktDiscardRateDlQci1Enb					Counter32,
		pdcpUpPktDiscardRateDlQci2Enb					Counter32,
		pdcpUpPktDiscardRateDlQci3Enb					Counter32,
		pdcpUpPktDiscardRateDlQci4Enb					Counter32,
		pdcpUpPktDiscardRateDlQci5Enb					Counter32,
		pdcpUpPktDiscardRateDlQci6Enb					Counter32,
		pdcpUpPktDiscardRateDlQci7Enb					Counter32,
		pdcpUpPktDiscardRateDlQci8Enb					Counter32,
		pdcpUpPktDiscardRateDlQci9Enb					Counter32
		}


	pdcpSduDlDiscRatioLcId		 OBJECT-TYPE
		SYNTAX					 Integer32( 0 .. 23 )
		MAX-ACCESS			 not-accessible
		STATUS					 current
		DESCRIPTION			 " -- "
		::=  { pdcpSduDlDiscRatioEntry  1 }


	pdcpSduDlDiscRatioRowStatus		 OBJECT-TYPE
		SYNTAX					 RowStatus
		MAX-ACCESS			 read-only
		STATUS					 current
		DESCRIPTION			 " -- "
		::=  { pdcpSduDlDiscRatioEntry  2 }


	pdcpSduSendTotalDataNumQci1		 OBJECT-TYPE
		SYNTAX					 Counter32
		MAX-ACCESS			 read-only
		STATUS					 current
		DESCRIPTION			 " -- "
		::=  { pdcpSduDlDiscRatioEntry  3 }


	pdcpSduSendTotalDataNumQci2		 OBJECT-TYPE
		SYNTAX					 Counter32
		MAX-ACCESS			 read-only
		STATUS					 current
		DESCRIPTION			 " -- "
		::=  { pdcpSduDlDiscRatioEntry  4 }


	pdcpSduSendTotalDataNumQci3		 OBJECT-TYPE
		SYNTAX					 Counter32
		MAX-ACCESS			 read-only
		STATUS					 current
		DESCRIPTION			 " -- "
		::=  { pdcpSduDlDiscRatioEntry  5 }


	pdcpSduSendTotalDataNumQci4		 OBJECT-TYPE
		SYNTAX					 Counter32
		MAX-ACCESS			 read-only
		STATUS					 current
		DESCRIPTION			 " -- "
		::=  { pdcpSduDlDiscRatioEntry  6 }


	pdcpSduSendTotalDataNumQci5		 OBJECT-TYPE
		SYNTAX					 Counter32
		MAX-ACCESS			 read-only
		STATUS					 current
		DESCRIPTION			 " -- "
		::=  { pdcpSduDlDiscRatioEntry  7 }


	pdcpSduSendTotalDataNumQci6		 OBJECT-TYPE
		SYNTAX					 Counter32
		MAX-ACCESS			 read-only
		STATUS					 current
		DESCRIPTION			 " -- "
		::=  { pdcpSduDlDiscRatioEntry  8 }


	pdcpSduSendTotalDataNumQci7		 OBJECT-TYPE
		SYNTAX					 Counter32
		MAX-ACCESS			 read-only
		STATUS					 current
		DESCRIPTION			 " -- "
		::=  { pdcpSduDlDiscRatioEntry  9 }


	pdcpSduSendTotalDataNumQci8		 OBJECT-TYPE
		SYNTAX					 Counter32
		MAX-ACCESS			 read-only
		STATUS					 current
		DESCRIPTION			 " -- "
		::=  { pdcpSduDlDiscRatioEntry  10 }


	pdcpSduSendTotalDataNumQci9		 OBJECT-TYPE
		SYNTAX					 Counter32
		MAX-ACCESS			 read-only
		STATUS					 current
		DESCRIPTION			 " -- "
		::=  { pdcpSduDlDiscRatioEntry  11 }


	pdcpSduDiscTotalDataNumQci1		 OBJECT-TYPE
		SYNTAX					 Counter32
		MAX-ACCESS			 read-only
		STATUS					 current
		DESCRIPTION			 " -- "
		::=  { pdcpSduDlDiscRatioEntry  12 }


	pdcpSduDiscTotalDataNumQci2		 OBJECT-TYPE
		SYNTAX					 Counter32
		MAX-ACCESS			 read-only
		STATUS					 current
		DESCRIPTION			 " -- "
		::=  { pdcpSduDlDiscRatioEntry  13 }


	pdcpSduDiscTotalDataNumQci3		 OBJECT-TYPE
		SYNTAX					 Counter32
		MAX-ACCESS			 read-only
		STATUS					 current
		DESCRIPTION			 " -- "
		::=  { pdcpSduDlDiscRatioEntry  14 }


	pdcpSduDiscTotalDataNumQci4		 OBJECT-TYPE
		SYNTAX					 Counter32
		MAX-ACCESS			 read-only
		STATUS					 current
		DESCRIPTION			 " -- "
		::=  { pdcpSduDlDiscRatioEntry  15 }


	pdcpSduDiscTotalDataNumQci5		 OBJECT-TYPE
		SYNTAX					 Counter32
		MAX-ACCESS			 read-only
		STATUS					 current
		DESCRIPTION			 " -- "
		::=  { pdcpSduDlDiscRatioEntry  16 }


	pdcpSduDiscTotalDataNumQci6		 OBJECT-TYPE
		SYNTAX					 Counter32
		MAX-ACCESS			 read-only
		STATUS					 current
		DESCRIPTION			 " -- "
		::=  { pdcpSduDlDiscRatioEntry  17 }


	pdcpSduDiscTotalDataNumQci7		 OBJECT-TYPE
		SYNTAX					 Counter32
		MAX-ACCESS			 read-only
		STATUS					 current
		DESCRIPTION			 " -- "
		::=  { pdcpSduDlDiscRatioEntry  18 }


	pdcpSduDiscTotalDataNumQci8		 OBJECT-TYPE
		SYNTAX					 Counter32
		MAX-ACCESS			 read-only
		STATUS					 current
		DESCRIPTION			 " -- "
		::=  { pdcpSduDlDiscRatioEntry  19 }


	pdcpSduDiscTotalDataNumQci9		 OBJECT-TYPE
		SYNTAX					 Counter32
		MAX-ACCESS			 read-only
		STATUS					 current
		DESCRIPTION			 " -- "
		::=  { pdcpSduDlDiscRatioEntry  20 }


	pdcpUpPktDiscardRateDlEnb		 OBJECT-TYPE
		SYNTAX					 Counter32
		MAX-ACCESS			 read-only
		STATUS					 current
		DESCRIPTION			 " -- "
		::=  { pdcpSduDlDiscRatioEntry  200 }


	pdcpUpPktDiscardRateDlQci1Enb		 OBJECT-TYPE
		SYNTAX					 Counter32
		MAX-ACCESS			 read-only
		STATUS					 current
		DESCRIPTION			 " -- "
		::=  { pdcpSduDlDiscRatioEntry  201 }


	pdcpUpPktDiscardRateDlQci2Enb		 OBJECT-TYPE
		SYNTAX					 Counter32
		MAX-ACCESS			 read-only
		STATUS					 current
		DESCRIPTION			 " -- "
		::=  { pdcpSduDlDiscRatioEntry  202 }


	pdcpUpPktDiscardRateDlQci3Enb		 OBJECT-TYPE
		SYNTAX					 Counter32
		MAX-ACCESS			 read-only
		STATUS					 current
		DESCRIPTION			 " -- "
		::=  { pdcpSduDlDiscRatioEntry  203 }


	pdcpUpPktDiscardRateDlQci4Enb		 OBJECT-TYPE
		SYNTAX					 Counter32
		MAX-ACCESS			 read-only
		STATUS					 current
		DESCRIPTION			 " -- "
		::=  { pdcpSduDlDiscRatioEntry  204 }


	pdcpUpPktDiscardRateDlQci5Enb		 OBJECT-TYPE
		SYNTAX					 Counter32
		MAX-ACCESS			 read-only
		STATUS					 current
		DESCRIPTION			 " -- "
		::=  { pdcpSduDlDiscRatioEntry  205 }


	pdcpUpPktDiscardRateDlQci6Enb		 OBJECT-TYPE
		SYNTAX					 Counter32
		MAX-ACCESS			 read-only
		STATUS					 current
		DESCRIPTION			 " -- "
		::=  { pdcpSduDlDiscRatioEntry  206 }


	pdcpUpPktDiscardRateDlQci7Enb		 OBJECT-TYPE
		SYNTAX					 Counter32
		MAX-ACCESS			 read-only
		STATUS					 current
		DESCRIPTION			 " -- "
		::=  { pdcpSduDlDiscRatioEntry  207 }


	pdcpUpPktDiscardRateDlQci8Enb		 OBJECT-TYPE
		SYNTAX					 Counter32
		MAX-ACCESS			 read-only
		STATUS					 current
		DESCRIPTION			 " -- "
		::=  { pdcpSduDlDiscRatioEntry  208 }


	pdcpUpPktDiscardRateDlQci9Enb		 OBJECT-TYPE
		SYNTAX					 Counter32
		MAX-ACCESS			 read-only
		STATUS					 current
		DESCRIPTION			 " -- "
		::=  { pdcpSduDlDiscRatioEntry  209 }


	ipThpDlTable		 OBJECT-TYPE
		SYNTAX					 SEQUENCE  OF	 IpThpDlEntry
		MAX-ACCESS			 not-accessible
		STATUS					 current
		DESCRIPTION			 " -- "
		::=  { rlcrelatedOriginCounter  2 }


	ipThpDlEntry		 OBJECT-TYPE
		SYNTAX					 IpThpDlEntry
		MAX-ACCESS			 not-accessible
		STATUS					 current
		DESCRIPTION			 " -- "
		INDEX						{ ipThpDlLcId }
		::=  { ipThpDlTable  1 }


	IpThpDlEntry		 ::=  SEQUENCE {
		ipThpDlLcId					Integer32,
		ipThpDlRowStatus					RowStatus,
		drbThpTimeDlSum					Counter32,
		drbThpTimeDlQci1					Counter32,
		drbThpTimeDlQci2					Counter32,
		drbThpTimeDlQci3					Counter32,
		drbThpTimeDlQci4					Counter32,
		drbThpTimeDlQci5					Counter32,
		drbThpTimeDlQci6					Counter32,
		drbThpTimeDlQci7					Counter32,
		drbThpTimeDlQci8					Counter32,
		drbThpTimeDlQci9					Counter32,
		drbBurstDataThpDLSum					Counter32,
		drbBurstDataThpDLQci1					Counter32,
		drbBurstDataThpDLQci2					Counter32,
		drbBurstDataThpDLQci3					Counter32,
		drbBurstDataThpDLQci4					Counter32,
		drbBurstDataThpDLQci5					Counter32,
		drbBurstDataThpDLQci6					Counter32,
		drbBurstDataThpDLQci7					Counter32,
		drbBurstDataThpDLQci8					Counter32,
		drbBurstDataThpDLQci9					Counter32
		}


	ipThpDlLcId		 OBJECT-TYPE
		SYNTAX					 Integer32( 0 .. 23 )
		MAX-ACCESS			 not-accessible
		STATUS					 current
		DESCRIPTION			 " -- "
		::=  { ipThpDlEntry  1 }


	ipThpDlRowStatus		 OBJECT-TYPE
		SYNTAX					 RowStatus
		MAX-ACCESS			 read-only
		STATUS					 current
		DESCRIPTION			 " -- "
		::=  { ipThpDlEntry  2 }


	drbThpTimeDlSum		 OBJECT-TYPE
		SYNTAX					 Counter32
		MAX-ACCESS			 read-only
		STATUS					 current
		DESCRIPTION			 " -- "
		::=  { ipThpDlEntry  3 }


	drbThpTimeDlQci1		 OBJECT-TYPE
		SYNTAX					 Counter32
		MAX-ACCESS			 read-only
		STATUS					 current
		DESCRIPTION			 " -- "
		::=  { ipThpDlEntry  4 }


	drbThpTimeDlQci2		 OBJECT-TYPE
		SYNTAX					 Counter32
		MAX-ACCESS			 read-only
		STATUS					 current
		DESCRIPTION			 " -- "
		::=  { ipThpDlEntry  5 }


	drbThpTimeDlQci3		 OBJECT-TYPE
		SYNTAX					 Counter32
		MAX-ACCESS			 read-only
		STATUS					 current
		DESCRIPTION			 " -- "
		::=  { ipThpDlEntry  6 }


	drbThpTimeDlQci4		 OBJECT-TYPE
		SYNTAX					 Counter32
		MAX-ACCESS			 read-only
		STATUS					 current
		DESCRIPTION			 " -- "
		::=  { ipThpDlEntry  7 }


	drbThpTimeDlQci5		 OBJECT-TYPE
		SYNTAX					 Counter32
		MAX-ACCESS			 read-only
		STATUS					 current
		DESCRIPTION			 " -- "
		::=  { ipThpDlEntry  8 }


	drbThpTimeDlQci6		 OBJECT-TYPE
		SYNTAX					 Counter32
		MAX-ACCESS			 read-only
		STATUS					 current
		DESCRIPTION			 " -- "
		::=  { ipThpDlEntry  9 }


	drbThpTimeDlQci7		 OBJECT-TYPE
		SYNTAX					 Counter32
		MAX-ACCESS			 read-only
		STATUS					 current
		DESCRIPTION			 " -- "
		::=  { ipThpDlEntry  10 }


	drbThpTimeDlQci8		 OBJECT-TYPE
		SYNTAX					 Counter32
		MAX-ACCESS			 read-only
		STATUS					 current
		DESCRIPTION			 " -- "
		::=  { ipThpDlEntry  11 }


	drbThpTimeDlQci9		 OBJECT-TYPE
		SYNTAX					 Counter32
		MAX-ACCESS			 read-only
		STATUS					 current
		DESCRIPTION			 " -- "
		::=  { ipThpDlEntry  12 }


	drbBurstDataThpDLSum		 OBJECT-TYPE
		SYNTAX					 Counter32
		MAX-ACCESS			 read-only
		STATUS					 current
		DESCRIPTION			 " -- "
		::=  { ipThpDlEntry  13 }


	drbBurstDataThpDLQci1		 OBJECT-TYPE
		SYNTAX					 Counter32
		MAX-ACCESS			 read-only
		STATUS					 current
		DESCRIPTION			 " -- "
		::=  { ipThpDlEntry  14 }


	drbBurstDataThpDLQci2		 OBJECT-TYPE
		SYNTAX					 Counter32
		MAX-ACCESS			 read-only
		STATUS					 current
		DESCRIPTION			 " -- "
		::=  { ipThpDlEntry  15 }


	drbBurstDataThpDLQci3		 OBJECT-TYPE
		SYNTAX					 Counter32
		MAX-ACCESS			 read-only
		STATUS					 current
		DESCRIPTION			 " -- "
		::=  { ipThpDlEntry  16 }


	drbBurstDataThpDLQci4		 OBJECT-TYPE
		SYNTAX					 Counter32
		MAX-ACCESS			 read-only
		STATUS					 current
		DESCRIPTION			 " -- "
		::=  { ipThpDlEntry  17 }


	drbBurstDataThpDLQci5		 OBJECT-TYPE
		SYNTAX					 Counter32
		MAX-ACCESS			 read-only
		STATUS					 current
		DESCRIPTION			 " -- "
		::=  { ipThpDlEntry  18 }


	drbBurstDataThpDLQci6		 OBJECT-TYPE
		SYNTAX					 Counter32
		MAX-ACCESS			 read-only
		STATUS					 current
		DESCRIPTION			 " -- "
		::=  { ipThpDlEntry  19 }


	drbBurstDataThpDLQci7		 OBJECT-TYPE
		SYNTAX					 Counter32
		MAX-ACCESS			 read-only
		STATUS					 current
		DESCRIPTION			 " -- "
		::=  { ipThpDlEntry  20 }


	drbBurstDataThpDLQci8		 OBJECT-TYPE
		SYNTAX					 Counter32
		MAX-ACCESS			 read-only
		STATUS					 current
		DESCRIPTION			 " -- "
		::=  { ipThpDlEntry  21 }


	drbBurstDataThpDLQci9		 OBJECT-TYPE
		SYNTAX					 Counter32
		MAX-ACCESS			 read-only
		STATUS					 current
		DESCRIPTION			 " -- "
		::=  { ipThpDlEntry  22 }


	caThroughputTable		 OBJECT-TYPE
		SYNTAX					 SEQUENCE  OF	 CaThroughputEntry
		MAX-ACCESS			 not-accessible
		STATUS					 current
		DESCRIPTION			 " -- "
		::=  { rlcrelatedOriginCounter  3 }


	caThroughputEntry		 OBJECT-TYPE
		SYNTAX					 CaThroughputEntry
		MAX-ACCESS			 not-accessible
		STATUS					 current
		DESCRIPTION			 " -- "
		INDEX						{ caThroughputLcId }
		::=  { caThroughputTable  1 }


	CaThroughputEntry		 ::=  SEQUENCE {
		caThroughputLcId					Integer32,
		caThroughputRowStatus					RowStatus,
		pdcpThpCaActiveDl2CC					Counter32,
		pdcpThpCaActiveUl2CC					Counter32,
		macCaActiveBurstDataThPDl2CC					Counter32,
		macCaActiveThrpTimeDL2CC					Counter32,
		pdcpThpCaActiveDl2CCTF					Counter32,
		macCaActiveBurstDataThPDl2CCTF					Counter32,
		macCaActiveThrpTimeDL2CCTF					Counter32
		}


	caThroughputLcId		 OBJECT-TYPE
		SYNTAX					 Integer32( 0 .. 23 )
		MAX-ACCESS			 not-accessible
		STATUS					 current
		DESCRIPTION			 " -- "
		::=  { caThroughputEntry  1 }


	caThroughputRowStatus		 OBJECT-TYPE
		SYNTAX					 RowStatus
		MAX-ACCESS			 read-only
		STATUS					 current
		DESCRIPTION			 " -- "
		::=  { caThroughputEntry  2 }


	pdcpThpCaActiveDl2CC		 OBJECT-TYPE
		SYNTAX					 Counter32
		MAX-ACCESS			 read-only
		STATUS					 current
		DESCRIPTION			 " -- "
		::=  { caThroughputEntry  3 }


	pdcpThpCaActiveUl2CC		 OBJECT-TYPE
		SYNTAX					 Counter32
		MAX-ACCESS			 read-only
		STATUS					 current
		DESCRIPTION			 " -- "
		::=  { caThroughputEntry  4 }


	macCaActiveBurstDataThPDl2CC		 OBJECT-TYPE
		SYNTAX					 Counter32
		MAX-ACCESS			 read-only
		STATUS					 current
		DESCRIPTION			 " -- "
		::=  { caThroughputEntry  5 }


	macCaActiveThrpTimeDL2CC		 OBJECT-TYPE
		SYNTAX					 Counter32
		MAX-ACCESS			 read-only
		STATUS					 current
		DESCRIPTION			 " -- "
		::=  { caThroughputEntry  6 }


	pdcpThpCaActiveDl2CCTF		 OBJECT-TYPE
		SYNTAX					 Counter32
		MAX-ACCESS			 read-only
		STATUS					 current
		DESCRIPTION			 " -- "
		::=  { caThroughputEntry  7 }


	macCaActiveBurstDataThPDl2CCTF		 OBJECT-TYPE
		SYNTAX					 Counter32
		MAX-ACCESS			 read-only
		STATUS					 current
		DESCRIPTION			 " -- "
		::=  { caThroughputEntry  8 }


	macCaActiveThrpTimeDL2CCTF		 OBJECT-TYPE
		SYNTAX					 Counter32
		MAX-ACCESS			 read-only
		STATUS					 current
		DESCRIPTION			 " -- "
		::=  { caThroughputEntry  9 }


	hoAbnormalIntraCellTable		 OBJECT-TYPE
		SYNTAX					 SEQUENCE  OF	 HoAbnormalIntraCellEntry
		MAX-ACCESS			 not-accessible
		STATUS					 current
		DESCRIPTION			 " -- "
		::=  { rlcrelatedOriginCounter  4 }


	hoAbnormalIntraCellEntry		 OBJECT-TYPE
		SYNTAX					 HoAbnormalIntraCellEntry
		MAX-ACCESS			 not-accessible
		STATUS					 current
		DESCRIPTION			 " -- "
		INDEX						{ hoAbnormalIntraCellLcId }
		::=  { hoAbnormalIntraCellTable  1 }


	HoAbnormalIntraCellEntry		 ::=  SEQUENCE {
		hoAbnormalIntraCellLcId					Integer32,
		hoAbnormalIntraCellRowStatus					RowStatus,
		hoSuccOutRlcIntraCell					Counter32,
		hoIntraCellAbnormalStat					Counter32
		}


	hoAbnormalIntraCellLcId		 OBJECT-TYPE
		SYNTAX					 Integer32( 0 .. 23 )
		MAX-ACCESS			 not-accessible
		STATUS					 current
		DESCRIPTION			 " -- "
		::=  { hoAbnormalIntraCellEntry  1 }


	hoAbnormalIntraCellRowStatus		 OBJECT-TYPE
		SYNTAX					 RowStatus
		MAX-ACCESS			 read-only
		STATUS					 current
		DESCRIPTION			 " -- "
		::=  { hoAbnormalIntraCellEntry  2 }


	hoSuccOutRlcIntraCell		 OBJECT-TYPE
		SYNTAX					 Counter32
		MAX-ACCESS			 read-only
		STATUS					 current
		DESCRIPTION			 " -- "
		::=  { hoAbnormalIntraCellEntry  3 }


	hoIntraCellAbnormalStat		 OBJECT-TYPE
		SYNTAX					 Counter32
		MAX-ACCESS			 read-only
		STATUS					 current
		DESCRIPTION			 " -- "
		::=  { hoAbnormalIntraCellEntry  4 }


	rlcPresetPerformanceTable		 OBJECT-TYPE
		SYNTAX					 SEQUENCE  OF	 RlcPresetPerformanceEntry
		MAX-ACCESS			 not-accessible
		STATUS					 current
		DESCRIPTION			 " -- "
		::=  { rlcrelatedOriginCounter  5 }


	rlcPresetPerformanceEntry		 OBJECT-TYPE
		SYNTAX					 RlcPresetPerformanceEntry
		MAX-ACCESS			 not-accessible
		STATUS					 current
		DESCRIPTION			 " -- "
		INDEX						{ rlcPresetPerformanceLcId }
		::=  { rlcPresetPerformanceTable  1 }


	RlcPresetPerformanceEntry		 ::=  SEQUENCE {
		rlcPresetPerformanceLcId					Integer32,
		rlcPresetPerformanceRowStatus					RowStatus,
		rlcPreset1					Counter32,
		rlcPreset2					Counter32,
		rlcPreset3					Counter32,
		rlcPreset4					Counter32,
		rlcPreset5					Counter32,
		rlcPreset6					Counter32,
		rlcPreset7					Counter32,
		rlcPreset8					Counter32,
		rlcPreset9					Counter32,
		rlcPreset10					Counter32,
		rlcPreset11					Counter32,
		rlcPreset12					Counter32,
		rlcPreset13					Counter32,
		rlcPreset14					Counter32,
		rlcPreset15					Counter32,
		rlcPreset16					Counter32,
		rlcPreset17					Counter32,
		rlcPreset18					Counter32,
		rlcPreset19					Counter32,
		rlcPreset20					Counter32,
		rlcPreset21					Counter32,
		rlcPreset22					Counter32,
		rlcPreset23					Counter32,
		rlcPreset24					Counter32,
		rlcPreset25					Counter32,
		rlcPreset26					Counter32,
		rlcPreset27					Counter32,
		rlcPreset28					Counter32,
		rlcPreset29					Counter32,
		rlcPreset30					Counter32,
		rlcPreset31					Counter32,
		rlcPreset32					Counter32,
		rlcPreset33					Counter32,
		rlcPreset34					Counter32,
		rlcPreset35					Counter32,
		rlcPreset36					Counter32,
		rlcPreset37					Counter32,
		rlcPreset38					Counter32,
		rlcPreset39					Counter32,
		rlcPreset40					Counter32
		}


	rlcPresetPerformanceLcId		 OBJECT-TYPE
		SYNTAX					 Integer32( 0 .. 23 )
		MAX-ACCESS			 not-accessible
		STATUS					 current
		DESCRIPTION			 " -- "
		::=  { rlcPresetPerformanceEntry  1 }


	rlcPresetPerformanceRowStatus		 OBJECT-TYPE
		SYNTAX					 RowStatus
		MAX-ACCESS			 read-only
		STATUS					 current
		DESCRIPTION			 " -- "
		::=  { rlcPresetPerformanceEntry  2 }


	rlcPreset1		 OBJECT-TYPE
		SYNTAX					 Counter32
		MAX-ACCESS			 read-only
		STATUS					 current
		DESCRIPTION			 " -- "
		::=  { rlcPresetPerformanceEntry  3 }


	rlcPreset2		 OBJECT-TYPE
		SYNTAX					 Counter32
		MAX-ACCESS			 read-only
		STATUS					 current
		DESCRIPTION			 " -- "
		::=  { rlcPresetPerformanceEntry  4 }


	rlcPreset3		 OBJECT-TYPE
		SYNTAX					 Counter32
		MAX-ACCESS			 read-only
		STATUS					 current
		DESCRIPTION			 " -- "
		::=  { rlcPresetPerformanceEntry  5 }


	rlcPreset4		 OBJECT-TYPE
		SYNTAX					 Counter32
		MAX-ACCESS			 read-only
		STATUS					 current
		DESCRIPTION			 " -- "
		::=  { rlcPresetPerformanceEntry  6 }


	rlcPreset5		 OBJECT-TYPE
		SYNTAX					 Counter32
		MAX-ACCESS			 read-only
		STATUS					 current
		DESCRIPTION			 " -- "
		::=  { rlcPresetPerformanceEntry  7 }


	rlcPreset6		 OBJECT-TYPE
		SYNTAX					 Counter32
		MAX-ACCESS			 read-only
		STATUS					 current
		DESCRIPTION			 " -- "
		::=  { rlcPresetPerformanceEntry  8 }


	rlcPreset7		 OBJECT-TYPE
		SYNTAX					 Counter32
		MAX-ACCESS			 read-only
		STATUS					 current
		DESCRIPTION			 " -- "
		::=  { rlcPresetPerformanceEntry  9 }


	rlcPreset8		 OBJECT-TYPE
		SYNTAX					 Counter32
		MAX-ACCESS			 read-only
		STATUS					 current
		DESCRIPTION			 " -- "
		::=  { rlcPresetPerformanceEntry  10 }


	rlcPreset9		 OBJECT-TYPE
		SYNTAX					 Counter32
		MAX-ACCESS			 read-only
		STATUS					 current
		DESCRIPTION			 " -- "
		::=  { rlcPresetPerformanceEntry  11 }


	rlcPreset10		 OBJECT-TYPE
		SYNTAX					 Counter32
		MAX-ACCESS			 read-only
		STATUS					 current
		DESCRIPTION			 " -- "
		::=  { rlcPresetPerformanceEntry  12 }


	rlcPreset11		 OBJECT-TYPE
		SYNTAX					 Counter32
		MAX-ACCESS			 read-only
		STATUS					 current
		DESCRIPTION			 " -- "
		::=  { rlcPresetPerformanceEntry  13 }


	rlcPreset12		 OBJECT-TYPE
		SYNTAX					 Counter32
		MAX-ACCESS			 read-only
		STATUS					 current
		DESCRIPTION			 " -- "
		::=  { rlcPresetPerformanceEntry  14 }


	rlcPreset13		 OBJECT-TYPE
		SYNTAX					 Counter32
		MAX-ACCESS			 read-only
		STATUS					 current
		DESCRIPTION			 " -- "
		::=  { rlcPresetPerformanceEntry  15 }


	rlcPreset14		 OBJECT-TYPE
		SYNTAX					 Counter32
		MAX-ACCESS			 read-only
		STATUS					 current
		DESCRIPTION			 " -- "
		::=  { rlcPresetPerformanceEntry  16 }


	rlcPreset15		 OBJECT-TYPE
		SYNTAX					 Counter32
		MAX-ACCESS			 read-only
		STATUS					 current
		DESCRIPTION			 " -- "
		::=  { rlcPresetPerformanceEntry  17 }


	rlcPreset16		 OBJECT-TYPE
		SYNTAX					 Counter32
		MAX-ACCESS			 read-only
		STATUS					 current
		DESCRIPTION			 " -- "
		::=  { rlcPresetPerformanceEntry  18 }


	rlcPreset17		 OBJECT-TYPE
		SYNTAX					 Counter32
		MAX-ACCESS			 read-only
		STATUS					 current
		DESCRIPTION			 " -- "
		::=  { rlcPresetPerformanceEntry  19 }


	rlcPreset18		 OBJECT-TYPE
		SYNTAX					 Counter32
		MAX-ACCESS			 read-only
		STATUS					 current
		DESCRIPTION			 " -- "
		::=  { rlcPresetPerformanceEntry  20 }


	rlcPreset19		 OBJECT-TYPE
		SYNTAX					 Counter32
		MAX-ACCESS			 read-only
		STATUS					 current
		DESCRIPTION			 " -- "
		::=  { rlcPresetPerformanceEntry  21 }


	rlcPreset20		 OBJECT-TYPE
		SYNTAX					 Counter32
		MAX-ACCESS			 read-only
		STATUS					 current
		DESCRIPTION			 " -- "
		::=  { rlcPresetPerformanceEntry  22 }


	rlcPreset21		 OBJECT-TYPE
		SYNTAX					 Counter32
		MAX-ACCESS			 read-only
		STATUS					 current
		DESCRIPTION			 " -- "
		::=  { rlcPresetPerformanceEntry  23 }


	rlcPreset22		 OBJECT-TYPE
		SYNTAX					 Counter32
		MAX-ACCESS			 read-only
		STATUS					 current
		DESCRIPTION			 " -- "
		::=  { rlcPresetPerformanceEntry  24 }


	rlcPreset23		 OBJECT-TYPE
		SYNTAX					 Counter32
		MAX-ACCESS			 read-only
		STATUS					 current
		DESCRIPTION			 " -- "
		::=  { rlcPresetPerformanceEntry  25 }


	rlcPreset24		 OBJECT-TYPE
		SYNTAX					 Counter32
		MAX-ACCESS			 read-only
		STATUS					 current
		DESCRIPTION			 " -- "
		::=  { rlcPresetPerformanceEntry  26 }


	rlcPreset25		 OBJECT-TYPE
		SYNTAX					 Counter32
		MAX-ACCESS			 read-only
		STATUS					 current
		DESCRIPTION			 " -- "
		::=  { rlcPresetPerformanceEntry  27 }


	rlcPreset26		 OBJECT-TYPE
		SYNTAX					 Counter32
		MAX-ACCESS			 read-only
		STATUS					 current
		DESCRIPTION			 " -- "
		::=  { rlcPresetPerformanceEntry  28 }


	rlcPreset27		 OBJECT-TYPE
		SYNTAX					 Counter32
		MAX-ACCESS			 read-only
		STATUS					 current
		DESCRIPTION			 " -- "
		::=  { rlcPresetPerformanceEntry  29 }


	rlcPreset28		 OBJECT-TYPE
		SYNTAX					 Counter32
		MAX-ACCESS			 read-only
		STATUS					 current
		DESCRIPTION			 " -- "
		::=  { rlcPresetPerformanceEntry  30 }


	rlcPreset29		 OBJECT-TYPE
		SYNTAX					 Counter32
		MAX-ACCESS			 read-only
		STATUS					 current
		DESCRIPTION			 " -- "
		::=  { rlcPresetPerformanceEntry  31 }


	rlcPreset30		 OBJECT-TYPE
		SYNTAX					 Counter32
		MAX-ACCESS			 read-only
		STATUS					 current
		DESCRIPTION			 " -- "
		::=  { rlcPresetPerformanceEntry  32 }


	rlcPreset31		 OBJECT-TYPE
		SYNTAX					 Counter32
		MAX-ACCESS			 read-only
		STATUS					 current
		DESCRIPTION			 " -- "
		::=  { rlcPresetPerformanceEntry  33 }


	rlcPreset32		 OBJECT-TYPE
		SYNTAX					 Counter32
		MAX-ACCESS			 read-only
		STATUS					 current
		DESCRIPTION			 " -- "
		::=  { rlcPresetPerformanceEntry  34 }


	rlcPreset33		 OBJECT-TYPE
		SYNTAX					 Counter32
		MAX-ACCESS			 read-only
		STATUS					 current
		DESCRIPTION			 " -- "
		::=  { rlcPresetPerformanceEntry  35 }


	rlcPreset34		 OBJECT-TYPE
		SYNTAX					 Counter32
		MAX-ACCESS			 read-only
		STATUS					 current
		DESCRIPTION			 " -- "
		::=  { rlcPresetPerformanceEntry  36 }


	rlcPreset35		 OBJECT-TYPE
		SYNTAX					 Counter32
		MAX-ACCESS			 read-only
		STATUS					 current
		DESCRIPTION			 " -- "
		::=  { rlcPresetPerformanceEntry  37 }


	rlcPreset36		 OBJECT-TYPE
		SYNTAX					 Counter32
		MAX-ACCESS			 read-only
		STATUS					 current
		DESCRIPTION			 " -- "
		::=  { rlcPresetPerformanceEntry  38 }


	rlcPreset37		 OBJECT-TYPE
		SYNTAX					 Counter32
		MAX-ACCESS			 read-only
		STATUS					 current
		DESCRIPTION			 " -- "
		::=  { rlcPresetPerformanceEntry  39 }


	rlcPreset38		 OBJECT-TYPE
		SYNTAX					 Counter32
		MAX-ACCESS			 read-only
		STATUS					 current
		DESCRIPTION			 " -- "
		::=  { rlcPresetPerformanceEntry  40 }


	rlcPreset39		 OBJECT-TYPE
		SYNTAX					 Counter32
		MAX-ACCESS			 read-only
		STATUS					 current
		DESCRIPTION			 " -- "
		::=  { rlcPresetPerformanceEntry  41 }


	rlcPreset40		 OBJECT-TYPE
		SYNTAX					 Counter32
		MAX-ACCESS			 read-only
		STATUS					 current
		DESCRIPTION			 " -- "
		::=  { rlcPresetPerformanceEntry  42 }


	rrurelatedOriginCounter		 OBJECT IDENTIFIER
		::=  { pmOriginCounterGrpInfo  8 }


	rruTransPowerTable		 OBJECT-TYPE
		SYNTAX					 SEQUENCE  OF	 RruTransPowerEntry
		MAX-ACCESS			 not-accessible
		STATUS					 current
		DESCRIPTION			 " -- "
		::=  { rrurelatedOriginCounter  1 }


	rruTransPowerEntry		 OBJECT-TYPE
		SYNTAX					 RruTransPowerEntry
		MAX-ACCESS			 not-accessible
		STATUS					 current
		DESCRIPTION			 " -- "
		INDEX						{ rruTransPowerTopoRRUNo }
		::=  { rruTransPowerTable  1 }


	RruTransPowerEntry		 ::=  SEQUENCE {
		rruTransPowerTopoRRUNo					Integer32,
		rruTransPowerRowStatus					RowStatus,
		phyRruMaxTxPower					Integer32,
		phyRruMeanTxPower					Integer32
		}


	rruTransPowerTopoRRUNo		 OBJECT-TYPE
		SYNTAX					 Integer32( 0 .. 191 )
		MAX-ACCESS			 not-accessible
		STATUS					 current
		DESCRIPTION			 " -- "
		::=  { rruTransPowerEntry  1 }


	rruTransPowerRowStatus		 OBJECT-TYPE
		SYNTAX					 RowStatus
		MAX-ACCESS			 read-only
		STATUS					 current
		DESCRIPTION			 " -- "
		::=  { rruTransPowerEntry  2 }


	phyRruMaxTxPower		 OBJECT-TYPE
		SYNTAX					 Integer32( -2147483648 .. 2147483647 )
		MAX-ACCESS			 read-only
		STATUS					 current
		DESCRIPTION			 " -- "
		::=  { rruTransPowerEntry  3 }


	phyRruMeanTxPower		 OBJECT-TYPE
		SYNTAX					 Integer32( -2147483648 .. 2147483647 )
		MAX-ACCESS			 read-only
		STATUS					 current
		DESCRIPTION			 " -- "
		::=  { rruTransPowerEntry  4 }

	END
